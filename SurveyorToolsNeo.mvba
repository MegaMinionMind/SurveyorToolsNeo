Attribute VB_Name = "ArcLineIntLocateText"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit

Implements ILocateCommandEvents

Public hostForm As FrmArcLineInt

Private myLC As LocateCriteria

Private Sub ILocateCommandEvents_Accept(ByVal Element As Element, point As Point3d, ByVal view As view)

End Sub



Private Sub ILocateCommandEvents_Cleanup()
   hostForm.Show
   ClearCommandPromptArea
   CommandState.EnableAccuSnap
End Sub



Private Sub ILocateCommandEvents_Dynamics(point As Point3d, ByVal view As view, ByVal DrawMode As MsdDrawingMode)
   
End Sub



Private Sub ILocateCommandEvents_LocateFailed()
End Sub



Private Sub ILocateCommandEvents_LocateFilter(ByVal Element As Element, point As Point3d, Accepted As Boolean)
   Dim myEl As Element
   Set myEl = CommandState.GetLocatedElement(False)
   If myEl.IsTextElement Then
          hostForm.EnterText myEl.AsTextElement.text
   End If
   CommandState.StartDefaultCommand
   Accepted = False
End Sub



Private Sub ILocateCommandEvents_LocateReset()
   CommandState.StartDefaultCommand
End Sub



Private Sub ILocateCommandEvents_Start()
   Set myLC = CommandState.CreateLocateCriteria(False)
   myLC.ExcludeAllTypes
   myLC.IncludeType msdElementTypeText
   myLC.IncludeType msdElementTypeTextNode
   myLC.IncludeType msdElementTypeCellHeader
   CommandState.SetLocateCriteria myLC
   
   ShowCommand COMMAND_NAME_ARC_LINE_INT
   ShowPrompt "Pick Text Element/Reset"

   ActiveModelReference.UnselectAllElements

   CommandState.DisableAccuSnap
End Sub

Attribute VB_Name = "Attributes"
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit

Public Const BY_LEVEL     As String = "ByLevel"

Private WasChosen         As Boolean             'TRUE IF COLOR WAS CHOSEN
Private TheColorString    As String              'THE STRING FOR THE COLOR CHOSEN

'*************************************************************************************************************
'************************************ATTRIBUTES COMBOBOX HANDLING*********************************************
'********COLOR COMBOBOX*******
Public Sub ColorBoxOnUpdate(ColorBox As ComboBox, ByVal Section As String, ByVal Key As String)
'PROCESS COLOR ENTRY
   If ColorBox.MatchFound Then
'SAVE TO SETTINGS IF ALREADY IN THE LIST
      SaveSetting APP_NAME, Section, Key, ColorBox.text
   Else
'REVERT TO SAVED SETTINGS IF NOT GOOD
      ColorBox.text = GetSetting(APP_NAME, Section, Key, "0")
      Beep
   End If
End Sub

Public Sub PopulateColorBox(ColorBox As ComboBox, ByVal Section As String, ByVal Key As String)
'POPULATE COLOR COMBOBOX
   ColorBox.style = fmStyleDropDownList
   ColorBox.Clear
   ColorBox.AddItem BY_LEVEL
   Dim previousColor As String
   previousColor = GetSetting(APP_NAME, Section, Key, "0")
   If previousColor = BY_LEVEL Then
      ColorBox.listIndex = 0
   End If
   Dim i As Long
   i = 0
   While i < 256
      Dim MyColor As String
      MyColor = Val(i)
      ColorBox.AddItem MyColor
      If MyColor = previousColor Then
         ColorBox.listIndex = i + 1
      End If
      i = i + 1
   Wend
End Sub



'********LEVEL COMBOBOX*************
Public Function LevelBoxOnUpdate(LevelBox As ComboBox, Section As String, Key As String) As Boolean
'PROCESS LEVEL ENTRY
'RETURNS TRUE IF GOOD, FALSE IF NOT
'INITIALIZE FLAG
   LevelBoxOnUpdate = False
'MAKE SURE IT'S A VALID LEVEL
   If CheckLevelName(LevelBox.text) Then
'SAVE TO SETTINGS IF IT'S VALID
      SaveSetting APP_NAME, Section, Key, LevelBox.text
      LevelBoxOnUpdate = True
   End If
End Function

Public Function CheckLevelName(EnteredLevelName As String) As Boolean
'PROCESS ENTRY, RETURNS TRUE IF GOOD
'MAKE SURE IT'S A VALID LEVEL
'INITIALIZE FLAG
   CheckLevelName = False
   
'CYCLE THROUGH THE VALID LEVEL NAMES
   Dim myLevel As Level
   For Each myLevel In ActiveDesignFile.Levels
      If myLevel.name = EnteredLevelName Then
'FOUND, RETURN TRUE
         CheckLevelName = True
         Exit Function
      End If
   Next
End Function

Public Sub PopulateLevelBox(LevelBox As ComboBox, ByVal Section As String, ByVal Key As String)
   HandleNoActiveLevel
'POPULATE LEVEL COMBOBOX
   LevelBox.style = fmStyleDropDownList
   LevelBox.Clear
   Dim previousLevel As String
   previousLevel = GetSetting(APP_NAME, Section, Key, "Default")
   Dim i As Long
   i = 0
   Dim myLevel As Level
   For Each myLevel In ActiveDesignFile.Levels
      LevelBox.AddItem myLevel.name
      If myLevel.name = previousLevel Then
'SET INDEX OF FONT TO USE
         LevelBox.listIndex = i
      End If
      i = i + 1
   Next
   If LevelBox.listIndex = -1 Then
'IF PREVIOUS LEVEL IS NOT VALID, USE ACTIVE SETTINGS
      LevelBox.text = ActiveSettings.Level.name
      SaveSetting APP_NAME, Section, Key, LevelBox.text
   End If
End Sub



'********LINESTYLE COMBOBOX*************
Public Function LineStyleBoxOnUpdate(LinestyleBox As ComboBox, ByVal Section As String, ByVal Key As String) As Boolean
'PROCESS LINESTYLE ENTRY
'RETURNS TRUE IF GOOD, FALSE IF NOT GOOD
'INITIALIZE FLAG
   LineStyleBoxOnUpdate = False

'CHECK IF VALID LINESTYLE
   If CheckValidLinestyle(LinestyleBox.text) Then
'IF IT IS VALID, THEN SAVE IT AS THE NEW PREVIOUS LINESTYLE
      SaveSetting APP_NAME, Section, Key, LinestyleBox.text
   End If

'CHECK IF IT IS IN CURRENT LIST
   If LinestyleBox.MatchFound Then
      LineStyleBoxOnUpdate = True
   End If
End Function

Public Sub PopulateLinestyleBox(LinestyleBox As ComboBox, ByVal Section As String, ByVal Key As String)
'POPULATE LINESTYLE COMBOBOX
   LinestyleBox.style = fmStyleDropDownList
   LinestyleBox.Clear
   Dim previousStyle As String
   previousStyle = GetSetting(APP_NAME, Section, Key, "0")
   LinestyleBox.AddItem BY_LEVEL
   If previousStyle = BY_LEVEL Then
      LinestyleBox.listIndex = 0
   End If
   Dim i As Integer
   i = 1
   Dim myLineStyle As LineStyle
   For Each myLineStyle In ActiveDesignFile.LineStyles
      LinestyleBox.AddItem myLineStyle.name
      If myLineStyle.name = previousStyle Then
         LinestyleBox.listIndex = i
      End If
      i = i + 1
   Next
'IF PREVIOUS LINE STYLE NOT FOUND, THEN USE CURRENT LINE STYLE
    If LinestyleBox.listIndex = -1 Then
       LinestyleBox.text = ActiveSettings.LineStyle.name
       SaveSetting APP_NAME, Section, Key, LinestyleBox.text
    End If
End Sub

Public Function CheckValidLinestyle(ByVal linestyleName As String) As Boolean
'CHECK IF A LINESTYLE NAME IS VALID, TRUE IF VALID
'INITIALIZE FLAG
   CheckValidLinestyle = False

'IF BYLEVEL, THEN GOOD
   If linestyleName = BY_LEVEL Then
      CheckValidLinestyle = True
      Exit Function
   End If

'CHECK OTHER NAMES
   Dim myLineStyle As LineStyle
   For Each myLineStyle In ActiveDesignFile.LineStyles
      If linestyleName = myLineStyle.name Then
         CheckValidLinestyle = True
         Exit Function
      End If
   Next
End Function



'********WEIGHT COMBOBOX*************
Public Sub WeightBoxOnUpdate(WeightBox As ComboBox, ByVal Section As String, ByVal Key As String)
'PROCESS ENTRY
   If WeightBox.MatchFound Then
      SaveSetting APP_NAME, Section, Key, WeightBox.text
   Else
      WeightBox.text = GetSetting(APP_NAME, Section, Key, "0")
      Beep
   End If
End Sub

Public Sub PopulateWeightBox(WeightBox As ComboBox, ByVal Section As String, ByVal Key As String)
'POPULATE WEIGHT COMBOBOX
   WeightBox.style = fmStyleDropDownList
   WeightBox.Clear
   WeightBox.AddItem BY_LEVEL
   Dim previousWeight As String
   previousWeight = GetSetting(APP_NAME, Section, Key, "0")
   If previousWeight = BY_LEVEL Then
      WeightBox.listIndex = 0
   End If
   Dim i As Long
   i = 0
   While i < 32
      Dim myWeight As String
      myWeight = Val(i)
      WeightBox.AddItem myWeight
      If myWeight = previousWeight Then
         WeightBox.listIndex = i + 1
      End If
      i = i + 1
   Wend
End Sub



'********FONT COMBOBOX*************
Public Function FontBoxOnUpdate(FontBox As ComboBox, ByVal Section As String, ByVal Key As String) As Boolean
'PROCESS FONT ENTRY
'RETURNS TRUE IF GOOD, FALSE IF NOT GOOD
'INITIALIZE FLAG
   FontBoxOnUpdate = False

'CHECK IF VALID FONTNAME
   If CheckFontName(FontBox.text) Then
'IF IT IS VALID, THEN SAVE IT AS THE NEW PREVIOUS LINESTYLE
      SaveSetting APP_NAME, Section, Key, FontBox.text
   End If

'CHECK IF IT IS IN CURRENT LIST
   If FontBox.MatchFound Then
      FontBoxOnUpdate = True
   End If
End Function

Public Sub PopulateFontBox(FontBox As ComboBox, ByVal Section As String, ByVal Key As String)
   HandleNoActiveFont
'POPULATE FONT COMBOBOX
   FontBox.style = fmStyleDropDownList
   FontBox.Clear
   Dim previousFont As String
   previousFont = GetSetting(APP_NAME, Section, Key, STRING_SPACE)
   If previousFont = STRING_SPACE Then
'SET PREVIOUS FONT TO THE ACTIVE FONT
      previousFont = ActiveSettings.Font.name
   End If
   
'POPULATE TEXT BOX WITH AVAILABLE FONTS
   Dim i As Long
   i = 0
   
   Dim SHXFontCapable As Boolean
   SHXFontCapable = IsShxFontAllowed()
   Dim TrueTypeFontCapable As Boolean
   TrueTypeFontCapable = IsTrueTypeFontAllowed()
   Dim UnknownTypeCapable As Boolean
   UnknownTypeCapable = IsRscFontAllowed()
   
   Dim myfont As Font
   For Each myfont In ActiveDesignFile.Fonts
      If myfont.Type = msdFontTypeMicroStation Then
'INCLUDE MICROSTATION FONTS
         FontBox.AddItem myfont.name
         If myfont.name = previousFont Then
'SET INDEX IF PREVIOUS FONT IS AVAILABLE
            FontBox.listIndex = i
         End If
         i = i + 1
      ElseIf myfont.Type = msdFontTypeSHX And SHXFontCapable Then
         FontBox.AddItem myfont.name
         If myfont.name = previousFont Then
'SET INDEX IF PREVIOUS FONT IS AVAILABLE
            FontBox.listIndex = i
         End If
         i = i + 1
      ElseIf myfont.Type = msdFontTypeWindowsTrueType And TrueTypeFontCapable Then
         FontBox.AddItem myfont.name
         If myfont.name = previousFont Then
'SET INDEX IF PREVIOUS FONT IS AVAILABLE
            FontBox.listIndex = i
         End If
         i = i + 1
      ElseIf myfont.Type = msdFontTypeUnknown And UnknownTypeCapable Then
         FontBox.AddItem myfont.name
         If myfont.name = previousFont Then
'SET INDEX IF PREVIOUS FONT IS AVAILABLE
            FontBox.listIndex = i
         End If
         i = i + 1
      End If
   Next

'IF PREVIOUS FONT WAS NOT FOUND, USE ACTIVE FONT
   If FontBox.listIndex = -1 Then
      Dim FontName As String
      FontName = ActiveSettings.Font.name
      For i = 0 To FontBox.topIndex
         If FontBox.List(i) = FontName Then
'SET INDEX IF PREVIOUS FONT IS AVAILABLE
            FontBox.listIndex = i
         End If
         i = i + 1
      Next
      
      If FontBox.listIndex = -1 Then
'IF ACTIVE FONT IS NOT AN AVAILABLE FONT, THEN SET TO FIRST FONT IN THE LISTBOX
         FontBox.listIndex = 0
      End If
      SaveSetting APP_NAME, Section, Key, FontBox.text
   End If
End Sub

Public Function CheckFontName(TheFontName As String) As Boolean
'VERIFY FONT NAME IS USABLE
'RETURNS TRUE IF IT IS OKAY
'INITIALIZE FLAGS
   CheckFontName = False

   Dim SHXFontCapable As Boolean
   SHXFontCapable = IsShxFontAllowed()
   Dim TrueTypeFontCapable As Boolean
   TrueTypeFontCapable = IsTrueTypeFontAllowed()
   Dim UnknownTypeCapable As Boolean
   UnknownTypeCapable = IsRscFontAllowed()


'GET ACTIVE FONTS AND CYCLE THROUGH THEM
   Dim myfont As Font
   For Each myfont In ActiveDesignFile.Fonts
      If myfont.Type = msdFontTypeMicroStation Then
'COMPARE THE MICROSTATION FONT NAMES TO SELECTED FONT NAME
         If myfont.name = TheFontName Then
'IF MICROSTATION FONT NAME IS SAME AS SELECTED FONT NAME, THEN SELECTED FONT NAME IS OKAY
            CheckFontName = True
            Exit Function
         End If
      ElseIf myfont.Type = msdFontTypeWindowsTrueType And TrueTypeFontCapable Then
         If myfont.name = TheFontName Then
'IF TRUETYPE FONT NAME IS SAME AS SELECTED FONT NAME, THEN SELECTED FONT NAME IS OKAY
            CheckFontName = True
            Exit Function
         End If
      ElseIf myfont.Type = msdFontTypeSHX And SHXFontCapable Then
         If myfont.name = TheFontName Then
'IF AUTOCAD FONT NAME IS SAME AS SELECTED FONT NAME, THEN SELECTED FONT NAME IS OKAY
            CheckFontName = True
            Exit Function
         End If
      ElseIf myfont.Type = msdFontTypeUnknown And UnknownTypeCapable Then
'IF AUTOCAD FONT NAME IS SAME AS SELECTED FONT NAME, THEN SELECTED FONT NAME IS OKAY
         If myfont.name = TheFontName Then
            CheckFontName = True
            Exit Function
         End If
      End If
   Next
End Function




'*************************************************************************************************************
'**********************************************CREATE TEMPLATES***********************************************
Public Function CreateLineTemplate(ByVal Section As String, _
                                   ByRef LevelBox As ComboBox, _
                                   ByVal levelKey As String, _
                                   ByRef WeightBox As ComboBox, _
                                   ByRef ColorBox As ComboBox, _
                                   ByRef LinestyleBox As ComboBox, _
                                   ByVal LinestyleKey As String) As LineElement
'CREATE A LINE ELEMENT TO WORK WITH
   Dim seedPoint As Point3d
   seedPoint = Point3dFromXYZ(0, 0, 0)
   Dim TemplateLine As LineElement
   Set TemplateLine = CreateLineElement2(Nothing, seedPoint, seedPoint)
   
'GET THE LEVEL
'IF SELECTED LEVEL IS NOT VALID, REPOPULATE THE LEVEL COMBOBOX
   If Not CheckLevelName(LevelBox.text) Then
      PopulateLevelBox LevelBox, Section, levelKey
   End If

'SET THE LEVEL
   Dim oLevel As Level
   Set oLevel = ActiveDesignFile.Levels.Find(LevelBox.text)
   
'SET LEVEL FOR LINE
   TemplateLine.Level = oLevel

'GET THE LINE WEIGHT FOR LINE
   If WeightBox.text = BY_LEVEL Then
      TemplateLine.LineWeight = ByLevelLineWeight
   Else
      TemplateLine.LineWeight = CInt(WeightBox.text)
   End If

'SET COLOR FOR LINE
   If ColorBox.text = BY_LEVEL Then
      TemplateLine.color = ByLevelColor
   Else
      TemplateLine.color = CInt(ColorBox.text)
   End If

'GET THE LINESTYLE
'IF LINESTYLE NOT VALID, REPOPULATE THE LINESTYLE BOX
   If Not CheckValidLinestyle(LinestyleBox.text) Then
      PopulateLinestyleBox LinestyleBox, Section, LinestyleKey
   End If

'SET THE LINESTYLE FOR THE LINE
   If LinestyleBox.text = BY_LEVEL Then
      TemplateLine.LineStyle = ByLevelLineStyle
   Else
      TemplateLine.LineStyle = ActiveDesignFile.LineStyles.Find(LinestyleBox.text)
   End If
   
'RETURN TEMPLATE
   Set CreateLineTemplate = TemplateLine
End Function



Public Function CreateTextTemplate(Section As String, _
                                   FontComboBox As ComboBox, _
                                   fontKey As String, _
                                   LevelComboBox As ComboBox, _
                                   levelKey As String, _
                                   WeightComboBox As ComboBox, _
                                   ColorComboBox As ComboBox, _
                                   StyleComboBox As ComboBox, _
                                   styleKey As String, _
                                   Optional characterSize As Double = -1, _
                                   Optional justif As MsdTextJustification = _
                                   msdTextJustificationLeftCenter) As TextElement

'CHECK IF OPTION ENTERED
   If characterSize = -1 Then
      characterSize = GetCharSize()
   End If

'RECHECK FONT
   If Not CheckFontName(FontComboBox.text) Then
      PopulateFontBox FontComboBox, Section, fontKey
   End If
'CREATE A LINE TEMPLATE FROM THE SETTINGS
   Dim TemplateLine As LineElement
   Set TemplateLine = CreateLineTemplate(Section, _
                                         LevelComboBox, _
                                         levelKey, _
                                         WeightComboBox, _
                                         ColorComboBox, _
                                         StyleComboBox, _
                                         styleKey)

   Dim seedPoint As Point3d
   seedPoint = Point3dFromXYZ(0, 0, 0)
   Dim myTextTemplate As TextElement
   Set myTextTemplate = CreateTextElement1Fixed(TemplateLine, "Template", seedPoint, Matrix3dIdentity)
   Dim MyTextStyle As TextStyle
   Set MyTextStyle = myTextTemplate.TextStyle
   MyTextStyle.Width = characterSize
   MyTextStyle.Height = characterSize
   MyTextStyle.Justification = justif
   MyTextStyle.Font = ActiveDesignFile.Fonts.Find(msdFontTypeUnknown, FontComboBox.text)

'WORK AROUND FOR BUG IN CE
#If VBA7 Then
   MyTextStyle.color = TemplateLine.color
#End If
      
   Set myTextTemplate.TextStyle = MyTextStyle
   Set CreateTextTemplate = myTextTemplate
End Function



Public Function CreateTextElement1Fixed(template As Element, text As String, origin As Point3d, rotation As Matrix3d) As TextElement
   If ActiveSettings.AnnotationScaleEnabled = True Then
      ActiveSettings.AnnotationScaleEnabled = False
      Set CreateTextElement1Fixed = CreateTextElement1(template, text, origin, rotation)
      ActiveSettings.AnnotationScaleEnabled = True
   Else
      Set CreateTextElement1Fixed = CreateTextElement1(template, text, origin, rotation)
   End If
End Function


'*************************************************************************************************************
'***************************************DETERMINING ALLOWABLE FONTS*******************************************
Private Function IsShxFontAllowed() As Boolean
    IsShxFontAllowed = IsFontTypeAllowed("-CAPABILITY_TEXT_FONTS_SHX")
End Function



Private Function IsTrueTypeFontAllowed() As Boolean
    IsTrueTypeFontAllowed = IsFontTypeAllowed("-CAPABILITY_TEXT_FONTS_TRUETYPE")
End Function



Private Function IsRscFontAllowed() As Boolean
    IsRscFontAllowed = IsFontTypeAllowed("-CAPABILITY_TEXT_FONTS_RSC")
End Function



Private Function IsFontTypeAllowed(fontCapability As String) As Boolean
    Dim capability As String
    capability = GetCapabilityVariable()
'ALLOW ALL FONT TYPES WHEN CAPABILITY FEATURE DOES NOT EXIST
    If capability = "" Then
       IsFontTypeAllowed = True
       Exit Function
    End If
    
    If InStr(1, capability, fontCapability, vbBinaryCompare) > 0 Then
        IsFontTypeAllowed = False
    Else
        IsFontTypeAllowed = True
    End If
End Function



Private Function GetCapabilityVariable() As String
On Error GoTo errhnd
    GetCapabilityVariable = ActiveWorkspace.ConfigurationVariableValue("_USTN_CAPABILITY", True)
    Exit Function
errhnd:
'FEATURE DOES NOT EXIST ON SS3, RETURN EMPTY STRING WHEN DOES NOT EXIST
   GetCapabilityVariable = ""
End Function




'*************************************************************************************************************
'*************************************************************************************************************
Public Sub HandleNoActiveLevel()
   If IsNoActiveFont() Then
      Dim myLevel As Level
      For Each myLevel In ActiveDesignFile.Levels
         Set ActiveSettings.Level = myLevel
         Exit Sub
      Next
   End If
End Sub

Public Function IsNoActiveFont() As Boolean
On Error GoTo errhnd
   Dim myfont As Font
   Set myfont = ActiveSettings.TextStyle.Font
   IsNoActiveFont = False
   Exit Function

errhnd:
   IsNoActiveFont = True
End Function

Public Sub HandleNoActiveFont()
   If IsNoActiveFont() Then
      Dim myfont As Font
      For Each myfont In ActiveDesignFile.Fonts
         If myfont.Type = msdFontTypeMicroStation Then
            Set ActiveSettings.TextStyle.Font = myfont
            Exit Sub
         End If
      Next
   End If
End Sub

Public Function IsNoActiveLevel() As Boolean
On Error GoTo errhnd
   Dim myLevel As Level
   Set myLevel = ActiveSettings.Level
   IsNoActiveLevel = False
   Exit Function

errhnd:
   IsNoActiveLevel = True
End Function



'*************************************************************************************************************
'********************************************THE COLOR CHOOSER************************************************
Public Sub PutWasChosen(ByVal theState As Boolean)
   WasChosen = theState
End Sub



Public Sub PutTheColorString(ColorString As String)
   TheColorString = ColorString
End Sub



Public Function ChooseMyTableColor(TheColorChosen As String) As Boolean
'IF COLOR WAS CHOSEN THEN RETURNS TRUE AND THE STRING AS TheColorChosen
   FrmChooseColor.Show
   ChooseMyTableColor = WasChosen
   If WasChosen Then
      TheColorChosen = TheColorString
   End If
End Function

Attribute VB_Name = "AzAzIntLocateText"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit

Implements ILocateCommandEvents

Public hostForm As FrmAzAzInt

Private myLC As LocateCriteria

Private Sub ILocateCommandEvents_Accept(ByVal Element As Element, point As Point3d, ByVal view As view)

End Sub



Private Sub ILocateCommandEvents_Cleanup()
   hostForm.Show
   ClearCommandPromptArea
   CommandState.EnableAccuSnap
End Sub



Private Sub ILocateCommandEvents_Dynamics(point As Point3d, ByVal view As view, ByVal DrawMode As MsdDrawingMode)
   
End Sub



Private Sub ILocateCommandEvents_LocateFailed()
End Sub



Private Sub ILocateCommandEvents_LocateFilter(ByVal Element As Element, point As Point3d, Accepted As Boolean)
   Dim myEl As Element
   Set myEl = CommandState.GetLocatedElement(False)
   If myEl.IsTextElement Then
          hostForm.EnterText myEl.AsTextElement.text
   End If
   CommandState.StartDefaultCommand
   Accepted = False
End Sub



Private Sub ILocateCommandEvents_LocateReset()
   CommandState.StartDefaultCommand
End Sub



Private Sub ILocateCommandEvents_Start()
   Set myLC = CommandState.CreateLocateCriteria(False)
   myLC.ExcludeAllTypes
   myLC.IncludeType msdElementTypeText
   myLC.IncludeType msdElementTypeTextNode
   myLC.IncludeType msdElementTypeCellHeader
   CommandState.SetLocateCriteria myLC
   
   ShowCommand COMMAND_NAME_AZ_AZ_INT
   ShowPrompt "Pick Text Element/Reset"

   ActiveModelReference.UnselectAllElements

   CommandState.DisableAccuSnap
End Sub

Attribute VB_Name = "Baselines"
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.



'GENERAL NOTES:
'ALL THESE ROUTINES WERE WRITTEN BY JASON LOOK.  THEY ARE NOT
'WRITTEN IN THE STYLE COMMONLY USED BY PROFESSIONAL PROGRAMMERS.
'THEY ARE WRITTEN IN THE STYLE PREFERRED BY JASON.  JASON IS NOT
'A PROFESSIONAL PROGRAMMER!

'PROGRAM ASSUMES MASTER UNIT IS FOOT OR SURVEY FOOT, SOME KIND OF FOOT


Option Explicit

Private Const STATION_PAD                As Double = 0.005
Private Const DEFAULT_STATION_STYLE      As Integer = 0
Public Const DEFAULT_STATION_PRECISION   As Long = 2
Public Const LINEAR_PRECISION_BASELINE   As Long = 2

Public Const TICK_SIZE                   As Double = 0.5 'size of baseline ticks in characters

Public Sub GetBasePntFwdAzSpiral(station As Double, _
                                 theElement As LineElement, _
                                 ByRef BaselinePoint As Point3d, _
                                 ByRef fwdSAz As Double)
   Dim stationString As String
   Dim stationDouble As Double
   Dim spiralLengthString As String
   Dim spiralLength As Double
   Dim spiralAngleString As String
   Dim spiralAngleDegrees As Double
   Dim curvesLeft As Boolean
   Dim ingoing As Boolean
   Dim xSpiral As Double
   Dim ySpiral As Double
   Dim chordSA As Double
   Dim chordDis As Double
   If IsSpiralElement(theElement, _
                      stationString, _
                      stationDouble, _
                      spiralLengthString, _
                      spiralLength, _
                      spiralAngleString, _
                      spiralAngleDegrees, _
                      curvesLeft, _
                      ingoing, _
                      xSpiral, _
                      ySpiral, _
                      chordSA, _
                      chordDis) Then
'SOLVE SHORT X AND Y AND THETA AT STATION
   Dim xAtSta As Double
   Dim yAtSta As Double
   Dim thetaAtSta As Double
   StationToSpiralXYTheta station, stationDouble, spiralLength, spiralAngleDegrees, ingoing, xAtSta, yAtSta, thetaAtSta
   
'DETERMINE DEFLECTION ANGLE
      Dim deflAngleDegrees As Double
      deflAngleDegrees = Degrees(Atn(ySpiral / xSpiral))
      If ingoing Then
'SOLVE WHEN INGOING SPIRAL
         If curvesLeft Then
            Dim inTangentSA As Double
            inTangentSA = chordSA + deflAngleDegrees
            Dim outTangentSA As Double
            outTangentSA = inTangentSA + spiralAngleDegrees
            fwdSAz = inTangentSA - thetaAtSta
         Else
            inTangentSA = chordSA - deflAngleDegrees
            outTangentSA = inTangentSA + spiralAngleDegrees
            fwdSAz = inTangentSA + thetaAtSta
         End If
         Dim tanAzX As Double
         tanAzX = inTangentSA
         Dim startXPoint As Point3d
         startXPoint = theElement.AsLineElement.startPoint
         Dim leftSide As Boolean
         leftSide = curvesLeft
      Else
'SOLVE WHEN OUTGOING SPIRAL
         If curvesLeft Then
            outTangentSA = chordSA - deflAngleDegrees
            inTangentSA = outTangentSA - spiralAngleDegrees
            fwdSAz = outTangentSA + thetaAtSta
         Else
            outTangentSA = chordSA + deflAngleDegrees
            inTangentSA = outTangentSA + spiralAngleDegrees
            fwdSAz = outTangentSA - thetaAtSta
         End If
         tanAzX = outTangentSA + 180
         startXPoint = theElement.AsLineElement.endPoint
         leftSide = Not curvesLeft
      End If
      MakeSure360 tanAzX
      MakeSure360 fwdSAz
      BaselinePoint = SpiralXYToPoint(startXPoint, tanAzX, leftSide, xAtSta, yAtSta)
   End If
End Sub



Public Function IsSpiralElementLite(maybeSpiral As LineElement) As Boolean
   Dim stationString As String
   Dim stationDouble As Double
   Dim spiralLengthString As String
   Dim spiralLength As Double
   Dim spiralAngleString As String
   Dim spiralAngleDegrees As Double
   Dim curvesLeft As Boolean
   Dim ingoing As Boolean
   Dim xSpiral As Double
   Dim ySpiral As Double
   Dim chordSA As Double
   Dim chordDis As Double
   IsSpiralElementLite = IsSpiralElement(maybeSpiral, _
                         stationString, _
                         stationDouble, _
                         spiralLengthString, _
                         spiralLength, _
                         spiralAngleString, _
                         spiralAngleDegrees, _
                         curvesLeft, _
                         ingoing, _
                         xSpiral, _
                         ySpiral, _
                         chordSA, _
                         chordDis)
End Function



Public Function IsSpiralElement(maybeSpiral As LineElement, _
                                ByRef stationString As String, _
                                ByRef stationDouble As Double, _
                                ByRef spiralLengthString As String, _
                                ByRef spiralLength As Double, _
                                ByRef spiralAngleString As String, _
                                ByRef spiralAngleDegrees As Double, _
                                ByRef curvesLeft As Boolean, _
                                ByRef ingoing As Boolean, _
                                ByRef xSpiral As Double, _
                                ByRef ySpiral As Double, _
                                ByRef chordSA As Double, _
                                ByRef chordDis As Double) As Boolean
'RETURNS TRUE IF IT IS A SPIRAL ELEMENT
'RETURNS SPIRAL METRICS IF TRUE
'SET FLAG
   IsSpiralElement = False
'MAKE SURE THERE ARE AT LEAST 9 VERTICES
   If maybeSpiral.VerticesCount < 9 Then
      Exit Function
   End If
'MAKE SURE BEGIN ELEVATION AND END ELEVATION ARE THE SAME.  PROBABLY SHOULD CHECK ALL ELEVATIONS.
   If maybeSpiral.startPoint.z <> maybeSpiral.endPoint.z Then
      Exit Function
   End If

'GET THE BEGIN STATION FROM TAG
   If Not GetSurveyorToolsTagValue(maybeSpiral, TAG_NAME_BEGIN_STATION, stationString) Then
      Exit Function
   End If

'CHECK IF THE TAG VALUE IS A STATION OR NOT
   Dim origPrec As Long
   If Not IsStationString(stationString, stationDouble, origPrec, DEFAULT_STATION_STYLE) Then
      Exit Function
   End If

'GET THE LENGTH
   If Not GetSurveyorToolsTagValue(maybeSpiral, TAG_NAME_LENGTH, spiralLengthString) Then
      Exit Function
   End If
   spiralLength = CDbl(spiralLengthString)

'GET THE SPIRAL ANGLE
   If Not GetSurveyorToolsTagValue(maybeSpiral, TAG_NAME_SPIRAL_ANGLE, spiralAngleString) Then
      Exit Function
   End If
   If Not AngleStringToDegree(spiralAngleString, spiralAngleDegrees) Then
      Exit Function
   End If

'GET IF CURVES LEFT
   Dim curvesLeftString As String
   If Not GetSurveyorToolsTagValue(maybeSpiral, TAG_NAME_CURVES_LEFT, curvesLeftString) Then
      Exit Function
   End If
   If curvesLeftString = OPTION_TRUE Then
      curvesLeft = True
   Else
      curvesLeft = False
   End If

'GET IF INGOING SPIRAL
   Dim ingoingString As String
   If Not GetSurveyorToolsTagValue(maybeSpiral, TAG_NAME_INGOING, ingoingString) Then
      Exit Function
   End If
   If ingoingString = OPTION_TRUE Then
      ingoing = True
   Else
      ingoing = False
   End If

'CALCULATE THE CHORD LENGTH
   Dim theta As Double
   SpiralXYTheta spiralLength, spiralLength, spiralAngleDegrees, xSpiral, ySpiral, theta
   Dim calcedChord As Double
   calcedChord = InverseDistance(ySpiral, xSpiral)
'INVERSE START TO END
   Inverse maybeSpiral.startPoint, maybeSpiral.endPoint, chordSA, chordDis

'COMPARE CALCED CHORD TO INVERSED CHORD
   If Abs(calcedChord - chordDis) > 0.01 Then
      Exit Function
   End If

   IsSpiralElement = True
End Function


Public Sub calcShortLongTanget(spiralAngleDecimal As Double, spiralLength As Double, ByRef longTangent As Double, ByRef shortTangent As Double)
'CALCULATE SHORT TANGENT
   Dim spiralX As Double
   Dim spiralY As Double
   Dim thetaAtLen As Double
   SpiralXYTheta spiralLength, spiralLength, spiralAngleDecimal, spiralX, spiralY, thetaAtLen
   Dim spiralAngleRadians As Double
   spiralAngleRadians = Radians(spiralAngleDecimal)
   shortTangent = spiralY / Sin(spiralAngleRadians)

'CALCULATE LONG TANGENT
   longTangent = spiralX - (shortTangent * Cos(spiralAngleRadians))
End Sub



Public Function SpiralXYToPoint(TSPoint As Point3d, _
                                TangentAzSA As Double, _
                                leftSide As Boolean, _
                                xSpiral As Double, _
                                ySpiral As Double) As Point3d
'AZIMUTH ENTERED IN SOUTH AZIMUTH DECIMAL
   Dim pointAlongTangent As Point3d
   pointAlongTangent = CoordFwdSAz(TSPoint, TangentAzSA, xSpiral)
   If leftSide Then
      Dim offsetAzimuthSA As Double
      offsetAzimuthSA = TangentAzSA - 90#
   Else
      offsetAzimuthSA = TangentAzSA + 90#
   End If
   SpiralXYToPoint = CoordFwdSAz(pointAlongTangent, offsetAzimuthSA, ySpiral)
End Function



Public Sub StationToSpiralXYTheta(station As Double, _
                                  startStation As Double, _
                                  lengthSpiral As Double, _
                                  thetaS As Double, _
                                  ingoing As Boolean, _
                                  ByRef xSpiral As Double, _
                                  ByRef ySpiral As Double, _
                                  ByRef thetaAtSta As Double)
'ANGLES ENTERED AND RETURNED IN DECIMAL DEGREES
'DETERMINE LEGNTH ALONG SPIRAL
   Dim length As Double
   length = station - startStation
   If Not ingoing Then
      length = lengthSpiral - length
   End If

   SpiralXYTheta length, lengthSpiral, thetaS, xSpiral, ySpiral, thetaAtSta
End Sub



Public Sub SpiralXYTheta(length As Double, _
                         lengthSpiral As Double, _
                         thetaS As Double, _
                         ByRef xSpiral As Double, _
                         ByRef ySpiral As Double, _
                         ByRef thetaAtLen As Double)
'ANGLES ENTERED AND RETURNED IN DECIMAL DEGREES
   Dim thetaAtLenRad As Double
   thetaAtLenRad = ((length / lengthSpiral) ^ 2) * Radians(thetaS)
   thetaAtLen = Degrees(thetaAtLenRad)
   xSpiral = ((((1 - ((thetaAtLenRad ^ 2) / 10#) + ((thetaAtLenRad ^ 4) / 216#)) - ((thetaAtLenRad ^ 6) / 9360#)) + ((thetaAtLenRad ^ 8) / 685440#))) * length
   ySpiral = ((thetaAtLenRad / 3) - ((thetaAtLenRad ^ 3) / 42#) + ((thetaAtLenRad ^ 5) / 1320#) - ((thetaAtLenRad ^ 7) / 75600#) + ((thetaAtLenRad ^ 9) / 6894720#)) * length
End Sub



Public Function IsPointWithinSegment(thePoint As Point3d, theSegment As Element, ByRef beginStation As Double, ByRef station As Double, ByRef offset As Double) As Boolean
'RETURNS TRUE IF WITHIN THE SEGMENT RANGE, BEGIN STATION OF SEGMENT, STATION OF POINT, AND OFFSET (NEGATIVE IF LEFT OF BASELINE)
'INITIALIZE FLAG
   IsPointWithinSegment = False

'DETERMINE IF SEGMENT IS USABLE TYPE, CALL APPROPRIATE FUNCTION
  If theSegment.IsArcElement Then
     IsPointWithinSegment = ArcSegmentStationOffset(thePoint, theSegment, beginStation, station, offset)
  ElseIf theSegment.Type = msdElementTypeLineString Then
     IsPointWithinSegment = SpiralSegmentStationOffset(thePoint, theSegment, beginStation, station, offset)
  ElseIf theSegment.Type = msdElementTypeLine Then
     IsPointWithinSegment = LineSegmentStationOffset(thePoint, theSegment, beginStation, station, offset)
  Else
     Exit Function
  End If
End Function



Private Function SpiralSegmentStationOffset(thePoint As Point3d, _
                                            theSegment As LineElement, _
                                            ByRef beginStation As Double, _
                                            ByRef station As Double, _
                                            ByRef offset As Double) As Boolean
'RETURNS TRUE IF ABLE TO CALCULATE A STATION OFFSET
'INITIALIZE FLAG
   SpiralSegmentStationOffset = False

'GET SPIRAL METRICS
   Dim stationString As String
   Dim stationDouble As Double
   Dim spiralLengthString As String
   Dim spiralLength As Double
   Dim spiralAngleString As String
   Dim spiralAngleDegrees As Double
   Dim curvesLeft As Boolean
   Dim ingoing As Boolean
   Dim xSpiral As Double
   Dim ySpiral As Double
   Dim chordSA As Double
   Dim chordDis As Double
   If Not IsSpiralElement(theSegment, _
                          stationString, _
                          stationDouble, _
                          spiralLengthString, _
                          spiralLength, _
                          spiralAngleString, _
                          spiralAngleDegrees, _
                          curvesLeft, _
                          ingoing, _
                          xSpiral, _
                          ySpiral, _
                          chordSA, _
                          chordDis) Then
      Exit Function
   End If

'GET BEGIN SPIRAL POINT AND AZIMUTH
   Dim beginPoint As Point3d
   Dim beginSAz As Double
   GetBasePntFwdAzSpiral stationDouble, theSegment, beginPoint, beginSAz

'INVERSE AZIMUTH(DECIMAL) FROM THE BEGIN SPIRAL TO THE POINT
   Dim AzBegToThePoint As Double
   Dim DistBegToThePoint As Double
   Inverse beginPoint, thePoint, AzBegToThePoint, DistBegToThePoint

'CHECK IF BEFORE THE LINE
   Dim BegRelAngle As Double
   BegRelAngle = To360(beginSAz, AzBegToThePoint)
   If (BegRelAngle < 90# Or BegRelAngle > 270#) And (Round(DistBegToThePoint, 6) <> 0#) Then
      Exit Function
   End If

'GET END SPIRAL POINT AND AZIMUTH
   Dim endStation As Double
   endStation = stationDouble + spiralLength
   Dim endPoint As Point3d
   Dim endSAz As Double
   GetBasePntFwdAzSpiral endStation, theSegment, endPoint, endSAz

'INVERSE AZIMUTH(DECIMAL) FROM THE END SPIRAL TO THE POINT
   Dim AzEndToThePoint As Double
   Dim DistEndToThePoint As Double
   Inverse endPoint, thePoint, AzEndToThePoint, DistEndToThePoint

'CHECK IF IT IS AFTER THE SPIRAL
   Dim endRelAngle As Double
   endRelAngle = To360(endSAz, AzEndToThePoint)
   If (endRelAngle > 90# And endRelAngle < 270#) And (Round(DistEndToThePoint, 6) <> 0#) Then
      Exit Function
   End If

'DETERMINE MAX OFFSET
'MAKE SURE SPIRAL HAS SOME DISTANCE
   If spiralLength <= 0.03 Then
      Exit Function
   End If

   If ingoing Then
'IF INGOING START FROM END
      Dim adjPoint As Point3d
      Dim adjAz As Double
      GetBasePntFwdAzSpiral endStation - 0.01, theSegment, adjPoint, adjAz
      Dim intersction As Point3d
      If Not calcPI(adjPoint, endPoint, adjAz + 90, endSAz + 90, intersction) Then
         Exit Function
      End If
      Dim MaxOffset As Double
      MaxOffset = InverseHD(endPoint, intersction)
   Else
'IF OUTGOING START FROM BEGINING
      GetBasePntFwdAzSpiral stationDouble + 0.01, theSegment, adjPoint, adjAz
      If Not calcPI(adjPoint, beginPoint, adjAz + 90, beginSAz + 90, intersction) Then
         Exit Function
      End If
      MaxOffset = InverseHD(beginPoint, intersction)
   End If
   MaxOffset = MaxOffset - 0.01

'IF TOO FAR AWAY, EXIT
   Dim chkAng As Double
   chkAng = To360(chordSA, AzBegToThePoint)
   Dim os As Double
   os = -(Sin(Radians(chkAng)) * DistBegToThePoint)
   If Abs(os) > MaxOffset Then
      If curvesLeft And os < 0 Then
         Exit Function
      End If
      If (Not curvesLeft) And os > 0 Then
         Exit Function
      End If
   End If

'START GUESSING HERE
   Dim lowSta As Double
   lowSta = stationDouble
   Dim hiSta As Double
   hiSta = endStation
   Dim i As Long
   i = 0
   Dim guessStation As Double
   guessStation = (hiSta + lowSta) / 2#
'TAKE UP TO 30 GUESSES BEFORE QUITTING
      Do While i < 30
         i = i + 1
         Dim guessPoint As Point3d
         Dim guessAz As Double
         GetBasePntFwdAzSpiral guessStation, theSegment, guessPoint, guessAz
         Dim guessToPointAz As Double
         Dim guessToPointDis As Double
         Inverse guessPoint, thePoint, guessToPointAz, guessToPointDis
         chkAng = To360(guessAz, guessToPointAz)
         os = -(Sin(Radians(chkAng)) * guessToPointDis)

'CHECK OFFSET TO BE SURE IT'S NOT TOO FAR
         If Abs(os) > MaxOffset Then
            If curvesLeft And os < 0 Then
               Exit Function
            End If
            If (Not curvesLeft) And os > 0 Then
               Exit Function
            End If
         End If
         Dim miss As Double
         miss = -(Cos(Radians(chkAng)) * guessToPointDis)
'IF GUESS IS WITHIN 0.003 IN STATIONING THEN IT IS FOUND
         If Abs(miss) < 0.003 Then
            Exit Do
         End If
'ADJUST FOR IF GUESS IS HIGH OR LOW
         If miss < 0 Then
            hiSta = guessStation
            guessStation = (lowSta + guessStation) / 2#
         Else
            lowSta = guessStation
            guessStation = (hiSta + guessStation) / 2#
         End If
      Loop
'IF MADE MAX NUMBER OF GUESSES AND STILL NOT FOUND, THEN QUIT NOT SUCCESSFUL
      If miss >= 0.003 Then
         Exit Function
      End If

'RETURN VALUES
   beginStation = stationDouble
   station = guessStation
   offset = os

'WITHIN SPIRAL
   SpiralSegmentStationOffset = True
End Function


Private Function LineSegmentStationOffset(thePoint As Point3d, _
                                          theSegment As LineElement, _
                                          ByRef beginStation As Double, _
                                          ByRef station As Double, _
                                          ByRef offset As Double) As Boolean

'RETURNS TRUE IF ABLE TO CALCULATE A STATION OFFSET
'INITIALIZE FLAG
   LineSegmentStationOffset = False
   
'CREATE WORKING COPY
   Dim ThePT As Point3d
   ThePT = theSegment.startPoint
   Dim thePC As Point3d
   thePC = theSegment.endPoint

'DETERMINE IF IT'S WITHIN THE LINE SEGMENT RANGE
   Dim LengthAlongLine As Double
   If Not IsWithinLineRange(thePoint, thePC, ThePT, LengthAlongLine, offset) Then
      Exit Function
   End If
   
'GET BEGINNING STATION OF LINE
   If Not GetBeginStation(theSegment, beginStation) Then
      Exit Function
   End If

'CALCULATE STATION OF THE POINT
   station = beginStation + LengthAlongLine

'GOOD LINE
   LineSegmentStationOffset = True
End Function



Private Function ArcSegmentStationOffset(thePoint As Point3d, _
                                         theSegment As ArcElement, _
                                         ByRef beginStation As Double, _
                                         ByRef station As Double, _
                                         ByRef offset As Double) As Boolean
'RETURNS TRUE IF ABLE TO CALCULATE A STATION OFFSET
'INITIALIZE FLAG
   ArcSegmentStationOffset = False

'CALCULATE LENGTH AND OFFSET
   Dim ArcLength As Double
   If Not IsWithinArcRange(thePoint, theSegment, ArcLength, offset) Then
      Exit Function
   End If

'GET THE BASELINE BEGINNING STATION
   If Not GetBeginStation(theSegment, beginStation) Then
      Exit Function
   End If

'CALCULATE THE STATION
   station = (beginStation - STATION_PAD) + ArcLength

'SIGNAL IT'S OKAY
   ArcSegmentStationOffset = True
End Function



Public Function IsWithinArcRange(thePoint As Point3d, _
                                 theSegment As ArcElement, _
                                 ByRef lengthAlongArc As Double, _
                                 ByRef offset As Double) As Boolean
'RETURNS TRUE IF ABLE TO CALCULATE A STATION OFFSET
'INITIALIZE FLAG
   IsWithinArcRange = False

'CREATE WORKING COPY
   Dim thePC As Point3d
   thePC = theSegment.startPoint
   Dim theRP As Point3d
   theRP = theSegment.CenterPoint

'INVERSE AZIMUTH(DECIMAL) FROM THE RADIUS POINT TO THE PC
   Dim RadialAzPC As Double
   Dim distance As Double
   Inverse theRP, thePC, RadialAzPC, distance

'INVERSE AZIMUTH(DECIMAL) FROM THE RADIUS POINT TO THE POINT
   Dim RadialAzTHEPOINT As Double
   Inverse theRP, thePoint, RadialAzTHEPOINT, distance

'IF THE POINT IS THE SAME AS THE RADIUS POINT, THEN NO SOLUTION
   If distance = 0# Then
      Exit Function
   End If

'CALCULATE ARC IN DEGREES FOR 0.005' ARC LEGNTH
   Dim halfHundredthArc As Double
   halfHundredthArc = 360# * (STATION_PAD / ((Pi + Pi) * theSegment.PrimaryRadius))


'DETERMINE ROTATION
   Dim theSweepAngle As Double
   theSweepAngle = theSegment.SweepAngle
   If theSweepAngle < 0# Then
'RIGHT HAND CURVE
      Dim beginAzimuth As Double
      beginAzimuth = RadialAzPC - halfHundredthArc
      Plus360WhenNeg beginAzimuth
      Dim AngleToCompare As Double
      AngleToCompare = RadialAzTHEPOINT - beginAzimuth
      Plus360WhenNeg AngleToCompare
   Else
'LEFT HAND CURVE
      beginAzimuth = RadialAzPC + halfHundredthArc
      If beginAzimuth >= 360# Then
         beginAzimuth = beginAzimuth - 360#
      End If
      AngleToCompare = beginAzimuth - RadialAzTHEPOINT
      Plus360WhenNeg AngleToCompare
   End If

'CALCULATE THE ORIGINAL LENGTH
   Dim originalLegnth As Double
   originalLegnth = CDbl(FormatNumber(theSegment.length, DEFAULT_STATION_PRECISION))

'CALCULATE ARC FOR EXTENDED ARC
   Dim extendedArcInDegrees As Double
   extendedArcInDegrees = 360# * ((originalLegnth + (STATION_PAD + STATION_PAD)) / ((Pi + Pi) * theSegment.PrimaryRadius))

'COMPARE ANGLES, IF SWEEP ANGLE IS SMALLER, THEN THE POINT IS OUTSIDE THE RANGE OF THE ARC
   If extendedArcInDegrees < AngleToCompare Then
      Exit Function
   End If

'CALCULATE THE OFFSET
   offset = distance - theSegment.PrimaryRadius
   If theSegment.SweepAngle < 0# Then
'FOR RIGHT HAND CURVE
      offset = -offset
   End If

'CONVERT THE ARC ANGLE TO ARC LENGTH
   lengthAlongArc = Radians(AngleToCompare) * theSegment.PrimaryRadius

'SIGNAL IT'S OKAY
   IsWithinArcRange = True
End Function



Public Function IsWithinLineRange(thePoint As Point3d, _
                                  thePC As Point3d, _
                                  ThePT As Point3d, _
                                  ByRef LengthAlongLine As Double, _
                                  ByRef offset As Double) As Boolean
'RETURNS TRUE IF THE POINT IS WITHIN RANGE OF THE LINE
'LENGTH ALONG LINE FROM BEGINNING, OFFSET IS NEGATIVE WHEN TO THE LEFT
'INITIALIZE FLAG
   IsWithinLineRange = False

'INVERSE AZIMUTH(DECIMAL) FROM THE PT TO THE PC
   Dim lineAz As Double
   Dim distance As Double
   Inverse ThePT, thePC, lineAz, distance
   
'INVERSE AZIMUTH(DECIMAL) FROM THE PT TO THE POINT
   Dim AzPTToThePoint As Double
   Dim DistPTToThePoint As Double
   Inverse ThePT, thePoint, AzPTToThePoint, DistPTToThePoint

'CHECK IF BEFORE THE LINE
   Dim relativeAngle As Double
   relativeAngle = To360(lineAz, AzPTToThePoint)
   If (relativeAngle < 90# Or relativeAngle > 270#) And (Round(DistPTToThePoint, 6) <> 0#) Then
      Exit Function
   End If
  
'INVERSE AZIMUTH(DECIMAL) FROM THE PC TO THE POINT
   Dim AzPCToThePoint As Double
   Dim DistPCToThePoint As Double
   Inverse thePC, thePoint, AzPCToThePoint, DistPCToThePoint

'CHECK IF AFTER THE LINE SEGMENT
   Dim relativeAngle2 As Double
   relativeAngle2 = To360(lineAz, AzPCToThePoint)
   If (relativeAngle2 > 90# And relativeAngle2 < 270#) And (Round(DistPCToThePoint, 6) <> 0#) Then
      Exit Function
   End If

'CALCULATE THE LENGTH ALONG THE LINE AND THE OFFSET
   CalculateLengthOffset lineAz, distance, AzPTToThePoint, DistPTToThePoint, AzPCToThePoint, DistPCToThePoint, LengthAlongLine, offset

'THE POINT IS WITHIN RANGE OF THE LINE SEGMENT
   IsWithinLineRange = True
End Function



Private Function GetBeginStation(theSegment As Element, ByRef beginStation As Double) As Boolean
'RETURNS TRUE IF SUCCESSFUL
'INITIALIZE FLAG
   GetBeginStation = False

'GET THE BASELINE INFO
   Dim theValue As Variant
   If Not GetSurveyorToolsTagValue(theSegment, TAG_NAME_BEGIN_STATION, theValue) Then
      Exit Function
   End If
   Dim origPrec As Long
   If Not IsStationString(theValue, beginStation, origPrec, DEFAULT_STATION_STYLE) Then
      Exit Function
   End If

'SUCCESSFUL
   GetBeginStation = True
End Function



Private Sub Plus360WhenNeg(ByRef angleIndecimalDegrees As Double)
   If angleIndecimalDegrees < 0# Then
      angleIndecimalDegrees = angleIndecimalDegrees + 360#
   End If
End Sub



Private Sub CalculateLengthOffset(ByVal AzOfLine As Double, _
                                  ByVal LengthOfLine As Double, _
                                  ByVal azPTtoPoint As Double, _
                                  ByVal distPTtoPoint As Double, _
                                  ByVal azPCtoPoint As Double, _
                                  ByVal distPCtoPoint As Double, _
                                  ByRef LengthOnLine As Double, _
                                  ByRef offset As Double)
'USE CLOSER END TO CALCULATE FROM
   If distPTtoPoint >= distPCtoPoint Then
      Dim distance As Double
      LengthAndOffset AzOfLine, LengthOfLine, azPCtoPoint, distPCtoPoint, distance, offset
      LengthOnLine = LengthOfLine + distance
   Else
      LengthAndOffset AzOfLine, LengthOfLine, azPTtoPoint, distPTtoPoint, LengthOnLine, offset
   End If
End Sub



Private Sub LengthAndOffset(ByVal AzOfLine As Double, _
                            ByVal LengthOfLine As Double, _
                            ByVal azToPoint As Double, _
                            ByVal distToPoint As Double, _
                            ByRef LengthOnLine As Double, _
                            ByRef offset As Double)
   Dim relativeAngle As Double
   relativeAngle = To360(AzOfLine, azToPoint) - 180#
   Dim relativeAngleRadians As Double
   relativeAngleRadians = Radians(relativeAngle) 'CORRECTING FOR LEFT ROTATION
   LengthOnLine = Cos(relativeAngleRadians) * distToPoint
   offset = Sin(relativeAngleRadians) * distToPoint
End Sub



Public Function FirstEven100Station(ByVal MinStation As Double) As Double
'IF THE MINSTATION IS THE FIRST EVEN STATION, THEN IT RETURNS THE MINSTATION
   FirstEven100Station = FirstEvenStation(MinStation, 100)
End Function



Public Function FirstEven500Station(ByVal MinStation As Double) As Double
'RETURN THE FIRST EVEN 500 STATION
'IF THE MINSTATION IS THE FIRST EVEN 500 STATION, THEN IT RETURNS THE MINSTATION
   FirstEven500Station = FirstEvenStation(MinStation, 500)
End Function



Public Function FirstEvenStation(ByVal MinStation As Double, ByVal Incr As Double) As Double
'IF THE MINSTATION IS THE FIRST EVEN STATION, THEN IT RETURNS THE MINSTATION
'ROUND IT SO SIGN DOESN'T CHANGE
   MinStation = Round(MinStation, DEFAULT_STATION_PRECISION)

'GET ABSOLUTE VALUE SO NEGATIVE STATIONS ARE NOT A PROBLEM
   Dim MinStationAbs As Double
   MinStationAbs = Abs(MinStation)

'GET STATION PART
   Dim StationPartABS As Double
   StationPartABS = Int((MinStationAbs / Incr))
   
'CONVERT IT TO STATIONFEET
   Dim StationFeet As Double
   StationFeet = Round(StationPartABS * Incr, DEFAULT_STATION_PRECISION)

'CORRECT ITS SIGN
   If MinStation < 0 Then
      StationFeet = -StationFeet
   End If

'IF STATIONFEET IS LESS THAN MINSTATION, MOVE IT TO THE NEXT STATION
   If MinStation > StationFeet Then
      StationFeet = StationFeet + Incr
   End If

'RETURN VALUE
   FirstEvenStation = Round(StationFeet, DEFAULT_STATION_PRECISION)
End Function



Public Function LineIsValidBaselineSegment(ByVal theLine As LineElement) As Boolean
'RETURNS TRUE IF IT IS VALID
'INITIALIZE FLAG
   LineIsValidBaselineSegment = False

'CHECK FOR ITS BASELINE BEGIN STATION TAG
   Dim theValue As Variant
   If Not GetSurveyorToolsTagValue(theLine, TAG_NAME_BEGIN_STATION, theValue) Then
      Exit Function
   End If

'CHECK IF THE TAG VALUE IS A STATION OR NOT
   Dim stationString As String
   stationString = theValue
   Dim stationDouble As Double
   Dim origPrec As Long
   If Not IsStationString(stationString, stationDouble, origPrec, DEFAULT_STATION_STYLE) Then
      Exit Function
   End If

'CHECK IF THE LENGTH HAS CHANGED NOTICEABLY
   If Not GetSurveyorToolsTagValue(theLine, TAG_NAME_LENGTH, theValue) Then
      Exit Function
   End If
   Dim OriginalLength As Double
   OriginalLength = CDbl(theValue)
   If OriginalLength <> CDbl(FormatNumber(theLine.length, DEFAULT_STATION_PRECISION)) Then
      Exit Function
   End If

'CHECK IF LIES IN THE XY PLANE
   If theLine.startPoint.z <> theLine.endPoint.z Then
      Exit Function
   End If

'SUCCESS, RETURN TRUE
   LineIsValidBaselineSegment = True
End Function



Public Function ArcIsValidBaselineSegment(ByVal theArc As ArcElement) As Boolean
'RETURNS TRUE IF IT IS VALID
'INITIALIZE FLAG
   ArcIsValidBaselineSegment = False

'CHECK FOR ITS BASELINE BEGIN STATION TAG
   Dim theValue As Variant
   If Not GetSurveyorToolsTagValue(theArc, TAG_NAME_BEGIN_STATION, theValue) Then
      Exit Function
   End If

'CHECK IF THE TAG VALUE IS A STATION OR NOT
   Dim stationString As String
   stationString = theValue
   Dim stationDouble As Double
   Dim origPrec As Long
   If Not IsStationString(stationString, stationDouble, origPrec, DEFAULT_STATION_STYLE) Then
      Exit Function
   End If

'CHECK IF THE LENGTH HAS CHANGED NOTICEABLY
   If Not GetSurveyorToolsTagValue(theArc, TAG_NAME_LENGTH, theValue) Then
      Exit Function
   End If
   Dim OriginalLength As Double
   OriginalLength = CDbl(theValue)
   If OriginalLength <> CDbl(FormatNumber(theArc.length, DEFAULT_STATION_PRECISION)) Then
      Exit Function
   End If
   
'CHECK IF LIES IN THE XY PLANE
   If theArc.startPoint.z <> theArc.endPoint.z Then
      Exit Function
   End If
   
   If theArc.startPoint.z <> theArc.CenterPoint.z Then
      Exit Function
   End If
   
   Dim rotation As Double
   If Not Matrix3dIsXYRotation(theArc.rotation, rotation) Then
      Exit Function
   End If

'SUCCESS, RETURN TRUE
   ArcIsValidBaselineSegment = True
End Function



Public Sub AddBaselineAutoDeleteTags(ByVal theElement As Element, ByVal station As Double, ByVal HostIDString As String)
'TAG ELEMENT WITH ITS ID STRING SO WE KNOW THIS PROGRAM CREATED IT, AND IT'S NOT JUST A COPY
'TAG THE ELEMENT WITH THE STATION IT'S FOR SO WE KNOW IF WE WANT TO ERASE IT OR NOT
'TAG THE ELEMENT WITH THE BASELINE ELEMENT'S ID SO WE KNOW IT RELATES ONLY TO THAT ELEMENT
   Dim ID As DLong
   Dim IDstring As String
   If Not GetTheElementID(theElement, ID, IDstring) Then
   'SOMETHING WRONG, EXIT
      Exit Sub
   End If
   TagMyElement theElement, TAG_NAME_MY_ID, IDstring
   TagMyElement theElement, TAG_NAME_STATION, StationToString(station, DEFAULT_STATION_PRECISION, DEFAULT_STATION_STYLE)
   TagMyElement theElement, TAG_NAME_HOST_ID, HostIDString
End Sub



Public Function IsValidBaselineSegment(ByVal theElement As Element) As Boolean
'RETURNS TRUE IF IT IS VALID
'INITIALIZE FLAG
   IsValidBaselineSegment = False
   If theElement.IsArcElement Then
      IsValidBaselineSegment = ArcIsValidBaselineSegment(theElement)
   ElseIf theElement.IsLineElement Then
      If IsSpiralElementLite(theElement) Then
         IsValidBaselineSegment = True
      ElseIf LineIsValidBaselineSegment(theElement) Then
         IsValidBaselineSegment = True
      End If
   End If
End Function



Public Sub GetBasePntFwdAzArc(ByVal station As Double, _
                              ByVal theElement As ArcElement, _
                              ByVal ElementBeginStation As Double, _
                              ByRef BaselinePoint As Point3d, _
                              ByRef FwdAz As Double)
'RETURNS POINT ON THE BASELINE AND THE FORWARD AZIMUTH IN DECIMAL DEGREES
'GET THE AZIMUTH FROM CC TO PC AND THE RADIUS
   Dim theRadius As Double
   Dim PCAz As Double
   Inverse theElement.CenterPoint, theElement.startPoint, PCAz, theRadius

'CALCULATE THE DISTANCE ALONG THE LINE TO THE STATION
   Dim distanceToStation As Double
   distanceToStation = station - ElementBeginStation

'CONVERT ARC TO RADIANS
   If theRadius = 0 Then
      Dim ArcRadians As Double
      ArcRadians = 0
   Else
      ArcRadians = distanceToStation / theRadius
   End If

'CONVERT ARC TO DEGREES
   Dim ArcDegrees As Double
   ArcDegrees = Degrees(ArcRadians)

'ADD THE ARC IN DEGREES TO THE PC AZIMUTH
   If theElement.SweepAngle >= 0 Then 'LEFT HAND
      Dim AzimuthToStation As Double
      AzimuthToStation = PCAz - ArcDegrees
   Else
      AzimuthToStation = PCAz + ArcDegrees
   End If

'CALCULATE POINT ON THE BASELINE
   BaselinePoint = CoordFwdSAz(theElement.CenterPoint, AzimuthToStation, theRadius)

'CALCULATE THE AZIMUTH FORWARD
   Dim FwdAzImproper As Double
   If theElement.SweepAngle >= 0 Then
      FwdAzImproper = AzimuthToStation - 90 'LEFT HAND CURVE
   Else
      FwdAzImproper = AzimuthToStation + 90 'RIGHT HAND CURVE
   End If
   FwdAz = To360(180, FwdAzImproper)
End Sub



Public Sub GetBasePntFwdAzLine(ByVal station As Double, _
                               ByVal theElement As LineElement, _
                               ByVal ElementBeginStation As Double, _
                               ByRef BaselinePoint As Point3d, _
                               ByRef FwdAz As Double)
'RETURNS POINT ON THE BASELINE AND THE FORWARD AZIMUTH IN DECIMAL DEGREES
'GET THE AZIMUTH OF THE LINE
   Dim theDistance As Double
   Inverse theElement.startPoint, theElement.endPoint, FwdAz, theDistance

'CALCULATE THE DISTANCE ALONG THE LINE TO THE STATION
   Dim distanceToStation As Double
   distanceToStation = station - ElementBeginStation

'CALCULATE POINT ON THE BASELINE
   BaselinePoint = CoordFwdSAz(theElement.startPoint, FwdAz, distanceToStation)
End Sub

Attribute VB_Name = "CONSTANTS"
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.



'THIS MODULE IS JUST GENERIC VBA, IT DOES NOT CONTAIN ANY API
'SPECIFIC CODE.

Option Explicit


'NAME OF THE APPLICATION
Public Const APP_NAME                       As String = "My Tools"
Public Const APP_PROGRAM_NAME               As String = "Surveyor Tools Neo"
Public Const APP_VERSION                    As String = "R8"
Public Const APP_UPDATE                     As String = "u2"


'FILE EXTENSIONS
Public Const FILE_EXTENSION_COMPASS_RULE    As String = ".cra"
Public Const FILE_EXTENSION_COORDINATE      As String = ".asc"
Public Const FILE_EXTENSION_REPORT          As String = ".txt"


'SECTIONS/COMMAND NAMES
Public Const SECTION_ARC_ARC_INT            As String = "SECTION_ARC_ARC_INT"
Public Const COMMAND_NAME_ARC_ARC_INT       As String = "Arc/Arc Intersect"

Public Const SECTION_ARC_LINE_INT           As String = "SECTION_ARC_LINE_INT"
Public Const COMMAND_NAME_ARC_LINE_INT      As String = "Arc/Line Intersect"

Public Const SECTION_AZ_AZ_INT              As String = "SECTION_AZ_AZ_INT"
Public Const COMMAND_NAME_AZ_AZ_INT         As String = "Az/Az Intersect"

Public Const SECTION_CHOOSE_COLOR           As String = "SECTION_CHOOSE_COLOR"
Public Const COMMAND_NAME_CHOOSE_COLOR      As String = "Color Picker"

Public Const SECTION_COMPASS_RULE_2D        As String = "SECTION_COMPASS_RULE_2D"
Public Const COMMAND_NAME_COMPASS_RULE_2D   As String = "Compass Rule 2D"

Public Const SECTION_COMPASS_RULE_2D_ENTER_TRAV       As String = "SECTION_COMPASS_RULE_2D_ENTER_TRAV"
Public Const COMMAND_NAME_COMPASS_RULE_2D_ENTER_TRAV  As String = "Enter Traverse Point"

Public Const SECTION_COMPASS_RULE_2D_ENTER_SIDE       As String = "SECTION_COMPASS_RULE_2D_ENTER_SIDE"
Public Const COMMAND_NAME_COMPASS_RULE_2D_ENTER_SIDE  As String = "Enter Side Shot"

Public Const SECTION_CURVE_SOLVER           As String = "SECTION_CURVE_SOLVER"
Public Const COMMAND_NAME_CURVE_SOLVER      As String = "Curve Solver"

Public Const SECTION_DROP_DIAGRAM           As String = "SECTION_DROP_DIAGRAM"
Public Const COMMAND_NAME_DROP_DIAGRAM      As String = "Drop Diagram"

Public Const SECTION_DUP_FINDER             As String = "SECTION_DUP_FINDER"
Public Const COMMAND_NAME_DUP_FINDER        As String = "Dup Finder"

Public Const SECTION_INV_SELECTED           As String = "SECTION_INV_SELECTED"
Public Const COMMAND_NAME_INV_SELECTED      As String = "Inverse Selected"

Public Const SECTION_LABEL_COORD            As String = "SECTION_LABEL_COORD"
Public Const COMMAND_NAME_LABELCOORD        As String = "Label Coordinate"

Public Const SECTION_LABEL_CURVE            As String = "SECTION_LABEL_CURVE"
Public Const COMMAND_NAME_LABEL_CURVE       As String = "Label Curve"

Public Const SECTION_LABEL_LINE             As String = "SECTION_LABEL_LINE"
Public Const COMMAND_NAME_LABEL_LINE        As String = "Label Line"

Public Const SECTION_LAUNCHER               As String = "SECTION_LAUNCHER"
Public Const COMMAND_NAME_LAUNCHER          As String = "Launcher"

Public Const SECTION_LOT_CLOSURE            As String = "SECTION_LOT_CLOSURE"
Public Const COMMAND_NAME_LOT_CLOSURE       As String = "Plot Lot"

Public Const SECTION_LOT_CLOSURE_EDIT       As String = "SECTION_LOT_CLOSURE_EDIT"

Public Const SECTION_MEASURE_DIR            As String = "SECTION_MEASURE_DIR"
Public Const COMMAND_NAME_MESAURE_DIR       As String = "Measure Direction"

Public Const SECTION_SAMPLE                 As String = "SECTION_SAMPLE"
Public Const COMMAND_NAME_SAMPLE            As String = "Sample User Interface"

Public Const SECTION_SETTINGS               As String = "SECTION_SETTINGS"
Public Const COMMAND_NAME_SETTINGS          As String = "Settings"

Public Const SECTION_SIDE_SHOT_BY_COORD     As String = "SECTION_SIDE_SHOT_BY_COORD"
Public Const COMMAND_NAME_SIDE_BY_COORD     As String = "Insert Side Shot by Coordinates"

Public Const SECTION_STATION_INVERSE        As String = "SECTION_STATION_INVERSE"
Public Const COMMAND_NAME_STATION_INVERSE   As String = "Label Station"

Public Const SECTION_STATION_PLOT_POINT     As String = "SECTION_STATION_PLOT_POINT"
Public Const COMMAND_NAME_STATION_PLOT      As String = "Plot by Station"

Public Const SECTION_STATION_TEXT           As String = "SECTION_STATION_TEXT"
Public Const COMMAND_NAME_STATION_TEXT      As String = "Station Text"

Public Const SECTION_TRAVERSE               As String = "SECTION_TRAVERSE"
Public Const COMMAND_NAME_TRVERSE           As String = "Draw Traverse"




'KEYS
Public Const KEY_ALIGNED                    As String = "KEY_ALIGNED"
Public Const KEY_AREA_COLOR                 As String = "KEY_AREA_COLOR"
Public Const KEY_AREA_FONT                  As String = "KEY_AREA_FONT"
Public Const KEY_AREA_FONT_SCALE            As String = "KEY_AREA_FONT_SCALE"
Public Const KEY_AREA_LEVEL                 As String = "KEY_AREA_LEVEL"
Public Const KEY_AREA_STYLE                 As String = "KEY_AREA_STYLE"
Public Const KEY_AREA_WEIGHT                As String = "KEY_AREA_WEIGHT"
Public Const KEY_BACK_SIGHT_ANGLE           As String = "KEY_BACK_SIGHT_ANGLE"
Public Const KEY_BASELINE_LEVEL             As String = "KEY_BASELINE_LEVEL"
Public Const KEY_BASELINE_COLOR             As String = "KEY_BASELINE_COLOR"
Public Const KEY_BASELINE_STYLE             As String = "KEY_BASELINE_STYLE"
Public Const KEY_BASELINE_WEIGHT            As String = "KEY_BASELINE_WEIGHT"
Public Const KEY_BIG                        As String = "KEY_BIG"
Public Const KEY_BOUNDARY_COLOR             As String = "KEY_BOUNDARY_COLOR"
Public Const KEY_BOUNDARY_LEVEL             As String = "KEY_BOUNDARY_LEVEL"
Public Const KEY_BOUNDARY_STYLE             As String = "KEY_BOUNDARY_STYLE"
Public Const KEY_BOUNDARY_WEIGHT            As String = "KEY_BOUNDARY_WEIGHT"
Public Const KEY_CHORD                      As String = "KEY_CHORD"
Public Const KEY_CHORD_AZ                   As String = "KEY_CHORD_AZ"
Public Const KEY_CHORD_COLOR                As String = "KEY_CHORD_COLOR"
Public Const KEY_CHORD_LEVEL                As String = "KEY_CHORD_LEVEL"
Public Const KEY_CHORD_ROT_LEFT             As String = "KEY_CHORD_ROT_LEFT"
Public Const KEY_CHORD_STYLE                As String = "KEY_CHORD_STYLE"
Public Const KEY_CHORD_TAN_IN               As String = "KEY_CHORD_TAN_IN"
Public Const KEY_CHORD_TAN_OUT              As String = "KEY_CHORD_TAN_OUT"
Public Const KEY_CHORD_WEIGHT               As String = "KEY_CHORD_WEIGHT"
Public Const KEY_COURSE_TYPE                As String = "KEY_COURSE_TYPE"
Public Const KEY_CURVE_DATA_LEVEL           As String = "KEY_CURVE_DATA_LEVEL"
Public Const KEY_CURVE_DATA_COLOR           As String = "KEY_CURVE_DATA_COLOR"
Public Const KEY_CURVE_DATA_STYLE           As String = "KEY_CURVE_DATA_STYLE"
Public Const KEY_CURVE_DATA_WEIGHT          As String = "KEY_CURVE_DATA_WEIGHT"
Public Const KEY_CURVE_DATA_FONT            As String = "KEY_CURVE_DATA_FONT"
Public Const KEY_CURVE_RADIUS               As String = "KEY_CURVE_RADIUS"
Public Const KEY_CC2PC                      As String = "KEY_CC2PC"
Public Const KEY_CC2PT                      As String = "KEY_CC2PT"
Public Const KEY_CELL_DESC_OFFSET_LR        As String = "KEY_CELL_DESC_OFFSET_LR"
Public Const KEY_CELL_DESC_OFFSET_UD        As String = "KEY_CELL_DESC_OFFSET_UD"
Public Const KEY_CELL_NAME_OFFSET_LR        As String = "KEY_CELL_NAME_OFFSET_LR"
Public Const KEY_CELL_NAME_OFFSET_UD        As String = "KEY_CELL_NAME_OFFSET_UD"
Public Const KEY_CELL_TEXT_FONT_SIZE        As String = "KEY_CELL_TEXT_FONT_SIZE"
Public Const KEY_CHECKBOX                   As String = "KEY_CHECKBOX"
Public Const KEY_CHECKBOX1                  As String = "KEY_CHECKBOX1"
Public Const KEY_CHK_MOVEUP                 As String = "KEY_CHK_MOVEUP"
Public Const KEY_COLOR                      As String = "KEY_COLOR"
Public Const KEY_COLOR2                     As String = "KEY_COLOR2"
Public Const KEY_CURVE_DATA                 As String = "KEY_CURVE_DATA"
Public Const KEY_CURVE_DEFINITION           As String = "KEY_CURVE_DEFINITION"
Public Const KEY_CURVE_IN_TYPE              As String = "KEY_CURVE_IN_TYPE"
Public Const KEY_CURVE_OUT_TYPE             As String = "KEY_CURVE_OUT_TYPE"
Public Const KEY_DELTA                      As String = "KEY_DELTA"
Public Const KEY_DESCRIPTION                As String = "KEY_DESCRIPTION"
Public Const KEY_DESCRIPTION2               As String = "KEY_DESCRIPTION2"
Public Const KEY_DESCRIPTION3               As String = "KEY_DESCRIPTION3"
Public Const KEY_DESCRIPTION4               As String = "KEY_DESCRIPTION4"
Public Const KEY_DESCRIPTION_COLOR          As String = "KEY_DESCRIPTION_COLOR"
Public Const KEY_DESCRIPTION_FONT           As String = "KEY_DESCRIPTION_FONT"
Public Const KEY_DESCRIPTION_FONT_SCALE     As String = "KEY_DESCRIPTION_FONT_SCALE"
Public Const KEY_DESCRIPTION_LEVEL          As String = "KEY_DESCRIPTION_LEVEL"
Public Const KEY_DESCRIPTION_STYLE          As String = "KEY_DESCRIPTION_STYLE"
Public Const KEY_DESCRIPTION_WEIGHT         As String = "KEY_DESCRIPTION_WEIGHT"
Public Const KEY_DIAGRAM_EAST               As String = "KEY_DIAGRAM_EAST"
Public Const KEY_DIAGRAM_FIN_COLOR          As String = "KEY_DIAGRAM_FIN_COLOR"
Public Const KEY_DIAGRAM_FONT               As String = "KEY_DIAGRAM_FONT"
Public Const KEY_DIAGRAM_LEVEL              As String = "KEY_DIAGRAM_LEVEL"
Public Const KEY_DIAGRAM_NORTH              As String = "KEY_DIAGRAM_NORTH"
Public Const KEY_DIAGRAM_OPTION_DESCRIPTION As String = "KEY_DIAGRAM_OPTION_DESCRIPTION"
Public Const KEY_DIAGRAM_OPTION_LEADER      As String = "KEY_DIAGRAM_OPTION_LEADER"
Public Const KEY_DIAGRAM_OPTION_POINT_NAME  As String = "KEY_DIAGRAM_OPTION_POINT_NAME"
Public Const KEY_DIAGRAM_PRE_COLOR          As String = "KEY_DIAGRAM_PRE_COLOR"
Public Const KEY_DIAGRAM_STYLE              As String = "KEY_DIAGRAM_STYLE"
Public Const KEY_DIAGRAM_WEIGHT             As String = "KEY_DIAGRAM_WEIGHT"
Public Const KEY_DIRECTION                  As String = "KEY_DIRECTION"
Public Const KEY_DIRECTION2                 As String = "KEY_DIRECTION2"
Public Const KEY_DIRECTION_TYPE             As String = "KEY_DIRECTION_TYPE"
Public Const KEY_DISTANCE                   As String = "KEY_DISTANCE"
Public Const KEY_DRAW_FROM                  As String = "KEY_DRAW_FROM"
Public Const KEY_DRAW_PC_SYMBOL             As String = "KEY_DRAW_PC_SYMBOL"
Public Const KEY_DRAW_PT_SYMBOL             As String = "KEY_DRAW_PT_SYMBOL"
Public Const KEY_DRAW_RADIALS               As String = "KEY_DRAW_RADIALS"
Public Const KEY_DRAW_RAD_ON_PC             As String = "KEY_DRAW_RAD_ON_PC"
Public Const KEY_DRAW_RAD_ON_PT             As String = "KEY_DRAW_RAD_ON_PT"
Public Const KEY_DRAW_SYMBOL_PC             As String = "KEY_DRAW_SYMBOL_PC"
Public Const KEY_DRAW_SYMBOL_PT             As String = "KEY_DRAW_SYMBOL_PT"
Public Const KEY_DRAW_TANGENTS              As String = "KEY_DRAW_TANGENTS"
Public Const KEY_EASTING                    As String = "KEY_EASTING"
Public Const KEY_END_PREFIX                 As String = "KEY_END_PREFIX"
Public Const KEY_END_PREFIX_OPTION          As String = "KEY_END_PREFIX_OPTION"
Public Const KEY_ERASE_OLD                  As String = "KEY_ERASE_OLD"
Public Const KEY_ELEVATION                  As String = "KEY_ELEVATION"
Public Const KEY_INTERVAL                   As String = "KEY_INTERVAL"
Public Const KEY_FILENAME                   As String = "KEY_FILENAME"
Public Const KEY_FILENAME_COORDINATE        As String = "KEY_FILENAME_COORDINATE"
Public Const KEY_FONT                       As String = "KEY_FONT"
Public Const KEY_FONT_SCALE                 As String = "KEY_FONT_SCALE"
Public Const KEY_FONT_SIZE_INCH             As String = "KEY_FONT_SIZE_INCH"
Public Const KEY_FORE_SIGHT_ANGLE           As String = "KEY_FORE_SIGHT_ANGLE"
Public Const KEY_FS_CHK_DESC1               As String = "KEY_FS_CHK_DESC1"
Public Const KEY_FS_CHK_DESC2               As String = "KEY_FS_CHK_DESC2"
Public Const KEY_FS_ELEVATION               As String = "KEY_FS_ELEVATION"
Public Const KEY_FS_INCLUDEELEV             As String = "KEY_FS_INCLUDEELEV"
Public Const KEY_FS_LABELCOORD              As String = "KEY_FS_LABELCOORD"
Public Const KEY_FS_LABELLINE               As String = "KEY_FS_LABELLINE"
Public Const KEY_FS_NAME                    As String = "KEY_FS_NAME"
Public Const KEY_FS_SYM_OPTION              As String = "KEY_FS_SYM_OPTION"
Public Const KEY_GRND_EAST                  As String = "KEY_GRND_EAST"
Public Const KEY_GRND_ELEVATION             As String = "KEY_GRND_ELEVATION"
Public Const KEY_GRND_NORTH                 As String = "KEY_GRND_NORTH"
Public Const KEY_HEADING                    As String = "KEY_HEADING"
Public Const KEY_HORIZONTAL_DISTANCE        As String = "KEY_HORIZONTAL_DISTANCE"
Public Const KEY_JUSTIFICATION              As String = "KEY_JUSTIFICATION"
Public Const KEY_LABEL_LINE                 As String = "KEY_LABEL_LINE"
Public Const KEY_INCLUDE_PT_TO_PC           As String = "KEY_INCLUDE_PT_TO_PC"
Public Const KEY_INCLUDE_SIDES              As String = "KEY_INCLUDE_SIDES"
Public Const KEY_LABEL_END                  As String = "KEY_LABEL_END"
Public Const KEY_LABEL_PC                   As String = "KEY_LABEL_PC"
Public Const KEY_LABEL_PC_LINE              As String = "KEY_LABEL_PC_LINE"
Public Const KEY_LABEL_PC_LINE_SIDE         As String = "KEY_LABEL_PC_LINE_SIDE"
Public Const KEY_LABEL_PC_LN_PREFIX_OTHER   As String = "KEY_LABEL_PC_LN_PREFIX_OTHER"
Public Const KEY_LABEL_PC_LN_PREFIX_OTH_TXT As String = "KEY_LABEL_PC_LN_PREFIX_OTH_TXT"
Public Const KEY_LABEL_PC_OTHER             As String = "KEY_LABEL_PC_OTHER"
Public Const KEY_LABEL_PC_OTHER_TEXT        As String = "KEY_LABEL_PC_OTHER_TEXT"
Public Const KEY_LABEL_PT                   As String = "KEY_LABEL_PT"
Public Const KEY_LABEL_PT_LINE              As String = "KEY_LABEL_PT_LINE"
Public Const KEY_LABEL_PT_LN_PREFIX_OTHER   As String = "KEY_LABEL_PT_LN_PREFIX_OTHER"
Public Const KEY_LABEL_PT_LN_PREFIX_OTH_TXT As String = "KEY_LABEL_PT_LN_PREFIX_OTH_TXT"
Public Const KEY_LABEL_PT_LINE_SIDE         As String = "KEY_LABEL_PT_LINE_SIDE"
Public Const KEY_LABEL_PT_OTHER             As String = "KEY_LABEL_PT_OTHER"
Public Const KEY_LABEL_PT_OTHER_TEXT        As String = "KEY_LABEL_PT_OTHER_TEXT"
Public Const KEY_LABEL_START                As String = "KEY_LABEL_START"
Public Const KEY_LABEL_STYLE                As String = "KEY_LABEL_STYLE"
Public Const KEY_LEAVE_OFF                  As String = "KEY_LEAVE_OFF"
Public Const KEY_LENGTH_BY                  As String = "KEY_LENGTH_BY"
Public Const KEY_LEVEL                      As String = "KEY_LEVEL"
Public Const KEY_LEVEL2                     As String = "KEY_LEVEL2"
Public Const KEY_LINE_AZIMUTH               As String = "KEY_LINE_AZIMUTH"
Public Const KEY_LINE_COLOR                 As String = "KEY_LINE_COLOR"
Public Const KEY_LINE_DIRECTION             As String = "KEY_LINE_DIRECTION"
Public Const KEY_LINE_DISTANCE              As String = "KEY_LINE_DISTANCE"
Public Const KEY_LINE_LEVEL                 As String = "KEY_LINE_LEVEL"
Public Const KEY_LINE_STYLE                 As String = "KEY_LINE_STYLE"
Public Const KEY_LINE_WEIGHT                As String = "KEY_LINE_WEIGHT"
Public Const KEY_MINI_CELL_COLOR            As String = "KEY_MINI_CELL_COLOR"
Public Const KEY_MINI_CELL_FONT             As String = "KEY_MINI_CELL_FONT"
Public Const KEY_MINI_CELL_LEVEL            As String = "KEY_MINI_CELL_LEVEL"
Public Const KEY_MINI_CELL_STYLE            As String = "KEY_MINI_CELL_STYLE"
Public Const KEY_MINI_CELL_WEIGHT           As String = "KEY_MINI_CELL_WEIGHT"
Public Const KEY_NORTHING                   As String = "KEY_NORTHING"
Public Const KEY_NORTH_MODE                 As String = "KEY_NORTH_MODE"
Public Const KEY_OCC_CHK_DESC1              As String = "KEY_OCC_CHK_DESC1"
Public Const KEY_OCC_CHK_DESC2              As String = "KEY_OCC_CHK_DESC2"
Public Const KEY_OCC_EASTING                As String = "KEY_OCC_EASTING"
Public Const KEY_OCC_ELEVATION              As String = "KEY_OCC_ELEVATION"
Public Const KEY_OCC_NORTHING               As String = "KEY_OCC_NORTHING"
Public Const KEY_OFFSET                     As String = "KEY_OFFSET"
Public Const KEY_OFFSET_LONGITUDINAL        As String = "KEY_OFFSET_LONGITUDINAL"
Public Const KEY_OPTION_ALIGN               As String = "KEY_OPTION_ALIGN"
Public Const KEY_OPTION_ALL_COURSES         As String = "KEY_OPTION_ALL_COURSES"
Public Const KEY_OPTION_BK_AZ               As String = "KEY_OPTION_BK_AZ"
Public Const KEY_OPTION_CELL_USE_CELL_CHK   As String = "KEY_OPTION_CELL_USE_CELL_CHK"
Public Const KEY_OPTION_CLEAR_TEXT          As String = "KEY_OPTION_CLEAR_TEXT"
Public Const KEY_OPTION_COMPLEX_CHAIN       As String = "KEY_OPTION_COMPLEX_CHAIN"
Public Const KEY_OPTION_CREATE_CELL         As String = "KEY_OPTION_CREATE_CELL"
Public Const KEY_OPTION_DESC2               As String = "KEY_OPTION_DESC2"
Public Const KEY_OPTION_DGN_AREA            As String = "KEY_OPTION_DGN_AREA"
Public Const KEY_OPTION_DGN_AREA_TYPE       As String = "KEY_OPTION_DGN_AREA_TYPE"
Public Const KEY_OPTION_DGN_CHORD           As String = "KEY_OPTION_DGN_CHORD"
Public Const KEY_OPTION_DGN_DESCRIPTION     As String = "KEY_OPTION_DGN_DESCRIPTION"
Public Const KEY_OPTION_DGN_RADIALS         As String = "KEY_OPTION_DGN_RADIALS"
Public Const KEY_OPTION_DRAW_SYMBOL         As String = "KEY_OPTION_DRAW_SYMBOL"
Public Const KEY_OPTION_DROP_DIAGRAM_OFF    As String = "KEY_OPTION_DROP_DIAGRAM_OFF"
Public Const KEY_OPTION_FILENAME            As String = "KEY_OPTION_FILENAME"
Public Const KEY_OPTION_FORCE_LEADER        As String = "KEY_OPTION_FORCE_LEADER"
Public Const KEY_OPTION_HOLD_PT             As String = "KEY_OPTION_HOLD_PT"
Public Const KEY_OPTION_INCLUDE_PLUS00      As String = "KEY_OPTION_INCLUDE_PLUS00"
Public Const KEY_OPTION_LEADER              As String = "KEY_OPTION_LEADER"
Public Const KEY_OPTION_LONGITUDINAL        As String = "KEY_OPTION_LONGITUDINAL"
Public Const KEY_OPTION_OPPOSITES           As String = "KEY_OPTION_OPPOSITES"
Public Const KEY_OPTION_OVERUNDER           As String = "KEY_OPTION_OVERUNDER"
Public Const KEY_OPTION_PATH                As String = "KEY_OPTION_PATH"
Public Const KEY_OPTION_PREFIX              As String = "KEY_OPTION_PREFIX"
Public Const KEY_OPTION_REPORT_AZIMUTH      As String = "KEY_OPTION_REPORT_AZIMUTH"
Public Const KEY_OPTION_REPORT_COORDINATE   As String = "KEY_OPTION_REPORT_COORDINATE"
Public Const KEY_OPTION_REPORT_DATE         As String = "KEY_OPTION_REPORT_DATE"
Public Const KEY_OPTION_REPORT_DESCRIPTION  As String = "KEY_OPTION_REPORT_DESCRIPTION"
Public Const KEY_OPTION_REPORT_FILENAME     As String = "KEY_OPTION_REPORT_FILENAME"
Public Const KEY_OPTION_REPORT_NOTE         As String = "KEY_OPTION_REPORT_NOTE"
Public Const KEY_OPTION_REPORT_PATH         As String = "KEY_OPTION_REPORT_PATH"
Public Const KEY_OPTION_REPORT_PROJ_NAME    As String = "KEY_OPTION_REPORT_PROJ_NAME"
Public Const KEY_OPTION_REPORT_PROJ_NUM     As String = "KEY_OPTION_REPORT_PROJ_NUM"
Public Const KEY_OPTION_SIDE_DESC_CHK       As String = "KEY_OPTION_SIDE_DESC_CHK"
Public Const KEY_OPTION_SIDE_PT_NAME_CHK    As String = "KEY_OPTION_SIDE_PT_NAME_CHK"
Public Const KEY_OPTION_SIDE_SHOTS_OFF      As String = "KEY_OPTION_SIDE_SHOTS_OFF"
Public Const KEY_OPTION_TEXT_DIR            As String = "KEY_OPTION_TEXT_DIR"
Public Const KEY_OPTION_TEXT_DIST           As String = "KEY_OPTION_TEXT_DIST"
Public Const KEY_OPTION_TRANSFORM_ANGLE     As String = "KEY_OPTION_TRANSFORM_ANGLE"
Public Const KEY_OPTION_TRANSFORM_SCALE     As String = "KEY_OPTION_TRANSFORM_SCALE"
Public Const KEY_OPTION_TRANSVERSE          As String = "KEY_OPTION_TRANSVERSE"
Public Const KEY_OPTION_TRAV_DESC_CHK       As String = "KEY_OPTION_TRAV_DESC_CHK"
Public Const KEY_OPTION_TRAV_ELEV_CHK       As String = "KEY_OPTION_TRAV_ELEV_CHK"
Public Const KEY_OPTION_TRAV_PT_NAME_CHK    As String = "KEY_OPTION_TRAV_PT_NAME_CHK"
Public Const KEY_OPTION_USE_LOT_DESC        As String = "KEY_OPTION_USE_LOT_DESC"
Public Const KEY_ORIENTATION                As String = "KEY_ORIENTATION"
Public Const KEY_OUTPUT_TO_FILE             As String = "KEY_OUTPUT_TO_FILE"
Public Const KEY_OVERRIDE                   As String = "KEY_OVERRIDE"
Public Const KEY_OVERRIDE_ELEVATION         As String = "KEY_OVERRIDE_ELEVATION"
Public Const KEY_PC2CC                      As String = "KEY_PC2CC"
Public Const KEY_PC_STA_CURVE               As String = "KEY_PC_STA_CURVE"
Public Const KEY_PC_STA_LINE                As String = "KEY_PC_STA_LINE"
Public Const KEY_POINT_DESC                 As String = "KEY_POINT_DESC"
Public Const KEY_POINTNAME                  As String = "KEY_POINTNAME"
Public Const KEY_POINTNAME2                 As String = "KEY_POINTNAME2"
Public Const KEY_PLOT_SCALE                 As String = "KEY_PLOT_SCALE"
Public Const KEY_PLUS_MINUS_ANGLE           As String = "KEY_PLUS_MINUS_ANGLE"
Public Const KEY_PREFIX                     As String = "KEY_PREFIX"
Public Const KEY_PRECISION                  As String = "KEY_PRECISION"
Public Const KEY_PRECISION_ANG              As String = "KEY_PRECISION_ANG"
Public Const KEY_PRECISION_CHORD            As String = "KEY_PRECISION_CHORD"
Public Const KEY_PRECISION_COORD            As String = "KEY_PRECISION_COORD"
Public Const KEY_PRECISION_DIST             As String = "KEY_PRECISION_DIST"
Public Const KEY_PRECISION_ELEV             As String = "KEY_PRECISION_ELEV"
Public Const KEY_PT_STA_CURVE               As String = "KEY_PT_STA_CURVE"
Public Const KEY_PT_STA_LINE                As String = "KEY_PT_STA_LINE"
Public Const KEY_RADIAL_IN                  As String = "KEY_RADIAL_IN"
Public Const KEY_RADIAL_OUT                 As String = "KEY_RADIAL_OUT"
Public Const KEY_RADIALS_LEVEL              As String = "KEY_RADIALS_LEVEL"
Public Const KEY_RADIALS_COLOR              As String = "KEY_RADIALS_COLOR"
Public Const KEY_RADIALS_STYLE              As String = "KEY_RADIALS_STYLE"
Public Const KEY_RADIALS_WEIGHT             As String = "KEY_RADIALS_WEIGHT"
Public Const KEY_RADIUS                     As String = "KEY_RADIUS"
Public Const KEY_RADIUS2                    As String = "KEY_RADIUS2"
Public Const KEY_REC_EAST                   As String = "KEY_REC_EAST"
Public Const KEY_REC_ELEVATION              As String = "KEY_REC_ELEVATION"
Public Const KEY_REC_NORTH                  As String = "KEY_REC_NORTH"
Public Const KEY_REF_AZ                     As String = "KEY_REF_AZ"
Public Const KEY_REPROT_ANGLE_PREC          As String = "KEY_REPROT_ANGLE_PREC"
Public Const KEY_REPORT_DISTANCE_PREC       As String = "KEY_REPORT_DISTANCE_PREC"
Public Const KEY_REPORT_OPTION_SIDESHOTS    As String = "KEY_REPORT_OPTION_SIDESHOTS"
Public Const KEY_RETURN_HERE                As String = "KEY_RETURN_HERE"
Public Const KEY_REVISION_COLOR             As String = "KEY_REVISION_COLOR"
Public Const KEY_ROTATION                   As String = "KEY_ROTATION"
Public Const KEY_SET_REVISION_COLOR         As String = "KEY_SET_REVISION_COLOR"
Public Const KEY_SETUP_SYM_OPTION           As String = "KEY_SETUP_SYM_OPTION"
Public Const KEY_SHOW_DESCRIPTION           As String = "KEY_SHOW_DESCRIPTION"
Public Const KEY_SHOW_DROP                  As String = "KEY_SHOW_DROP"
Public Const KEY_SHOW_ELEVATION             As String = "KEY_SHOW_ELEVATION"
Public Const KEY_SHOW_NE                    As String = "KEY_SHOW_NE"
Public Const KEY_SIDE                       As String = "KEY_SIDE"
Public Const KEY_SIDE_DESC_OFFSET_LR        As String = "KEY_SIDE_DESC_OFFSET_LR"
Public Const KEY_SIDE_DESC_OFFSET_UD        As String = "KEY_SIDE_DESC_OFFSET_UD"
Public Const KEY_SIDE_LINE_COLOR            As String = "KEY_SIDE_LINE_COLOR"
Public Const KEY_SIDE_LINE_LEVEL            As String = "KEY_SIDE_LINE_LEVEL"
Public Const KEY_SIDE_LINE_STYLE            As String = "KEY_SIDE_LINE_STYLE"
Public Const KEY_SIDE_LINE_WEIGHT           As String = "KEY_SIDE_LINE_WEIGHT"
Public Const KEY_SIDE_NAME_OFFSET_LR        As String = "KEY_SIDE_NAME_OFFSET_LR"
Public Const KEY_SIDE_NAME_OFFSET_UD        As String = "KEY_SIDE_NAME_OFFSET_UD"
Public Const KEY_SIDE_SYMBOL_COLOR          As String = "KEY_SIDE_SYMBOL_COLOR"
Public Const KEY_SIDE_SYMBOL_LEVEL          As String = "KEY_SIDE_SYMBOL_LEVEL"
Public Const KEY_SIDE_SYMBOL_STYLE          As String = "KEY_SIDE_SYMBOL_STYLE"
Public Const KEY_SIDE_SYMBOL_WEIGHT         As String = "KEY_SIDE_SYMBOL_WEIGHT"
Public Const KEY_SIDE_TEXT_COLOR            As String = "KEY_SIDE_TEXT_COLOR"
Public Const KEY_SIDE_TEXT_LEVEL            As String = "KEY_SIDE_TEXT_LEVEL"
Public Const KEY_SIDE_TEXT_STYLE            As String = "KEY_SIDE_TEXT_STYLE"
Public Const KEY_SIDE_TEXT_WEIGHT           As String = "KEY_SIDE_TEXT_WEIGHT"
Public Const KEY_SIDE_TEXT_FONT             As String = "KEY_SIDE_TEXT_FONT"
Public Const KEY_SPIRAL_ANGLE               As String = "KEY_SPIRAL_ANGLE"
Public Const KEY_SPIRAL_DATA_HEADING         As String = "KEY_SPIRAL_DATA_HEADING"
Public Const KEY_SPIRAL_DATA_PREFIX         As String = "KEY_SPIRAL_DATA_PREFIX"
Public Const KEY_SPIRAL_DEF_TYPE            As String = "KEY_SPIRAL_DEF_TYPE"
Public Const KEY_SPIRAL_DRAW_END_SYM        As String = "KEY_SPIRAL_DRAW_END_SYM"
Public Const KEY_SPIRAL_DRAW_SPIRAL_DATA    As String = "KEY_SPIRAL_DRAW_SPIRAL_DATA"
Public Const KEY_SPIRAL_DRAW_START_SYM      As String = "KEY_SPIRAL_DRAW_START_SYM"
Public Const KEY_SPIRAL_DRAW_TANGENTS       As String = "KEY_SPIRAL_DRAW_TANGENTS"
Public Const KEY_SPIRAL_LEGNTH              As String = "KEY_SPIRAL_LEGNTH"
Public Const KEY_SPIRAL_MODE                As String = "KEY_SPIRAL_MODE"
Public Const KEY_SPIRAL_ORIENT              As String = "KEY_SPIRAL_ORIENT"
Public Const KEY_SPIRAL_INGOING             As String = "KEY_SPIRAL_INGOING"
Public Const KEY_SPIRAL_RADIUS              As String = "KEY_SPIRAL_RADIUS"
Public Const KEY_SPIRAL_TANGENT_IN          As String = "KEY_SPIRAL_TANGENT_IN"
Public Const KEY_SQUARE                     As String = "KEY_SQUARE"
Public Const KEY_SQUARE_SIZE                As String = "KEY_SQUARE_SIZE"
Public Const KEY_START_LEFT                 As String = "KEY_START_LEFT"
Public Const KEY_START_POINT_Z              As String = "KEY_START_POINT_Z"
Public Const KEY_START_PREFIX               As String = "KEY_START_PREFIX"
Public Const KEY_START_PREFIX_OPTION        As String = "KEY_START_PREFIX_OPTION"
Public Const KEY_START_TOP                  As String = "KEY_START_TOP"
Public Const KEY_STATION                    As String = "KEY_STATION"
Public Const KEY_STATION_START              As String = "KEY_STATION_START"
Public Const KEY_STATION_END                As String = "KEY_STATION_END"
Public Const KEY_STYLE                      As String = "KEY_STYLE"
Public Const KEY_STYLE2                     As String = "KEY_STYLE2"
Public Const KEY_SYM_COLOR                  As String = "KEY_SYM_COLOR"
Public Const KEY_SYM_LEVEL                  As String = "KEY_SYM_LEVEL"
Public Const KEY_SYM_STYLE                  As String = "KEY_SYM_STYLE"
Public Const KEY_SYM_WEIGHT                 As String = "KEY_SYM_WEIGHT"
Public Const KEY_SYMBOL_LEVEL               As String = "KEY_SYMBOL_LEVEL"
Public Const KEY_SYMBOL_COLOR               As String = "KEY_SYMBOL_COLOR"
Public Const KEY_SYMBOL_STYLE               As String = "KEY_SYMBOL_STYLE"
Public Const KEY_SYMBOL_WEIGHT              As String = "KEY_SYMBOL_WEIGHT"
Public Const KEY_TANGENT_AZ_IN              As String = "KEY_TANGENT_AZ_IN"
Public Const KEY_TANGENT_AZ_OUT             As String = "KEY_TANGENT_AZ_OUT"
Public Const KEY_TANGENT_IN                 As String = "KEY_TANGENT_IN"
Public Const KEY_TANGENT_OUT                As String = "KEY_TANGENT_OUT"
Public Const KEY_TI_CHORD_DR                As String = "KEY_TI_CHORD_DR"
Public Const KEY_TICKS_LEFT                 As String = "KEY_TICKS_LEFT"
Public Const KEY_TICKS_RIGHT                As String = "KEY_TICKS_RIGHT"
Public Const KEY_TICKS_SCALE_LEFT           As String = "KEY_TICKS_SCALE_LEFT"
Public Const KEY_TICKS_SCALE_RIGHT          As String = "KEY_TICKS_SCALE_RIGHT"
Public Const KEY_TO_CHORD_DR                As String = "KEY_TO_CHORD_DR"
Public Const KEY_TOGGLE_LARGER              As String = "KEY_TOGGLE_LARGER"
Public Const KEY_TRANSFORMATION_ANGLE       As String = "KEY_TRANSFORMATION_ANGLE"
Public Const KEY_TRANSFORMATION_SCALE       As String = "KEY_TRANSFORMATION_SCALE"
Public Const KEY_TRANSVERSE_OFFSET          As String = "KEY_TRANSVERSE_OFFSET"
Public Const KEY_TRAV_DESC_OFFSET_LR        As String = "KEY_TRAV_DESC_OFFSET_LR"
Public Const KEY_TRAV_DESC_OFFSET_UD        As String = "KEY_TRAV_DESC_OFFSET_UD"
Public Const KEY_TRAV_ELEV_OFFSET_LR        As String = "KEY_TRAV_ELEV_OFFSET_LR"
Public Const KEY_TRAV_ELEV_OFFSET_UD        As String = "KEY_TRAV_ELEV_OFFSET_UD"
Public Const KEY_TRAV_LINE_COLOR            As String = "KEY_TRAV_LINE_COLOR"
Public Const KEY_TRAV_LINE_LEVEL            As String = "KEY_TRAV_LINE_LEVEL"
Public Const KEY_TRAV_LINE_STYLE            As String = "KEY_TRAV_LINE_STYLE"
Public Const KEY_TRAV_LINE_WEIGHT           As String = "KEY_TRAV_LINE_WEIGHT"
Public Const KEY_TRAV_NAME_OFFSET_LR        As String = "KEY_TRAV_NAME_OFFSET_LR"
Public Const KEY_TRAV_NAME_OFFSET_UD        As String = "KEY_TRAV_NAME_OFFSET_UD"
Public Const KEY_TRAV_SYMBOL_COLOR          As String = "KEY_TRAV_SYMBOL_COLOR"
Public Const KEY_TRAV_SYMBOL_LEVEL          As String = "KEY_TRAV_SYMBOL_LEVEL"
Public Const KEY_TRAV_SYMBOL_STYLE          As String = "KEY_TRAV_SYMBOL_STYLE"
Public Const KEY_TRAV_SYMBOL_WEIGHT         As String = "KEY_TRAV_SYMBOL_WEIGHT"
Public Const KEY_TRAV_TEXT_COLOR            As String = "KEY_TRAV_TEXT_COLOR"
Public Const KEY_TRAV_TEXT_FONT             As String = "KEY_TRAV_TEXT_FONT"
Public Const KEY_TRAV_TEXT_LEVEL            As String = "KEY_TRAV_TEXT_LEVEL"
Public Const KEY_TRAV_TEXT_STYLE            As String = "KEY_TRAV_TEXT_STYLE"
Public Const KEY_TRAV_TEXT_WEIGHT           As String = "KEY_TRAV_TEXT_WEIGHT"
Public Const KEY_TRAV_SYMBOL                As String = "KEY_TRAV_SYMBOL"
Public Const KEY_TEXT_LEVEL                 As String = "KEY_TEXT_LEVEL"
Public Const KEY_TEXT_COLOR                 As String = "KEY_TEXT_COLOR"
Public Const KEY_TEXT_STYLE                 As String = "KEY_TEXT_STYLE"
Public Const KEY_TEXT_WEIGHT                As String = "KEY_TEXT_WEIGHT"
Public Const KEY_TEXT_FONT                  As String = "KEY_TEXT_FONT"
Public Const KEY_UPDATE_AFTER               As String = "KEY_UPDATE_AFTER"
Public Const KEY_WEIGHT                     As String = "KEY_WEIGHT"
Public Const KEY_WEIGHT2                    As String = "KEY_WEIGHT2"
Public Const KEY_X_AXIS_OFFSET              As String = "KEY_X_AXIS_OFFSET"
Public Const KEY_Y_AXIS_OFFSET              As String = "KEY_Y_AXIS_OFFSET"


'OPTIONS
Public Const OPTION_100S                    As String = "OPTION_100S"
Public Const OPTION_500S                    As String = "OPTION_500S"

Public Const OPTION_TRUE                    As String = "True"
Public Const OPTION_FALSE                   As String = "False"

Public Const OPTION_ALIGN_LEFT              As String = "OPTION_ALIGN_LEFT"
Public Const OPTION_ALIGN_RIGHT             As String = "OPTION_ALIGN_RIGHT"

Public Const OPTION_AHEAD                   As String = "OPTION_AHEAD"
Public Const OPTION_BACK                    As String = "OPTION_BACK"

Public Const OPTION_AZ_DIST                 As String = "OPTION_AZ_DIST"
Public Const OPTION_AZ                      As String = "OPTION_AZ"
Public Const OPTION_DIST                    As String = "OPTION_DIST"
Public Const OPTION_ARROW                   As String = "OPTION_ARROW"

Public Const OPTION_LEFT                    As String = "Left"
Public Const OPTION_RIGHT                   As String = "Right"

Public Const OPTION_CURVE                   As String = "OPTION_CURVE"
Public Const OPTION_LINE                    As String = "OPTION_LINE"

Public Const OPTION_PC                      As String = "PC"
Public Const OPTION_PI                      As String = "PI"

Public Const OPTION_STATION                 As String = "Station"
Public Const OPTION_DISTANCE                As String = "Distance"

Public Const OPTION_CURVE_IN_TYPE_TANGENT   As String = "Tangent"
Public Const OPTION_CURVE_IN_TYPE_PC2CC     As String = "PcToCc"

Public Const OPTION_CURVE_OUT_TYPE_DELTA    As String = "Delta"
Public Const OPTION_CURVE_OUT_TYPE_PT_STA   As String = "PtSta"
Public Const OPTION_CURVE_OUT_TYPE_TAN_OUT  As String = "TangentOut"
Public Const OPTION_CURVE_OUT_TYPE_CC2PC    As String = "CcToPc"

Public Const OPTION_DIR_TYPE_AZIMUTH        As String = "Azimuth"
Public Const OPTION_DIR_TYPE_BEARING        As String = "Bearing"

Public Const OPTION_JUSTIFIED_RIGHT         As String = "OPTION_JUSTIFIED_RIGHT"
Public Const OPTION_JUSTIFIED_CENTER        As String = "OPTION_JUSTIFIED_CENTER"
Public Const OPTION_JUSTIFIED_LEFT          As String = "OPTION_JUSTIFIED_LEFT"

Public Const OPTION_PREC_ANG_SEC            As String = "Sec."
Public Const OPTION_PREC_ANG_SEC1           As String = "0.1 Sec."
Public Const OPTION_PREC_ANG_SEC01          As String = "0.01 Sec."
Public Const OPTION_PREC_ANG_SEC001         As String = "0.001 Sec."
Public Const OPTION_PREC_ANG_SEC0001        As String = "0.0001 Sec."

Public Const OPTION_PREC_DIST_FT            As String = "ft."
Public Const OPTION_PREC_DIST_FT1           As String = "0.1 ft."
Public Const OPTION_PREC_DIST_FT01          As String = "0.01 ft."
Public Const OPTION_PREC_DIST_FT001         As String = "0.001 ft."
Public Const OPTION_PREC_DIST_FT0001        As String = "0.0001 ft."
Public Const OPTION_PREC_DIST_FT00001       As String = "0.00001 ft."

Public Const OPTION_TOP_TO_LEFT             As String = "OPTION_TOP_TO_LEFT"
Public Const OPTION_TOP_TO_RIGHT            As String = "OPTION_TOP_TO_RIGHT"
Public Const OPTION_TOP_FORWARD             As String = "OPTION_TOP_FORWARD"
Public Const OPTION_TOP_BACK                As String = "OPTION_TOP_BACK"

Public Const OPTION_NO_00                   As String = "OPTION_NO_00"
Public Const OPTION_NO_00_00                As String = "OPTION_NO_00_00"
Public Const OPTION_NOTHING                 As String = "OPTION_NOTHING"

Public Const OPTION_FEET                    As String = "OPTION_FEET"
Public Const OPTION_ACRES                   As String = "OPTION_ACRES"
Public Const OPTION_FEET_AND_ACRES          As String = "OPTION_FEET_AND_ACRES"

Public Const CURVE_DEFINITION_CHORD         As String = "CURVE_DEFINITION_CHORD"
Public Const CURVE_DEFINITION_RADIALS       As String = "CURVE_DEFINITION_RADIALS"
Public Const CURVE_DEFINITION_TANGENTS      As String = "CURVE_DEFINITION_TANGENTS"
Public Const CURVE_DEFINITION_TAN_OUT_CHD   As String = "CURVE_DEFINITION_TAN_OUT_CHD"
Public Const CURVE_DEFINITION_TAN_IN_CHD    As String = "CURVE_DEFINITION_TAN_IN_CHD"

Public Const OPTION_RADIUS                  As String = "OPTION_RADIUS"
Public Const OPTION_SPIRAL_ANGLE            As String = "OPTION_SPIRAL_ANGLE"

Public Const OPTION_DEFAULT                 As String = "OPTION_DEFAULT"
Public Const OPTION_OTHER                   As String = "OPTION_OTHER"

'VALUES
Public Const Square_Feet_Per_Acre           As Double = 43560

Public Const WINDOW_DEFAULT_LEFT            As String = "100.00"
Public Const WINDOW_DEFAULT_TOP             As String = "100.00"

Public Const TOOL_TIP_ENTER_DIRECTION       As String = "Enter azimuth or bearing, + or - prefix and postfix for quadrant."
Public Const TOOL_TIP_ENTER_STATION         As String = "Enter station."

Public Const ACCEPT_RESET_STRING            As String = "Accept/Reset"
Public Const CANCELLED_BY_RESET_STRING      As String = "Cancelled by Reset."

Public Const Column_Width_Multiplier        As Double = 1#  'use for adjusting column width on Plot Lot and Compass Rule


'TAGS CARRIED OVER FROM ORIGINAL TO KEEP COMPATIBLE
Public Const TAG_NAME_BEGIN_STATION         As String = "beginStation"
Public Const TAG_NAME_LENGTH                As String = "length"
Public Const TAG_SET_NAME                   As String = "Surveyor Tools 2015"
Public Const TAG_NAME_STATION               As String = "station"
Public Const TAG_NAME_MY_ID                 As String = "myid"
Public Const TAG_NAME_HOST_ID               As String = "hostid"
Public Const TAG_NAME_DROP                  As String = "Drop Diagram"
Public Const TAG_NAME_COMPASS_RULE_2D_ID    As String = "TravFileID"

'NEW TAGS
Public Const TAG_NAME_LABEL_LINE            As String = "Line Label"
Public Const TAG_NAME_SPIRAL_ANGLE          As String = "SpiralAngle"
Public Const TAG_NAME_CURVES_LEFT           As String = "CurvesLeft"
Public Const TAG_NAME_INGOING               As String = "Ingoing"


'ERROR NUMBERS
Public Const ERROR_NUM_513                  As Long = 513  'TEMPORARY ERROR CODE TO BE REPLACED
Public Const ERROR_NUM_514                  As Long = 514  'FORM FrmCurveSolver Function CreateTempCurve
Public Const ERROR_NUM_515                  As Long = 515  'FORM FrmCurveSolver Function CreateTempCurve
Public Const ERROR_NUM_516                  As Long = 516  'FORM FrmCurveSolver Function CreateTempCurve
Public Const ERROR_NUM_517                  As Long = 517  'FORM FrmCurveSolver Sub DrawPermBaseCurve
Public Const ERROR_NUM_518                  As Long = 518  'FORM FrmCurveSolver Sub DrawPermBaseCurve
Public Const ERROR_NUM_519                  As Long = 519  'FORM FrmCurveSolver Sub DrawPermBaseCurve
Public Const ERROR_NUM_520                  As Long = 520  'FORM FrmCurveSolver Function CreateArcPartFromPC
Public Const ERROR_NUM_521                  As Long = 521  'FORM FrmCurveSolver Function CreateArcPartFromPC
Public Const ERROR_NUM_522                  As Long = 522  'FORM FrmCurveSolver Function CreateLinePart
Public Const ERROR_NUM_523                  As Long = 523  'MODULE DropDiagramCode, Function CreateDropCell
Public Const ERROR_NUM_524                  As Long = 524  'MODULE DropDiagramCode, Function CreateRefDirString
Public Const ERROR_NUM_525                  As Long = 525  'MODULE DropDiagramCode, Function GetDropCell
Public Const ERROR_NUM_526                  As Long = 526  'MODULE DropDiagramCode, Sub CalcDiagramValues
Public Const ERROR_NUM_527                  As Long = 527  'FORM frmCompasRule, Function AngleStringPrecision
Public Const ERROR_NUM_528                  As Long = 528  'MODULE CompassRuleFileCode,FormatToWriteNorth
Public Const ERROR_NUM_529                  As Long = 529  'MODULE CompassRuleFileCode,FormatToWriteEast
Public Const ERROR_NUM_530                  As Long = 530  'FORM frmCompasRule, Function CalcRaw
Public Const ERROR_NUM_531                  As Long = 531  'FORM frmCompasRule, Sub DrawTheCircuit
Public Const ERROR_NUM_532                  As Long = 532  'FORM frmCompasRule, Function forwardPoint
Public Const ERROR_NUM_533                  As Long = 533  'FORM frmCompasRule, Function GetNorthing
Public Const ERROR_NUM_534                  As Long = 534  'FORM frmCompasRule, Function forwardPoint
Public Const ERROR_NUM_535                  As Long = 535  'FORM frmCompasRule, Function GetEasting
Public Const ERROR_NUM_536                  As Long = 536  'FORM frmCompasRule, Sub TraversesAddButton_Click
Public Const ERROR_NUM_537                  As Long = 537  'MODULE TextEntriesAndChkBox, Function AngleStringToDegree
Public Const ERROR_NUM_538                  As Long = 538  'FORM frmCompasRule, Sub AdjSecondPartOfArray
Public Const ERROR_NUM_539                  As Long = 539  'FORM FrmPlotLot, Function DrawLineCourse
Public Const ERROR_NUM_540                  As Long = 540  'FORM FrmPlotLot, Function DrawLineCourse
Public Const ERROR_NUM_541                  As Long = 541  'FORM FrmPlotLot, Sub CurveByChordToElement
Public Const ERROR_NUM_542                  As Long = 542  'FORM FrmPlotLot, Sub CurveByChordToElement
Public Const ERROR_NUM_543                  As Long = 543  'FORM FrmPlotLot, Sub CurveByChordToElement
Public Const ERROR_NUM_544                  As Long = 544  'FORM FrmPlotLot, Function DrawCurveByChord
Public Const ERROR_NUM_545                  As Long = 545  'FORM FrmPlotLot, Sub CurveByRadialsToElement
Public Const ERROR_NUM_546                  As Long = 546  'FORM FrmPlotLot, Sub CurveByRadialsToElement
Public Const ERROR_NUM_547                  As Long = 547  'FORM FrmPlotLot, Sub CurveByRadialsToElement
Public Const ERROR_NUM_548                  As Long = 548  'FORM FrmPlotLot, Sub CurveByTangentsToElement
Public Const ERROR_NUM_549                  As Long = 549  'FORM FrmPlotLot, Sub CurveByTangentsToElement
Public Const ERROR_NUM_550                  As Long = 550  'FORM FrmPlotLot, Sub CurveByTangentsToElement
Public Const ERROR_NUM_551                  As Long = 551  'FORM FrmPlotLot, Function calcLineEndFromIndex
Public Const ERROR_NUM_552                  As Long = 552  'FORM FrmPlotLot, Function calcLineEndFromIndex
Public Const ERROR_NUM_553                  As Long = 553  'FORM FrmPlotLot, Function CalcCurveEndFromIndex
Public Const ERROR_NUM_554                  As Long = 554  'FORM FrmPlotLot, Function DirectionStringPlus
Public Const ERROR_NUM_555                  As Long = 555  'FORM FrmPlotLot, Function DirectionStringPlus
Public Const ERROR_NUM_556                  As Long = 556  'FORM FrmPlotLot, CurveByTanOutChrToElement
Public Const ERROR_NUM_557                  As Long = 557  'FORM FrmPlotLot, CurveByTanOutChrToElement
Public Const ERROR_NUM_558                  As Long = 558  'FORM FrmPlotLot, CurveByTanOutChrToElement
Public Const ERROR_NUM_559                  As Long = 559  'FORM FrmPlotLot, CurveByTanInChrToElement
Public Const ERROR_NUM_560                  As Long = 560  'FORM FrmPlotLot, CurveByTanInChrToElement
Public Const ERROR_NUM_561                  As Long = 561  'FORM FrmPlotLot, CurveByTanInChrToElement
Public Const ERROR_NUM_562                  As Long = 562  'FORM FrmCurveSolver, Function SpiralCalc
Public Const ERROR_NUM_563                  As Long = 563  'FORM FrmCurveSolver, SUB getCurveDef
Public Const ERROR_NUM_564                  As Long = 564  'FORM FrmCurveSolver, SUB getCurveDef
Public Const ERROR_NUM_565                  As Long = 565  'FORM FrmCurveSolver, SUB getCurveDef
Public Const ERROR_NUM_566                  As Long = 566  'FORM FrmCurveSolver, Function CreateTempSpiral
Public Const ERROR_NUM_567                  As Long = 567  'FORM FrmCurveSolver, SUB DrawPermBaseSpiral
Public Const ERROR_NUM_568                  As Long = 568  'FORM FrmCurveSolver, SUB DrawPermBaseSpiral

Attribute VB_Name = "ClsOpenCloseDupFind"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.



'GENERAL NOTES:
'PROGRAM ASSUMES MASTER UNIT IS FOOT OR SURVEY FOOT, SOME KIND OF FOOT

Option Explicit

Private WithEvents hooks As Application
Attribute hooks.VB_VarHelpID = -1

Private Sub Class_Initialize()
   Set hooks = Application
End Sub

Private Sub hooks_OnDesignFileClosed(ByVal DesignFileName As String)
   FrmDupFinder.enabled = False
End Sub

Private Sub hooks_OnDesignFileOpened(ByVal DesignFileName As String)
   FrmDupFinder.enabled = True
End Sub

Attribute VB_Name = "ClsOpenClosePlotLot"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.



'GENERAL NOTES:
'PROGRAM ASSUMES MASTER UNIT IS FOOT OR SURVEY FOOT, SOME KIND OF FOOT

Option Explicit

Private WithEvents hooks As Application
Attribute hooks.VB_VarHelpID = -1

Private Sub Class_Initialize()
   Set hooks = Application
End Sub

Private Sub hooks_OnDesignFileClosed(ByVal DesignFileName As String)
   FrmPlotLot.enabled = False
End Sub

Private Sub hooks_OnDesignFileOpened(ByVal DesignFileName As String)
   FrmPlotLot.enabled = True
   FrmPlotLot.UpdatePlotLotOnFileOpen
End Sub

Attribute VB_Name = "ClsViewChange"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.


Option Explicit

Implements IViewUpdateEvents
Private WithEvents hooks As Application
Attribute hooks.VB_VarHelpID = -1

Private Sub Class_Initialize()
   Set hooks = Application
End Sub

Private Sub IViewUpdateEvents_AfterRedraw(TheViews() As view, TheModels() As ModelReference, ByVal DrawMode As MsdDrawingMode)
   FrmDupFinder.DisplaySquares
End Sub

Private Sub IViewUpdateEvents_BeforeRedraw(TheViews() As view, TheModels() As ModelReference, ByVal DrawMode As MsdDrawingMode)

End Sub

Attribute VB_Name = "Commoners"
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit

Public Const backgroundGrey = &H8000000F
Public Const backgroundWhite = &H80000005
Public Const SEPARATOR_KEY2                     As String = ":"

#If VBA7 Then
'  Code is running in the new VBA7 editor
     #If Win64 Then
     '  Code is running in 64-bit version of Microsoft Office
     #Else
     '  Code is running in 32-bit version of Microsoft Office
     #End If
#Else
' Code is running in VBA version 6 or earlier
#End If




#If VBA7 Then
   Public Declare PtrSafe Function ShellExecute Lib "shell32.dll" Alias _
        "ShellExecuteA" (ByVal hwnd As LongPtr, _
        ByVal lpOperation As String, ByVal lpFile As String, _
        ByVal lpParameters As String, ByVal lpDirectory As String, _
        ByVal nShowCmd As Long) As Long
#Else
   Public Declare Function ShellExecute Lib "shell32.dll" Alias _
        "ShellExecuteA" (ByVal hwnd As Long, _
        ByVal lpOperation As String, ByVal lpFile As String, _
        ByVal lpParameters As String, ByVal lpDirectory As String, _
        ByVal nShowCmd As Long) As Long
#End If




#If VBA7 Then
   Declare PtrSafe Function mdlDialog_fileOpen Lib "stdmdlbltin.dll" (ByVal _
      filename As String, ByVal rFileH As LongPtr, ByVal _
      resourceId As Long, ByVal SuggestedFilename As String, _
      ByVal FilterString As String, ByVal defaultDirectory As String, _
      ByVal titleString As String) As Long
#Else
   Declare Function mdlDialog_fileOpen Lib "stdmdlbltin.dll" (ByVal _
      filename As String, ByVal rFileH As Long, ByVal _
      resourceId As Long, ByVal SuggestedFilename As String, _
      ByVal FilterString As String, ByVal defaultDirectory As String, _
      ByVal titleString As String) As Long
#End If
    
    
    
    
    
#If VBA7 Then
   Declare PtrSafe Function mdlDialog_fileCreate Lib "stdmdlbltin.dll" (ByVal _
      filename As String, ByVal rFileH As LongPtr, ByVal resourceId As Long, _
      ByVal SuggestedFilename As String, ByVal FilterString As String, _
      ByVal defaultDirectory As String, ByVal titleString As String) As Long
#Else
   Declare Function mdlDialog_fileCreate Lib "stdmdlbltin.dll" (ByVal _
      filename As String, ByVal rFileH As Long, ByVal resourceId As Long, _
      ByVal SuggestedFilename As String, ByVal FilterString As String, _
      ByVal defaultDirectory As String, ByVal titleString As String) As Long
#End If
    
    



#If VBA7 Then
   Declare PtrSafe Function mdlDialog_fileOpenExt Lib "stdmdlbltin.dll" (ByVal fileNameP As String, _
      ByVal extraInfoP As LongPtr, ByVal paramsP As LongPtr, ByVal attributes As Long) As Long
#Else
   Declare Function mdlDialog_fileOpenExt Lib "stdmdlbltin.dll" (ByVal fileNameP As String, _
      ByVal extraInfoP As Long, ByVal paramsP As Long, ByVal attributes As Long) As Long
#End If
    
    
    
#If VBA7 Then
   Declare PtrSafe Function mdlDialog_fileCreateFromSeed Lib _
      "stdmdlbltin.dll" (ByVal filename As String, _
      ByVal rFileH As Long, ByVal resourceId As LongPtr, _
      ByVal SuggestedFilename As String, _
      ByVal FilterString As String, _
      ByVal defaultDirectory As String, _
      ByVal titleString As String, _
      ByVal seedFile As String, _
      ByVal seedDirectory As String, _
      ByVal seedFilter As String) As Long
#Else
   Declare Function mdlDialog_fileCreateFromSeed Lib _
      "stdmdlbltin.dll" (ByVal filename As String, _
      ByVal rFileH As Long, ByVal resourceId As Long, _
      ByVal SuggestedFilename As String, _
      ByVal FilterString As String, _
      ByVal defaultDirectory As String, _
      ByVal titleString As String, _
      ByVal seedFile As String, _
      ByVal seedDirectory As String, _
      ByVal seedFilter As String) As Long
#End If



Public Sub ShellExecuteNormal(FileToOpen As String)
    ShellExecute 0, "OPEN", _
        FileToOpen, "", "C:\Windows", vbNormalFocus 'vbMaximizedFocus
End Sub




Public Function calcCharSize(ByVal TheView As view, ByVal PixelsPerChar As Integer) As Double
'FOR USING FIXED SCREEN SIZED CHARACTERS
   calcCharSize = CalcMasterUnitPerPixel(TheView) * Abs(PixelsPerChar)
End Function



Private Function CalcMasterUnitPerPixel(ByVal TheView As view) As Double
   Dim Extents As Point3d
   Dim ViewOrigin As Point3d
   Dim ViewRotation As Matrix3d

'MAKE WORKING COPY
   Extents = TheView.Extents
   ViewOrigin = TheView.origin
   ViewRotation = TheView.rotation

'CALCULATE MEASUREMENT POINT
   Dim MeasurePoint As Point3d
   Dim MetricX As Double
   Dim Vector As Point3d
   
   MetricX = Extents.X * 0.99  'so the pixel does not fall off the edge
      
   'CALCULATE FOR VIEW ROTATION
   Vector = Point3dFromMatrix3dInverseTimesPoint3d(ViewRotation, Point3dFromXYZ(MetricX, 0, 0))
   MeasurePoint.X = ViewOrigin.X + Vector.X
   MeasurePoint.Y = ViewOrigin.Y + Vector.Y
   MeasurePoint.z = ViewOrigin.z + Vector.z
   
'CONVERT TO PIXELS
   Dim PixelPosition As Point2d

   PixelPosition = TheView.GetPixelPosition(MeasurePoint, True)

'CALCULATE THE RATIO
   CalcMasterUnitPerPixel = MetricX / Max(PixelPosition.X, 1) 'make sure you don't divide by zero
End Function



Public Function getSelectedIndex(ByRef CoordinateListBox As ListBox) As Long
   getSelectedIndex = -1
   Dim i As Long
   For i = 0 To CoordinateListBox.ListCount - 1
      If CoordinateListBox.Selected(i) Then
         getSelectedIndex = i
         Exit For
      End If
   Next i
End Function



Public Sub selectionAll(state As Boolean, ByRef CoordinateListBox As ListBox)
   Dim i As Long
   For i = 0 To CoordinateListBox.ListCount - 1
      If CoordinateListBox.Selected(i) <> state Then
         CoordinateListBox.Selected(i) = state
      End If
   Next i
End Sub


Public Function GetAngPrec1(precString As String) As Long
   Select Case precString
      Case OPTION_PREC_ANG_SEC
         GetAngPrec1 = 4
      Case OPTION_PREC_ANG_SEC1
         GetAngPrec1 = 5
      Case OPTION_PREC_ANG_SEC01
         GetAngPrec1 = 6
      Case OPTION_PREC_ANG_SEC001
         GetAngPrec1 = 7
      Case Else
         GetAngPrec1 = 4
   End Select
End Function



Public Function ParsePointString(InputString As String, _
                                 ByRef name As String, _
                                 ByRef northing As String, _
                                 ByRef easting As String, _
                                 ByRef elevation As String, _
                                 ByRef description As String) As Boolean
'RETURNS TRUE IF SUCCESSFUL
'SET FLAG
   ParsePointString = False

'CHECK FOR EMPTINESS
   If Trim(InputString) = "" Then
      Exit Function
   End If

'SEPERATE BY COMMAS
   Dim XSplit As Variant
   XSplit = Split(InputString, ",")

'CHECK IF ENOUGH FIELDS
   Dim NumberOfFields As Long
   NumberOfFields = UBound(XSplit) - LBound(XSplit) + 1
   If NumberOfFields < 4 Then
      Exit Function
   End If

'CHECK IF NORTHING, EASTING, AND ELEVATION FIELDS ARE NUMBERS
   Dim index As Long
   index = LBound(XSplit) + 1
   If IsNumeric(XSplit(index)) Then
      Dim NorthingString As String
      NorthingString = FormatNumber(CDbl(XSplit(index)), 4)
      index = index + 1
   Else
      Exit Function
   End If
   If IsNumeric(XSplit(index)) Then
      Dim EastingString As String
      EastingString = FormatNumber(CDbl(XSplit(index)), 4)
      index = index + 1
   Else
      Exit Function
   End If
   If IsNumeric(XSplit(index)) Then
      Dim elevationString As String
      elevationString = FormatNumber(CDbl(XSplit(index)), 4)
      index = index + 1
   Else
      Exit Function
   End If
 
'PROCESS THE DESCRIPTION FIELD
   If NumberOfFields = 4 Then
      Dim TheDescription As String
      TheDescription = STRING_SPACE
   ElseIf NumberOfFields = 5 Then
      TheDescription = XSplit(index)
   Else
      Dim descriptionString As String
      descriptionString = XSplit(LBound(XSplit) + 4)
      Dim i As Long
      For i = LBound(XSplit) + 5 To UBound(XSplit)
         descriptionString = descriptionString & "," & XSplit(i)
      Next i
      TheDescription = descriptionString
   End If

'RETURN VALUES IF VALID
   name = XSplit(LBound(XSplit))
   northing = NorthingString
   easting = EastingString
   elevation = elevationString
   description = TheDescription
   ParsePointString = True
End Function



Public Function PaddedNorthingString(ByVal northing As Double, prec As Long) As String
   PaddedNorthingString = PadLead(DoubleToNorthingString(northing, prec), 14)
End Function



Public Function PaddedEastingString(ByVal easting As Double, prec As Long) As String
   PaddedEastingString = PadLead(DoubleToEastingString(easting, prec), 14)
End Function



Public Function PadTheEnd(TextToPad As String, ByVal MinStringLen As Long) As String
'PADS THE ENDING OF A STRING WITH SPACES TO ACHIEVE MINIMUM STRING LENGTH
   Dim ThePadString As String
   ThePadString = ""
   Dim StringLen As Long
   StringLen = Len(TextToPad)
   Dim i As Long
   For i = 1 To MinStringLen - StringLen
      ThePadString = " " & ThePadString
   Next
   PadTheEnd = TextToPad & ThePadString
End Function



Public Function PadLead(TextToPad As String, ByVal MinStringLen As Long) As String
'PADS THE BEGINNING OF A STRING WITH SPACES TO ACHIEVE MINIMUM STRING LENGTH
   Dim ThePadString As String
   ThePadString = ""
   Dim StringLen As Long
   StringLen = Len(TextToPad)
   Dim i As Long
   For i = 1 To MinStringLen - StringLen
      ThePadString = " " & ThePadString
   Next
   PadLead = ThePadString & TextToPad
End Function



Public Function StringTrueFalse(ByVal TFString As String) As Boolean
   If TFString = OPTION_TRUE Then
      StringTrueFalse = True
   Else
      StringTrueFalse = False
   End If
End Function



Public Sub TextTheLine(textTemplate As TextElement, _
                       theLine As LineElement, _
                       theTextString As String, _
                       vertOffset As Double, _
                       linePointsLeft As Boolean)
'SUBROUTINE FOR INTERSECTION PROGAMS
'TEXT TEMPLATE SHOULD BE CENTER,CENTER JUSTIFIED
   Dim MidLine As Point3d
   MidLine = CalcMidPoint(theLine.startPoint, theLine.endPoint)
   Dim insertPoint As Point3d
   insertPoint = MidLine
   insertPoint.Y = insertPoint.Y + vertOffset
   Dim LineText As TextElement
   Set LineText = CreateTextElement1(textTemplate, theTextString, insertPoint, Matrix3dIdentity)
'ROTATE IT APPROPRIATELY
   Dim lineSAz As Double
   lineSAz = InverseAzimuth(theLine.startPoint, theLine.endPoint)
      Dim rotateToRadians As Double
      If linePointsLeft Then
         rotateToRadians = -Radians(lineSAz - 90#)
      Else
         rotateToRadians = -Radians(lineSAz - 270#)
      End If
   LineText.RotateAboutZ MidLine, rotateToRadians
   ActiveModelReference.AddElement LineText
   LineText.Redraw
End Sub



Public Sub DrawTether(beginPoint As Point3d, endPoint As Point3d, ByVal DrawMode As MsdDrawingMode)
'DRAW TETHER LINE
   Dim oLineStyle As LineStyle
   Set oLineStyle = ActiveDesignFile.LineStyles.Find("0")
   Dim tetherline As LineElement
   Set tetherline = CreateLineElement2(Nothing, beginPoint, endPoint)
   Set tetherline.LineStyle = oLineStyle
   tetherline.color = GetTetherColor()
   tetherline.Redraw DrawMode
End Sub



Public Function PickSub(ByVal CommandName As String, _
                         ByVal Prompt As String, _
                         ByRef pickedPoint As Point3d) As Boolean
    PickSub = False
    CadInputQueue.SendReset
    Dim myCIQ As CadInputQueue
    Set myCIQ = CadInputQueue
    CommandState.EnableAccuSnap
    ShowCommand CommandName
    ShowPrompt Prompt
    Dim NoInput As Boolean
    NoInput = True
    Dim myCIM As CadInputMessage
    Set myCIQ = CadInputQueue

    Do While NoInput = True
       Set myCIM = myCIQ.GetInput
       Select Case myCIM.InputType
          Case msdCadInputTypeReset
             ShowPrompt ""
             ShowCommand CommandName
             ShowStatus CANCELLED_BY_RESET_STRING
             NoInput = False
          Case msdCadInputTypeDataPoint
             pickedPoint = myCIM.point
             ClearCommandPromptArea
             NoInput = False
             CadInputQueue.SendReset
             PickSub = True
       End Select
    Loop
End Function



Public Function GetSelectedView() As view
'FIGURES OUT WHICH IS THE ACTIVE VIEW
  Set GetSelectedView = Nothing
  Dim oView As view
  
  
  For Each oView In ActiveDesignFile.Views
    If oView.IsSelected Then
      Set GetSelectedView = oView
      Exit Function
    End If
  Next oView

End Function



Public Function CreatePrototypeTextJust(ByVal characterSize As Double, justify As MsdTextJustification) As TextElement
   Dim somePoint As Point3d
   somePoint = Point3dFromXYZ(0, 0, 0)

   Dim myLine As LineElement
   Set myLine = CreateLineElement2(Nothing, somePoint, somePoint)
   Dim textTemplate As TextElement
   Set textTemplate = CreateTextElement1Fixed(myLine, "Template", somePoint, Matrix3dIdentity)
   Dim MyTextStyle As TextStyle
   Set MyTextStyle = textTemplate.TextStyle
   
   Set MyTextStyle.Font = ActiveSettings.TextStyle.Font
   MyTextStyle.Width = characterSize
   MyTextStyle.Height = characterSize
   MyTextStyle.Justification = justify
   Set textTemplate.TextStyle = MyTextStyle
   Set CreatePrototypeTextJust = textTemplate
End Function



Public Sub ChangeJustification(TempTextElement As TextElement, ByVal NewJustification As MsdTextJustification)
'CHANGE JUSTIFICATION
   Dim tempTextStyle As TextStyle

   Set tempTextStyle = TempTextElement.TextStyle
   tempTextStyle.Justification = NewJustification
   Set TempTextElement.TextStyle = tempTextStyle
End Sub



Public Function SplitRecord2(ByVal InputString As String, ByRef Key As String, ByRef Data As String) As Boolean
'SPLITS RECORD INTO KEY AND DATA
   Dim xSplit2 As Variant
   xSplit2 = Split(InputString, SEPARATOR_KEY2)
   If (UBound(xSplit2) - LBound(xSplit2)) < 1 Then
      Exit Function
   End If

'ASSEMBLE THE KEY PART
   Key = xSplit2(LBound(xSplit2)) & SEPARATOR_KEY2

'GET RID OF KEY PART
   xSplit2(LBound(xSplit2)) = ""

'ASSEMBLE THE DATA PART
   Data = Join(xSplit2, SEPARATOR_KEY2)

'TAKE OFF THE LEADING COLON FROM DATA
   Data = Mid(Data, 2)

'GOOD SET FLAG
   SplitRecord2 = True
End Function



Public Function PointsAreExactlySame(pnt1 As Point3d, pnt2 As Point3d) As Boolean
'RETURNS TRUE IF POINTS ARE EXACLTY SAME VALUES
'INITIALIZE FLAG
   PointsAreExactlySame = False
   If pnt1.X <> pnt2.X Then
      Exit Function
   End If
   If pnt1.Y <> pnt2.Y Then
      Exit Function
   End If
   If pnt1.z <> pnt2.z Then
      Exit Function
   End If
   PointsAreExactlySame = True
End Function



Public Sub ReadOnlyErrorMess()
   MsgBox "Read Only File"
   Beep
End Sub



Public Function BackOLE_COLOR(ByVal BackColorIsEnabled As Boolean) As OLE_COLOR
   If BackColorIsEnabled Then
      BackOLE_COLOR = backgroundWhite
   Else
      BackOLE_COLOR = backgroundGrey
   End If
End Function



Public Function Max(ByVal a As Double, ByVal b As Double) As Double
   If a < b Then
      Max = b
   Else
      Max = a
   End If
End Function



Public Function Min(ByVal a As Double, ByVal b As Double) As Double
   If a > b Then
      Min = b
   Else
      Min = a
   End If
End Function



Public Sub ClearCommandPromptArea()
   ShowCommand ""
   ShowPrompt ""
   ShowStatus ""
End Sub



Public Function CreateTempLine() As LineElement
'CREATE TEMPORARY GRAPHICS TEMPLATE LINE
   Dim somePoint As Point3d
   somePoint.X = 0
   somePoint.Y = 0
   somePoint.z = 0
   Dim myLineElem As LineElement
   Set myLineElem = CreateLineElement2(Nothing, somePoint, somePoint)

'CHANGE ITS LINESTYLE
   Dim oLineStyle As LineStyle
   Set oLineStyle = ActiveDesignFile.LineStyles.Find("0")
   Set myLineElem.LineStyle = oLineStyle
   Set CreateTempLine = myLineElem
End Function



Public Sub AddItToArray(CellElementArray() As Element, theElement As Element)
   ReDim Preserve CellElementArray(UBound(CellElementArray) + 1)
   Set CellElementArray(UBound(CellElementArray)) = theElement
End Sub



Public Function TheViewRotRadians(ByVal MyView As view) As Double
   Dim ViewAngle As Double
'CALCULATE THE ROTATION FOR THE VIEW
   If Matrix3dIsXYRotation(MyView.rotation, ViewAngle) Then
      ViewAngle = -ViewAngle
   Else
      ViewAngle = 0
   End If
   TheViewRotRadians = ViewAngle
End Function



Public Function To360(ByVal referenceAngle As Double, ByVal newAngle As Double) As Double
' if reference angle were equal to 180 then what would the newangle equal to on a 360 degree
' clockwise circle
' angles in decimal degrees
   To360 = newAngle - referenceAngle + 180#
   MakeSure360 To360
End Function



Public Function linePointsLeft(ByVal sAzFwd As Double, ByVal RotToRadians As Double) As Boolean
'DETERMINE IF LINE POINTS LEFT OF VIEW
'RotToDegrees as it is calculated by TheViewRotDegrees
'Returns True if the line points left
   If To360(180, sAzFwd + Degrees(RotToRadians)) < 180 Then
      linePointsLeft = True
   Else
      linePointsLeft = False
   End If
End Function



'*************************************************************************************************************
'****************************************************TAGS*****************************************************
Public Function GetTagSet(ByVal tagName As String) As TagSet
    Dim strName As String
    Dim oTagSets As TagSets
    
    strName = TAG_SET_NAME
    Set oTagSets = ActiveDesignFile.TagSets
    On Error Resume Next
    Set GetTagSet = oTagSets(strName)
    If GetTagSet Is Nothing Then
        Dim td As TagDefinition
        Set GetTagSet = oTagSets.Add(strName)
        Set td = GetTagSet.TagDefinitions.Add(tagName, msdTagTypeCharacter)
        td.DefaultValue = ""
        td.IsConstant = False
    End If
End Function



Public Sub TagMyElement(oElement As Element, ByVal tagName As String, ByVal TagValue As String)
'TAG THE ELEMENT
'GET TAG SET, ADD TO TAG SET IF NOT THERE
   Dim ts As TagSet
   Set ts = GetTagSet(tagName)
      
'GET THE TAG DEFS IN THE TAG SET
   Dim tagDefs As TagDefinitions
   Set tagDefs = ts.TagDefinitions
      
'LOOK FOR OUR TAG NAME
   Dim tagDef As TagDefinition
   Set tagDef = tagDefs.Find(tagName)
   
'CREATE IT IF IT DOES NOT EXIST
   If tagDef Is Nothing Then
      Set tagDef = tagDefs.Add(tagName, msdTagTypeCharacter)
      tagDef.DefaultValue = ""
      tagDef.IsConstant = False
   End If
   
'CREATE A TAG ELEMENT
   Dim eleTag As TagElement
   Set eleTag = oElement.AddTag(tagDef)

'SET ITS VALUE
   eleTag.value = TagValue
      
'MAKES SURE IT'S HIDDEN
   eleTag.IsHidden = True

'MAKE SURE IT GOT WRITTEN
   eleTag.Rewrite
End Sub



Public Function CheckForSurveyorToolsTag(theElement As Element, ByVal TheTagName As String) As Boolean
'RETURNS TRUE IF SUCCESSFUL
   Dim TheTagVal As Variant
   CheckForSurveyorToolsTag = CheckForSurveyorToolsTagAndVal(theElement, TheTagName, TheTagVal)
End Function



Public Function CheckForSurveyorToolsTagAndVal(ByVal theElement As Element, ByVal TheTagName As String, ByRef Val As Variant) As Boolean
'RETURNS TRUE IF SUCCESSFUL
'INITIALIZE FLAG
   CheckForSurveyorToolsTagAndVal = False

'CHECK IF IT HAS THE CORRECT TAGS
   If theElement.HasAnyTags Then
'GET THE TAGS
      Dim theTags() As TagElement
      theTags = theElement.GetTags()
'LOOP THROUGH THE TAGS, CHECK FOR CORRECT TAGS
      Dim i As Integer
      For i = LBound(theTags) To UBound(theTags)
         Dim aTag As TagElement
         Set aTag = theTags(i)

        'do this extra code because sometimes Microstation might change the tag names to all lower case.
         Dim SetNameString As String
         SetNameString = Trim(aTag.TagSetName)
         Dim DefinitionNameString As String
         DefinitionNameString = Trim(aTag.TagDefinitionName)
         Dim SetNameKeyString As String
         SetNameKeyString = Trim(TAG_SET_NAME)
         Dim DefNameKeyString As String
         DefNameKeyString = Trim(TheTagName)
         If LCase(SetNameString) = LCase(SetNameKeyString) And LCase(DefinitionNameString) = LCase(DefNameKeyString) Then
'CORRECT TAG FOUND
            CheckForSurveyorToolsTagAndVal = True 'set flag to found
            Val = theTags(i).value
         End If
      Next i
   End If
End Function



Public Function GetSurveyorToolsTagValue(theElement As Element, ByVal TheTagName As String, ByRef theValue As Variant) As Boolean
'RETURNS TRUE IF THERE WAS A VALUE
'INITIALIZE FLAG
   GetSurveyorToolsTagValue = False

'FIRST CHECK IF THE TAG EXISTS
   If Not CheckForSurveyorToolsTagAndVal(theElement, TheTagName, theValue) Then
      Exit Function
   End If

'SUCCESS, RETURN TRUE
   GetSurveyorToolsTagValue = True
End Function



Public Function GetTheElementID(ByVal theElement As Element, ByRef ItsID As DLong, ByRef IDstring As String) As Boolean
'TRUE IF SUCCESSFUL
'INITIALIZE FLAG
   GetTheElementID = True
   
'PREPARE FOR ERROR
   On Error GoTo errhndlr

'GET THE ELEMENT'S ID
   Dim TempID As DLong
   TempID = theElement.ID
   
'RETURN ID VALUE
   ItsID = TempID

'RETURN ID STRING
   IDstring = DLongToString(ItsID)
   Exit Function

errhndlr:
   GetTheElementID = False
End Function



Public Function IsSToolsCell(tagName As String, theElement As Element, dataString As String) As Boolean
'CHECKS TYPE AND TAGS TO SEE IF THE ELEMENT IS A DIAGRAM CELL
'RETURNS TRUE IF IT IS, AND RETURNS THE TAG VALUE AS LeaderIDString STRING

'INITIALIZE FLAG
    IsSToolsCell = False

'CHECK IF IT'S A CELL
   If theElement.IsCellElement = False Then
      Exit Function
   End If
   IsSToolsCell = IsSToolsElement(tagName, theElement, dataString)
End Function



Public Function IsSToolsElement(tagName As String, theElement As Element, dataString As String) As Boolean
'CHECKS TYPE AND TAGS TO SEE IF THE ELEMENT IS CORRECT
'RETURNS TRUE IF IT IS, AND RETURNS THE TAG VALUE AS LeaderIDString STRING

'INITIALIZE FLAG
   IsSToolsElement = False

'CHECK IF IT HAS THE CORRECT TAGS
   If theElement.HasAnyTags Then
'GET THE TAGS
      Dim theTags() As TagElement
      theTags = theElement.GetTags()
'LOOP THROUGH THE TAGS, CHECK FOR CORRECT TAGS
      Dim i As Integer
      For i = LBound(theTags) To UBound(theTags)
         Dim aTag As TagElement
         Set aTag = theTags(i)

'do this extra code because sometimes Microstation changes the tag names to all lower case.
'it is not consistent in doing this.
         Dim SetNameString As String
         SetNameString = Trim(aTag.TagSetName)
         Dim DefinitionNameString As String
         DefinitionNameString = Trim(aTag.TagDefinitionName)
         Dim SetNameKeyString As String
         SetNameKeyString = Trim(TAG_SET_NAME)
         Dim DefNameKeyString As String
         DefNameKeyString = Trim(tagName)
         If LCase(SetNameString) = LCase(SetNameKeyString) And LCase(DefinitionNameString) = LCase(DefNameKeyString) Then
         'CORRECT TAG FOUND
            dataString = aTag.value
            IsSToolsElement = True 'set flag to found
         End If
      Next i
   End If
End Function



'*************************************************************************************************************
'*******************************************COORDINATE FILES**************************************************
Public Sub CreateNewCoordinateFile(OutputFilename As String)
On Error GoTo errhnd
   Dim FFILE As Long
   FFILE = FreeFile
   Open OutputFilename For Output As #FFILE
   Close #FFILE
   Exit Sub

errhnd:
   ErrorMess Err.Number
   Err.Clear
   
End Sub



Public Function GetNewFilename(CurrentFullFileName As String, ByRef TheFilename As String, fileExtension As String, Caption As String) As Boolean
'RETURNS TRUE IF SUCCESSFUL, NEWFILENAME AS THEFILENAME
   GetNewFilename = False

'GET SUGGESTED PATH FOR REPORT FILE
   Dim NewTextFilePath As String
   NewTextFilePath = GetSuggestedPath(CurrentFullFileName)

'CREATE FILTER STRING
   Dim FilterString As String
   FilterString = "*" & fileExtension

'CALL COMMON DIALOG FOR CREATING FILE
   Dim retVal As Long
   Dim lngfhandle As Long
   Dim lngrid As Long
   Dim strFName As String
   strFName = space(255)
   retVal = mdlDialog_fileCreate(strFName, lngfhandle, lngrid, "", FilterString, NewTextFilePath, Caption)
   Select Case retVal
      Case 0 'Open
'RETURN NEW FILENAME
         strFName = Left(strFName, InStr(1, strFName, Chr(0)) - 1)
         TheFilename = strFName
         GetNewFilename = True
      Case 1 'Cancel

   End Select
End Function



Public Function GetNewCoordFilename(CurrentFullFileName As String, ByRef TheFilename As String) As Boolean
   GetNewCoordFilename = GetNewFilename(CurrentFullFileName, TheFilename, FILE_EXTENSION_COORDINATE, "Create Coordinate File")
End Function
    
    
    
Public Function GetSuggestedPath(CurrentFullFileName As String) As String
   Dim FilePath As String
   If Trim(CurrentFullFileName) = "" Then
      FilePath = "C:\output" & FILE_EXTENSION_COORDINATE
   Else
      FilePath = CurrentFullFileName
   End If
   Dim xSplit2 As Variant
   xSplit2 = Split(FilePath, "\")
   xSplit2(UBound(xSplit2)) = ""
   Dim NewTextFilePath As String
   NewTextFilePath = Join(xSplit2, "\")
   GetSuggestedPath = NewTextFilePath
End Function


Public Function OpenCoordFilename(CurrentFullFileName As String, ByRef OPENFILENAME As String) As Boolean
'RETURNS TRUE IF SUCESSFUL, NEWFILENAME AS OPENFILENAME
'INITIALIZE FLAG
   OpenCoordFilename = False

'CREATE FILTER STRING
   Dim FilterString As String
   FilterString = "*" & FILE_EXTENSION_COORDINATE

'GET SUGGETED PATH
   Dim NewTextFilePath As String
   NewTextFilePath = GetSuggestedPath(CurrentFullFileName)

'CALL COMMON DIALOG
   Dim retVal As Long
   Dim strFName As String
   strFName = space(255)
   Dim lngfhandle As Long
   Dim lngrid As Long
   retVal = mdlDialog_fileOpen(strFName, lngfhandle, lngrid, _
                               "", FilterString, NewTextFilePath, "Open Coordinate File")

   Select Case retVal
      Case 0 'OPEN
         OpenCoordFilename = True
         strFName = Left(strFName, InStr(1, strFName, Chr(0)) - 1)
         OPENFILENAME = strFName
      Case 1 'Cancel, no action

    End Select
End Function



Public Sub ErrorMess(ByVal TheError As Long)
   Select Case TheError
      Case msdErrorEndOfFile
         MsgBox "End of file"
   
      Case msdErrorAccessViolation
         MsgBox "Access Violation"
   
      Case msdErrorCannotOpenFile
         MsgBox "Cannot open file"
   
      Case Else
         MsgBox "Unknown Error"
   End Select
End Sub

Attribute VB_Name = "CompassRuleDropSnap"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit

Implements IPrimitiveCommandEvents

Private Sub IPrimitiveCommandEvents_Cleanup()
   FrmCompassRule.Show
   ClearCommandPromptArea
End Sub

Private Sub IPrimitiveCommandEvents_DataPoint(point As Point3d, ByVal view As view)
   Dim DiagramCell As CellElement
   Set DiagramCell = CreateSnapDiagram(point)
   ActiveModelReference.AddElement DiagramCell
   DiagramCell.Redraw
   CommandState.StartDefaultCommand
End Sub

Private Sub IPrimitiveCommandEvents_Dynamics(point As Point3d, ByVal view As view, ByVal DrawMode As MsdDrawingMode)
   Dim DiagramCell As CellElement
   Set DiagramCell = CreateSnapDiagram(point)
   DiagramCell.Redraw DrawMode
End Sub

Private Sub IPrimitiveCommandEvents_Keyin(ByVal Keyin As String)

End Sub

Private Sub IPrimitiveCommandEvents_Reset()
   CommandState.StartDefaultCommand
End Sub

Private Sub IPrimitiveCommandEvents_Start()
   ShowCommand COMMAND_NAME_COMPASS_RULE_2D
   ShowPrompt "Pick Place for Diagram"
   CommandState.EnableAccuSnap
   CommandState.StartDynamics
End Sub


Private Function CreateSnapDiagram(InsertionPoint As Point3d) As CellElement
   If FrmCompassRule.OppositesCheckBox.value Then
      Dim XOffset As Double
      XOffset = CDbl(FrmCompassRule.OppositeXLabel.Caption)
      Dim YOffset As Double
      YOffset = CDbl(FrmCompassRule.OppositeYLabel.Caption)
   Else
      XOffset = CDbl(FrmCompassRule.XAxisOffsetTextBox.text)
      YOffset = CDbl(FrmCompassRule.YAxisOffsetTextBox.text)
   End If
   
   Dim AbsXOffset As Double
   AbsXOffset = Abs(XOffset)
   Dim AbsYOffset As Double
   AbsYOffset = Abs(YOffset)
   Dim biggerDim As Double
   biggerDim = Max(AbsXOffset, AbsYOffset)
   Dim BoxHalfSize As Double
   BoxHalfSize = CalcBoxHalfSize(biggerDim)
   Dim BoxSize As Double
   BoxSize = BoxHalfSize + BoxHalfSize

   Dim b2 As Point3d
   b2 = InsertionPoint
   Dim b1 As Point3d
   b1 = b2
   b1.X = b1.X - BoxHalfSize
   Dim b3 As Point3d
   b3 = b2
   Dim a2 As Point3d
   b3.X = b3.X + BoxHalfSize
   a2 = b2
   a2.Y = a2.Y + BoxHalfSize
   Dim a1 As Point3d
   a1 = a2
   a1.X = a1.X - BoxHalfSize
   Dim a3 As Point3d
   a3 = a2
   a3.X = a3.X + BoxHalfSize
   Dim c2 As Point3d
   c2 = b2
   c2.Y = c2.Y - BoxHalfSize
   Dim c1 As Point3d
   c1 = c2
   c1.X = c1.X - BoxHalfSize
   Dim c3 As Point3d
   c3 = c2
   c3.X = c3.X + BoxHalfSize
   
   Dim cellArray() As Element
   ReDim cellArray(0)
   Dim textTemplate As TextElement
   Set textTemplate = FrmCompassRule.CreatePreDropDiagramTextTemplate
   
   Dim tempLine As LineElement
   Set tempLine = CreateLineElement2(textTemplate, a1, a3)
   Set cellArray(0) = tempLine
   Set tempLine = CreateLineElement2(textTemplate, a1, c1)
   AddItToArray cellArray, tempLine
   Set tempLine = CreateLineElement2(textTemplate, c1, c3)
   AddItToArray cellArray, tempLine
   Set tempLine = CreateLineElement2(textTemplate, c3, a3)
   AddItToArray cellArray, tempLine
   Set tempLine = CreateLineElement2(textTemplate, a2, c2)
   AddItToArray cellArray, tempLine
   Set tempLine = CreateLineElement2(textTemplate, b1, b3)
   AddItToArray cellArray, tempLine
   
   Dim LineStartPoint As Point3d
   LineStartPoint = InsertionPoint
   LineStartPoint.X = LineStartPoint.X + XOffset
   Dim LineEndPoint As Point3d
   LineEndPoint = LineStartPoint
   LineEndPoint.Y = LineEndPoint.Y + YOffset
   Set tempLine = CreateLineElement2(textTemplate, LineStartPoint, LineEndPoint)
   AddItToArray cellArray, tempLine
   LineStartPoint = InsertionPoint
   LineStartPoint.Y = LineStartPoint.Y + YOffset
   Set tempLine = CreateLineElement2(textTemplate, LineStartPoint, LineEndPoint)
   AddItToArray cellArray, tempLine

   Dim circleRadius As Double
   circleRadius = BoxHalfSize / 4
   Dim theCircle As EllipseElement
   Set theCircle = CreateEllipseElement2(textTemplate, LineEndPoint, circleRadius, circleRadius, Matrix3dIdentity)
   AddItToArray cellArray, theCircle
   Dim MyTextStyle As TextStyle
   Set MyTextStyle = textTemplate.TextStyle
   Dim TextSize As Double
   TextSize = BoxHalfSize / 3.5
   MyTextStyle.Width = TextSize
   MyTextStyle.Height = TextSize
   Set textTemplate.TextStyle = MyTextStyle
   Dim PlaceTextPoint As Point3d
   PlaceTextPoint = InsertionPoint
   Dim TextOffset As Double
   TextOffset = BoxHalfSize + (TextSize * 0.8)
   PlaceTextPoint.Y = PlaceTextPoint.Y + TextOffset
   
   Dim ArrowDirection As Boolean
   ArrowDirection = True
   Dim Arrow1InsertPoint As Point3d
   Arrow1InsertPoint = InsertionPoint
   Arrow1InsertPoint.Y = Arrow1InsertPoint.Y + TextOffset
   Dim Arrow2InsertPoint As Point3d
   Arrow2InsertPoint = InsertionPoint
   Arrow2InsertPoint.Y = Arrow2InsertPoint.Y - TextOffset
   Arrow1InsertPoint.X = Arrow1InsertPoint.X - BoxHalfSize
   If XOffset >= 0 Then
      PlaceTextPoint.X = PlaceTextPoint.X - BoxHalfSize
      ArrowDirection = False
      Arrow1InsertPoint.X = InsertionPoint.X
   End If
   Arrow2InsertPoint.X = Arrow1InsertPoint.X
   
   Dim Arrow1 As CellElement
   Set Arrow1 = MyCreateArrowCell(Arrow1InsertPoint, TextSize, ArrowDirection, textTemplate)
   AddItToArray cellArray, Arrow1
   Dim Arrow2 As CellElement
   Set Arrow2 = MyCreateArrowCell(Arrow2InsertPoint, TextSize, ArrowDirection, textTemplate)
   AddItToArray cellArray, Arrow2
   
   Dim TheTextElement As TextElement
   Set TheTextElement = CreateTextElement1(textTemplate, FormatNumber(AbsXOffset, 2), PlaceTextPoint, Matrix3dIdentity)
   AddItToArray cellArray, TheTextElement
   PlaceTextPoint.Y = InsertionPoint.Y - TextOffset
   Set TheTextElement = CreateTextElement1(textTemplate, FormatNumber(AbsXOffset, 2), PlaceTextPoint, Matrix3dIdentity)
   AddItToArray cellArray, TheTextElement
   PlaceTextPoint = InsertionPoint
   PlaceTextPoint.X = PlaceTextPoint.X + TextOffset
   
   Arrow1InsertPoint = InsertionPoint
   Arrow2InsertPoint = InsertionPoint
   Arrow1InsertPoint.X = Arrow1InsertPoint.X - TextOffset
   Arrow2InsertPoint.X = Arrow2InsertPoint.X + TextOffset
   Arrow1InsertPoint.Y = Arrow1InsertPoint.Y + -BoxHalfSize
   Arrow2InsertPoint.Y = Arrow1InsertPoint.Y
   Set Arrow1 = MyCreateArrowCell(Arrow1InsertPoint, TextSize, ArrowDirection, textTemplate)
   Set Arrow2 = MyCreateArrowCell(Arrow2InsertPoint, TextSize, ArrowDirection, textTemplate)
   ArrowDirection = True
   If YOffset >= 0 Then
      PlaceTextPoint.Y = PlaceTextPoint.Y - BoxHalfSize
      Arrow1InsertPoint.Y = InsertionPoint.Y
      Arrow2InsertPoint.Y = Arrow1InsertPoint.Y
      ArrowDirection = False
   End If
   Set Arrow1 = MyCreateArrowCell(Arrow1InsertPoint, TextSize, ArrowDirection, textTemplate)
   Set Arrow2 = MyCreateArrowCell(Arrow2InsertPoint, TextSize, ArrowDirection, textTemplate)
   Arrow1.RotateAboutZ Arrow1InsertPoint, Pi / 2
   Arrow2.RotateAboutZ Arrow2InsertPoint, Pi / 2
   AddItToArray cellArray, Arrow1
   AddItToArray cellArray, Arrow2
   Set TheTextElement = CreateTextElement1(textTemplate, FormatNumber(AbsYOffset, 2), PlaceTextPoint, Matrix3dIdentity)
   TheTextElement.RotateAboutZ PlaceTextPoint, Pi / 2
   AddItToArray cellArray, TheTextElement
   PlaceTextPoint.X = InsertionPoint.X - TextOffset
   Set TheTextElement = CreateTextElement1(textTemplate, FormatNumber(AbsYOffset, 2), PlaceTextPoint, Matrix3dIdentity)
   TheTextElement.RotateAboutZ PlaceTextPoint, Pi / 2
   AddItToArray cellArray, TheTextElement
   Dim AngleString As String
   AngleString = FrmCompassRule.DropAzimuthTextBox.text
   PlaceTextPoint = InsertionPoint
   PlaceTextPoint.X = PlaceTextPoint.X - BoxHalfSize
   PlaceTextPoint.Y = PlaceTextPoint.Y - (TextOffset + TextSize * 1.4)

   Dim angleInDegrees As Double
   If Not AngleStringToDegree(AngleString, angleInDegrees) Then
      angleInDegrees = 0
   End If
'   AngleString = AzInToString2(AngleInDegrees, 0, FORMAT_DMS_LEAVEOFF_00, 0)
    AngleString = DegreesToAngleString(angleInDegrees, 4, STYLE_ANGLE_NO_00_SEC + STYLE_ANGLE_DEG_LEAD + STYLE_ANGLE_CARET + STYLE_ANGLE_NO_00_SEC)
   Set TheTextElement = CreateTextElement1(textTemplate, AngleString, PlaceTextPoint, Matrix3dIdentity)
   AddItToArray cellArray, TheTextElement

   Arrow1InsertPoint = PlaceTextPoint
   Dim TextElSize As Point2d
   TheTextElement.GetTotalTextSize TextElSize.X, TextElSize.Y
   Arrow1InsertPoint.X = Arrow1InsertPoint.X + TextElSize.X + TextSize
   Set Arrow1 = MyCreateArrowCell(Arrow1InsertPoint, TextSize, False, textTemplate)
   AddItToArray cellArray, Arrow1
   Set CreateSnapDiagram = CreateCellElement1(vbNullString, cellArray, InsertionPoint)
   CreateSnapDiagram.RotateAboutZ InsertionPoint, Radians(270 - angleInDegrees)
End Function

Private Function CalcBoxHalfSize(ByVal Extents As Double) As Double
'PAD IT A LITTLE SO NOT TO LAND ON THE EDGE OF THE BOX
   Extents = Extents * 1.25
   Dim BoxHalfSize As Double
   BoxHalfSize = 1
   Do While BoxHalfSize < Extents
      BoxHalfSize = BoxHalfSize + BoxHalfSize
   Loop
   CalcBoxHalfSize = BoxHalfSize
End Function

Attribute VB_Name = "CompassRuleFileCode"
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit


Public Type AdjTabData
   ApplyChkBox As Boolean
   AngErrChkBox As Boolean
   AngErrTxtBox As String
   SinglePathOption As Boolean
   TwoPathOption As Boolean
   TwoPathObsIndex As Long
   TwoPathNorthing As String
   TwoPathEasting As String
   RerunOption As Boolean
   OneSecondOption As Boolean
   TenthSecondOption As Boolean
   hundredthFootOption As Boolean
   ThousandthFootOption As Boolean
   HoldCoordinateOption As Boolean
   TransformationChkBox As Boolean
   TranslationIndex As Long
   TranslationNorthing As String
   TranslationEasting As String
   RotationChkBox As Boolean
   RotationTxtBox As String
End Type

Private Const Compass_Rule_Format_Number    As String = "5"
Private Const Compass_Rule_File_Header      As String = "CRA"



'Private MoveToObsListIndex As Long 'STORE INDEX UNTIL FINISHED LOADING FILE
'Private TwoPointObsListIndex As Long 'STORE INDEX UNTIL FINISHED LOADING FILE

'FILE FORMAT
'LINE 1  HEADER "CRA"
'LINE 2  FORMAT NUMBER "4"
'LINE 3  UNIQUE FILE IDENTIFIER STRING FOR TAGS
'LINE 4  Z VALUE 4 DECIMAL PLACES
'LINE 5  NORTHING VALUE 4 DECIMAL PLACES
'LINE 6  EASTING VALUE 4 DECIMAL PLACES
'LINE 7  FIRST BACK SIGHT AZIMUTH STRING
'LINE 8+ ALL THE RECORDS THAT DEFINE YOUR TRAVERSE AND ADJUSTMENT AND CLOSURE
'        TRAVERSE RECORD FOLLOWED BY ALL THE SIDE SHOT RECORDS TAKEN FROM THAT TRAVERSE
'        THEN NEXT TRAVERSE RECORD ...
'RECORDS PERTAINING TO ADJUSTMENT CAN OCCUR ANY LINE AFTER LINE 7
'
'
'
' Side Shot or Traverse:Point name, BS angle, FS angle, HD,Description
'
Public Const KEY_COMPASS_RULE_START_OBS_NAME_DESC   As String = "STND:"
Public Const KEY_COMPASS_RULE_SIDE_SHOT             As String = "SIDE:"
Public Const KEY_COMPASS_RULE_TRAV                  As String = "TRAV:"
Public Const KEY_COMPASS_RULE_CLOSE_TYPE            As String = "CTYP:"
Public Const OPT_COMPASS_RULE_CTYP_NONE             As String = "NONE"
Public Const OPT_COMPASS_RULE_CTYP_BEGIN            As String = "BEGIN"
Public Const OPT_COMPASS_RULE_CTYP_2PT              As String = "POINT"
Public Const KEY_COMPASS_RULE_CLOSE_NORTH           As String = "CNORT:"
Public Const KEY_COMPASS_RULE_CLOSE_EAST            As String = "CEAST:"
Public Const KEY_COMPASS_RULE_CLOSE_OBS             As String = "COBS:"
Public Const OPT_COMPASS_RULE_CLOSING_OBS_LAST_FS   As String = "LASTFS"
Public Const OPT_COMPASS_RULE_CLOSING_OBS_LAST_OC   As String = "LASTOC"
Public Const KEY_COMPASS_RULE_CLOSE_OBS_NAME_DESC   As String = "OBSND:"
Public Const KEY_COMPASS_RULE_CLOSE_OBS_NAME        As String = "OBSN:"
Public Const KEY_COMPASS_RULE_CLOSE_OBS_DESC        As String = "OBSD:"
Public Const KEY_COMPASS_RULE_CLOSE_OBS_EL          As String = "OBSE:"
Public Const KEY_COMPASS_RULE_CLOSE_OBS_INCLUDE_EL  As String = "OBSI:"
Public Const KEY_COMPASS_RULE_CLOSE_OBS_PLOT_EL     As String = "OBSP:"
Public Const KEY_COMPASS_RULE_SOL_RULES_COURSES     As String = "SRULC:"
Public Const OPT_COMPASS_RULE_COURSE_SOLUTION_PREC  As String = "PREC"
Public Const OPT_COMPASS_RULE_COURSE_SOLUTION_INV   As String = "INV"
Public Const KEY_COMPASS_RULE_SOL_COURSE_PREC       As String = "RPREC:"
Public Const OPT_COMPASS_RULE_COURSE_PRECISION_SECOND         As String = "1SEC"
Public Const OPT_COMPASS_RULE_COURSE_PRECISION_TENTH_SEC      As String = "0.1SEC"
Public Const OPT_COMPASS_RULE_COURSE_PRECISION_100TH_SEC      As String = "0.01SEC"
Public Const KEY_COMPASS_RULE_SOL_COURSE_DIST_PREC            As String = "RDPREC:"
Public Const OPT_COMPASS_RULE_COURSE_PRECISION_HUNDREDTH_FT   As String = "0.01FT"
Public Const OPT_COMPASS_RULE_COURSE_PRECISION_THOUSANDTH_FT  As String = "0.001FT"
Public Const KEY_COMPASS_RULE_POINT_TYPE            As String = "CRTYP:"
Public Const OPT_COMPASS_RULE_ONE_POINT_TYPE        As String = "ONEPT"
Public Const OPT_COMPASS_RULE_TWO_POINT_TYPE        As String = "TWOPT"
Public Const KEY_COMPASS_RULE_APPLY                 As String = "APPLY:"
Public Const KEY_COMPASS_RULE_TWO_POINT_NORTH       As String = "2PNORT:"
Public Const KEY_COMPASS_RULE_TWO_POINT_EAST        As String = "2PEAST:"
Public Const KEY_COMPASS_RULE_TWO_POINT_OBS         As String = "2POBS:"
Public Const KEY_COMPASS_RULE_MOVE_ALL              As String = "MOVALL:"
Public Const KEY_COMPASS_RULE_MOVE_TO_NORTH         As String = "MNORT:"
Public Const KEY_COMPASS_RULE_MOVE_TO_EAST          As String = "MEAST:"
Public Const KEY_COMPASS_RULE_MOVE_TO_OBS           As String = "MOBS:"
Public Const KEY_COMPASS_RULE_ROTATE                As String = "ROTATE:"
Public Const KEY_COMPASS_RULE_ROTATION              As String = "ROTATION:"
Public Const KEY_COMPASS_RULE_ANGULAR_ADJ_CHECK     As String = "ANGADJCHK:"
Public Const KEY_COMPASS_RULE_ANGULAR_ADJ           As String = "ANGADJ:"
Public Const KEY_COMPASS_RULE_NO_DROP               As String = "NODROP:"
Public Const KEY_COMPASS_RULE_DATE                  As String = "DATE:"
Public Const KEY_COMPASS_RULE_PROJ                  As String = "PROJ:"
Public Const KEY_COMPASS_RULE_ORIGIN                As String = "ORIGIN:"
Public Const KEY_COMPASS_RULE_AZIMUTH               As String = "AZIMUTH:"
Public Const KEY_COMPASS_RULE_FIELDBOOK             As String = "FB:"
Public Const KEY_COMPASS_RULE_NOTES                 As String = "NOTES:"
Public Const KEY_COMPASS_RULE_DROP                  As String = "DROP:"
Public Const KEY_COMPASS_RULE_ELEVATION             As String = "ELEV:"
Public Const KEY_SIGNAL                             As String = "SIGNAL:"
Public Const OPT_PRELIMIARY_ADJ                     As String = "PRELIMADJ"
Public Const OPT_FINAL_ADJ                          As String = "FINALADJ"
Public Const KEY_ADJUSTMENT_PHASE                   As String = "PHASE:"
Public Const SEPARATOR_COMPASS_RULE_DROP            As String = ";"
Public Const KEY_COMPASS_RULE_DIAGRAM_AZIMUTH       As String = "DIAGAZ:"

Public Const PLOT_EL_TRUE                           As String = "T"
Public Const PLOT_EL_FALSE                          As String = "F"

Public Const START_COORD_PREC                       As Long = 4
Public Const ANGLUAR_ADJ_LIMIT                      As Double = 10 'TEN DEGREES

Private Const DEFAULT_ELEVATION_STRING As String = "0.00"

Private TraverseHasBeenEnteredFlag As Boolean

Private Sub SetTraverseHasBeenEnteredFlag()
   TraverseHasBeenEnteredFlag = True
End Sub

Private Sub ClearTraverseHasBeenEnteredFlag()
   TraverseHasBeenEnteredFlag = False
End Sub

Private Function TraverseHasBeenEntered() As Boolean
   TraverseHasBeenEntered = TraverseHasBeenEnteredFlag
End Function

Private Function ReformatDistEntry(ByVal EnteredDistanceText As String, _
                                    ByRef DistanceString As String, _
                                    ByVal UseComma As Boolean) As Boolean
'SET FLAG
   ReformatDistEntry = False
   
'EXIT IF NOT A NUMBER
   If Not IsNumeric(EnteredDistanceText) Then
      Exit Function
   End If

'GET ITS PRECISION
   Dim precision As Long
   precision = StrPrec(EnteredDistanceText)

'CONVERT IT TO A DOUBLE
   Dim TempDouble As Double
   TempDouble = Round(CDbl(EnteredDistanceText), Min(MAX_PRECISION_DISTANCE, precision))

'EXIT IF LESS THAN/EQUAL TO ZERO
   If TempDouble <= 0 Then
      Exit Function
   End If

'RETURN THE NEW DISTANCE STRING
   DistanceString = FormatNumber(TempDouble, precision, vbTrue, vbFalse, UseComma)

'FLAG GOOD ENTRY
   ReformatDistEntry = True
End Function

Private Function FormatToWriteNorth(NorthingString As String) As String
   Dim scaler As Double
   Dim origPrec As Long
   If Not IsNorthingString(NorthingString, scaler, origPrec) Then
'SHOULD NEVER GET HERE, CREATE ERROR IF IT DOES
      Err.Raise ERROR_NUM_528
   End If
   FormatToWriteNorth = FormatNumber(scaler, origPrec, vbTrue, vbFalse, vbFalse)
End Function

Private Function FormatToWriteEast(EastingString As String) As String
   Dim scaler As Double
   Dim origPrec As Long
   If Not IsEastingString(EastingString, scaler, origPrec) Then
'SHOULD NEVER GET HERE, CREATE ERROR IF IT DOES
      Err.Raise ERROR_NUM_529
   End If
   FormatToWriteEast = FormatNumber(scaler, origPrec, vbTrue, vbFalse, vbFalse)
End Function



Public Function TrueFalseString(ByVal TrueFalse As Boolean) As String
   If TrueFalse Then
      TrueFalseString = OPTION_TRUE
   Else
      TrueFalseString = OPTION_FALSE
   End If
End Function


Public Function WriteCompassRuleFile(filename As String, CRForm As FrmCompassRule) As Boolean
'INITIALIZE FLAG
   WriteCompassRuleFile = False

'JUMP ON ERROR
   On Error GoTo errhnd

'OPEN FILE
   Dim FFILE As Long
   FFILE = FreeFile
   Open filename For Output As #FFILE

'WRITE HEADER
      Print #FFILE, Compass_Rule_File_Header

'WRITE FILE FORMAT VERSION NUMBER
      Print #FFILE, Compass_Rule_Format_Number

'WRITE FILE ID
      Print #FFILE, CRForm.IDstring

'WRITE START POINT Z
      Print #FFILE, CRForm.StartPointZString

'WRITE START POINT NORTHING
      Print #FFILE, FormatToWriteNorth(CRForm.TextNorthing.text)

'WRITE START POINT EASTING
      Print #FFILE, FormatToWriteEast(CRForm.TextEasting.text)

'WRITE FIRST BS AZIMUTH
      Print #FFILE, CRForm.FirstBSAzTextBox.text
      
'WRITE CLOSURE TYPE
      Print #FFILE, KEY_COMPASS_RULE_CLOSE_TYPE & ClosureTypeString(CRForm)

'WRITE CLOSURE NORTHING
      Print #FFILE, KEY_COMPASS_RULE_CLOSE_NORTH & FormatToWriteNorth(CRForm.CloseNorthTextBox.text)

'WRITE CLOSURE EASTING
      Print #FFILE, KEY_COMPASS_RULE_CLOSE_EAST & FormatToWriteEast(CRForm.CloseEastTextBox.text)

'WRITE CLOSING POINT OBSERVATION
      Print #FFILE, KEY_COMPASS_RULE_CLOSE_OBS & ClosingPointObsString(CRForm)

'WRITE CLOSING POINT NAME AND DESCRIPTION CHECK BOX STATE
      Print #FFILE, KEY_COMPASS_RULE_CLOSE_OBS_NAME_DESC & TrueFalseString(CRForm.NameAndDescCheckBox.value)

'WRITE CLOSING POINT INCLUDE ELEVATION CHECK BOX STATE
      Print #FFILE, KEY_COMPASS_RULE_CLOSE_OBS_INCLUDE_EL & TrueFalseString(CRForm.IncludeElCheckBox.value)

'WRITE STARTING POINT NAME AND DESCRIPTION CHECK BOX STATE
      Print #FFILE, KEY_COMPASS_RULE_START_OBS_NAME_DESC & TrueFalseString(CRForm.DrawStartCheckBox.value)

'WRITE CLOSING POINT NAME
      Print #FFILE, KEY_COMPASS_RULE_CLOSE_OBS_NAME & CRForm.CloseNameTextBox.text

'WRITE CLOSING POINT DESCRIPTION
      Print #FFILE, KEY_COMPASS_RULE_CLOSE_OBS_DESC & CRForm.CloseDescTextBox.text

'WRITE CLOSING POINT ELEVATION TEXT BOX
      Print #FFILE, KEY_COMPASS_RULE_CLOSE_OBS_EL & CRForm.ElevationTextBox.text

'WRITE NO DROP OPTION
      Print #FFILE, KEY_COMPASS_RULE_NO_DROP & TrueFalseString(False)

'WRITE DROP DIAGRAM AZIMUTH
      Print #FFILE, KEY_COMPASS_RULE_DIAGRAM_AZIMUTH & CRForm.DropAzimuthTextBox.text

'MAKE SURE BOTH TABS ARE STORED
      If CRForm.PreliminaryOption.value = True Then
         CRForm.StoPrelimTab
         Print #FFILE, KEY_ADJUSTMENT_PHASE & OPT_PRELIMIARY_ADJ
      Else
         CRForm.StoFinalTab
         Print #FFILE, KEY_ADJUSTMENT_PHASE & OPT_FINAL_ADJ
      End If

'WRITE PRELIMINARY TAB FIRST
      WriteAdjTab FFILE, CRForm.GetPrelimData()

'WRITE FINAL ADJSUTMENT TAB
      Print #FFILE, KEY_SIGNAL & OPT_FINAL_ADJ
      WriteAdjTab FFILE, CRForm.GetFinalData()

'WRITE DATE FIELD
      Print #FFILE, KEY_COMPASS_RULE_DATE & CRForm.DateTextBox.text

'WRITE PROJECT FIELD
      Print #FFILE, KEY_COMPASS_RULE_PROJ & CRForm.ProjectTextBox.text

'WRITE ORIGIN FIELD
      Print #FFILE, KEY_COMPASS_RULE_ORIGIN & CRForm.OriginTextBox.text

'WRITE AZIMUTH FIELD
      Print #FFILE, KEY_COMPASS_RULE_AZIMUTH & CRForm.AzimuthTextBox.text

'WRITE FIELDBOOK FIELD
      Print #FFILE, KEY_COMPASS_RULE_FIELDBOOK & CRForm.FieldBookTextBox.text

'WRITE NOTES FIELD
      Print #FFILE, KEY_COMPASS_RULE_NOTES & CRForm.NotesTextBox.text

'WRITE RAW LIST BOX
      Dim topIndex As Long  'TOP LIMIT OF LIST BOX
      topIndex = CRForm.RawListTopIndex()
      Dim index As Long     'LOOP INDEX
      index = 0             'INITALIZE TO STARTING INDEX
      Do While index <= topIndex
         Dim shotType As String
         Dim pointName As String
         Dim bSString As String
         Dim fSString As String
         Dim hDString As String
         Dim descriptionString As String
         Dim showDrop As Boolean
         Dim elevationString As String
         CRForm.GetRawListLine index, shotType, pointName, bSString, fSString, hDString, descriptionString, showDrop, elevationString
         Dim ReformattedDistString As String
         ReformattedDistString = Replace(hDString, ",", "")
         Print #FFILE, shotType & pointName & "," & bSString & "," & fSString & "," & ReformattedDistString & "," & descriptionString
         
         If shotType = KEY_COMPASS_RULE_TRAV Then
            Print #FFILE, KEY_COMPASS_RULE_ELEVATION & elevationString
         End If
         
         If shotType = KEY_COMPASS_RULE_SIDE_SHOT Then
            Dim RecordNorth As String
            Dim RecordEast As String
            Dim DiagramNorth As String
            Dim DiagramEast As String
            
            CRForm.GetDropsListLine index, RecordNorth, RecordEast, DiagramNorth, DiagramEast
            Dim DropString As String
            DropString = KEY_COMPASS_RULE_DROP & TrueFalseString(showDrop) & SEPARATOR_COMPASS_RULE_DROP
            DropString = DropString & RecordNorth & SEPARATOR_COMPASS_RULE_DROP & RecordEast & SEPARATOR_COMPASS_RULE_DROP & DiagramNorth & SEPARATOR_COMPASS_RULE_DROP & DiagramEast
                        
            Print #FFILE, DropString
         End If
         index = index + 1
      Loop

'ERROR HANDLING'CLOSE FILE
   Close #FFILE

'SIGNAL SUCCESS
   WriteCompassRuleFile = True

'JUMP PAST ERROR CODE
   Exit Function

'ERROR HANDLING
errhnd:
   ErrorMess Err.Number
   Err.Clear
End Function


Private Sub WriteAdjTab(ByVal FFILE As Long, TabData As AdjTabData)
'WRITE SOLUTION RULES TYPE
      Print #FFILE, KEY_COMPASS_RULE_SOL_RULES_COURSES & SolutionRulesString(TabData)

'WRITE SOLUTION RULES COURSE ANGLE PRECISION
      Print #FFILE, KEY_COMPASS_RULE_SOL_COURSE_PREC & SolutionPrecisionString(TabData)
      
'WRITE SOLUTION RULES COURSE DISTANCE PRECISION
      Print #FFILE, KEY_COMPASS_RULE_SOL_COURSE_DIST_PREC & SolutionDistPrecisionString(TabData)

'WRITE ONE POINT TYPE OR TWO POINT TYPE
      Print #FFILE, KEY_COMPASS_RULE_POINT_TYPE & CompassRuleTypeString(TabData)

'WRITE APPLY STATE
      Print #FFILE, KEY_COMPASS_RULE_APPLY & TrueFalseString(TabData.ApplyChkBox)

'WRITE TWO POINT NORTHING
      Print #FFILE, KEY_COMPASS_RULE_TWO_POINT_NORTH & FormatToWriteNorth(TabData.TwoPathNorthing)

'WRITE TWO POINT EASTING
      Print #FFILE, KEY_COMPASS_RULE_TWO_POINT_EAST & FormatToWriteEast(TabData.TwoPathEasting)

'WRITE TWO POINT OBSERVATION
      Print #FFILE, KEY_COMPASS_RULE_TWO_POINT_OBS & TabData.TwoPathObsIndex

'WRITE MOVE ALL STATE
      Print #FFILE, KEY_COMPASS_RULE_MOVE_ALL & TrueFalseString(TabData.TransformationChkBox)

'WRITE MOVE TO NORTHING
      Print #FFILE, KEY_COMPASS_RULE_MOVE_TO_NORTH & FormatToWriteNorth(TabData.TranslationNorthing)

'WRITE MOVE TO EASTING
      Print #FFILE, KEY_COMPASS_RULE_MOVE_TO_EAST & FormatToWriteEast(TabData.TranslationEasting)

'WRITE MOVE TO OBSERVATION
      Print #FFILE, KEY_COMPASS_RULE_MOVE_TO_OBS & TabData.TranslationIndex

'WRITE ROTATION CHECK BOX
      Print #FFILE, KEY_COMPASS_RULE_ROTATE & TrueFalseString(TabData.RotationChkBox)

'WRITE ROTATION TEXT BOX
      Print #FFILE, KEY_COMPASS_RULE_ROTATION & TabData.RotationTxtBox

'WRITE ANGULAR ADJUSTMENT STATE
      Print #FFILE, KEY_COMPASS_RULE_ANGULAR_ADJ_CHECK & TrueFalseString(TabData.AngErrChkBox)
      
'WRITE ANGULAR ADJUSTMENT VALUE
      Print #FFILE, KEY_COMPASS_RULE_ANGULAR_ADJ & TabData.AngErrTxtBox
End Sub




Private Function CompassRuleTypeString(AdjTab As AdjTabData) As String
   If AdjTab.SinglePathOption Then
      CompassRuleTypeString = OPT_COMPASS_RULE_ONE_POINT_TYPE
   Else
      CompassRuleTypeString = OPT_COMPASS_RULE_TWO_POINT_TYPE
   End If
End Function

Private Function SolutionPrecisionString(AdjTab As AdjTabData) As String
   If AdjTab.OneSecondOption Then
      SolutionPrecisionString = OPT_COMPASS_RULE_COURSE_PRECISION_SECOND
   Else
      SolutionPrecisionString = OPT_COMPASS_RULE_COURSE_PRECISION_TENTH_SEC
   End If
End Function

Private Function SolutionDistPrecisionString(AdjTab As AdjTabData) As String
   If AdjTab.hundredthFootOption Then
      SolutionDistPrecisionString = OPT_COMPASS_RULE_COURSE_PRECISION_HUNDREDTH_FT
   Else
      SolutionDistPrecisionString = OPT_COMPASS_RULE_COURSE_PRECISION_THOUSANDTH_FT
   End If
End Function

Private Function SolutionRulesString(AdjTab As AdjTabData) As String
   If AdjTab.RerunOption Then
      SolutionRulesString = OPT_COMPASS_RULE_COURSE_SOLUTION_PREC
   Else
      SolutionRulesString = OPT_COMPASS_RULE_COURSE_SOLUTION_INV
   End If
End Function






Private Function ClosureTypeString(CRForm As FrmCompassRule) As String
    If CRForm.NoneYetOption.value = True Then
       ClosureTypeString = OPT_COMPASS_RULE_CTYP_NONE
    ElseIf CRForm.ToBeginningOption.value = True Then
       ClosureTypeString = OPT_COMPASS_RULE_CTYP_BEGIN
    Else
       ClosureTypeString = OPT_COMPASS_RULE_CTYP_2PT
    End If
End Function

Private Function ClosingPointObsString(CRForm As FrmCompassRule) As String
    If CRForm.LastForesightOption.value = True Then
       ClosingPointObsString = OPT_COMPASS_RULE_CLOSING_OBS_LAST_FS
    Else
       ClosingPointObsString = OPT_COMPASS_RULE_CLOSING_OBS_LAST_OC
    End If
End Function

'**************************************LOAD FILE***************************************
Public Function LoadCompassRuleFile(filename As String, CRForm As FrmCompassRule) As Boolean
'RETURNS TRUE IF SUCCESSFUL

'INITIALIZE FLAG
   LoadCompassRuleFile = True
   ClearTraverseHasBeenEnteredFlag

'INITIALIZE DEFAULT INDICES
   Dim MoveToObsListIndex As Long
   MoveToObsListIndex = -1 'GLOBAL VARIABLE, MODULE WIDE
   Dim TwoPointObsListIndex As Long
   TwoPointObsListIndex = -1 'GLOBAL VARIABLE, MODULE WIDE

'JUMP ON ERROR
   On Error GoTo errhnd

'OPEN FILE
   Dim FFILE As Long
   FFILE = FreeFile
   Open filename For Input As #FFILE

'CLEAR LIST BOXES
   CRForm.RawEntriesListBox.Clear
   CRForm.TraversesListBox.Clear
   CRForm.SideshotsListBox.Clear
   CRForm.DropsListBox.Clear

'GET RID OF OLD INFO
   CRForm.ClearAverageDrop

'INITIALIZE FORM FIELDS
   CRForm.InitNewCRForm
   
'SET DRAW SYMBOL & LABEL CHECK BOX TO TRUE IN CASE PRE FORMAT 4 FILE IS LOADED
   CRForm.DrawStartCheckBox.value = True

'SET DEFAULT POINT ELEVATION TEXT BOX IN CASE PRE FORMAT 5 FILE IS LOADED
   CRForm.ElevationTextBox.text = DEFAULT_ELEVATION_STRING

'CREATE VARIABLE TO STORE ADJUSTMENT TAB ALUES
   Dim TabData As AdjTabData
   TabData = FrmCompassRule.GetPrelimData()

'READ FILE ONE LINE AT A TIME
   Dim LineNum As Long
   LineNum = 1
   Dim TextLine As String
   Do While EOF(FFILE) = False
      Line Input #FFILE, TextLine
      Select Case LineNum
         Case 1 'HEADER
            If StrComp(TextLine, Compass_Rule_File_Header, vbBinaryCompare) <> 0 Then
               LoadCompassRuleFile = False
               MsgBox "bad header"
               Exit Do
            End If
         
         Case 2 'FORMAT NUMBER
            If Not IsNumeric(TextLine) Then
               LoadCompassRuleFile = False
               MsgBox "bad format number"
               Exit Do
            End If
            Dim FormatNumber As Double
            FormatNumber = CDbl(TextLine)
            If FormatNumber > Compass_Rule_Format_Number Then
               LoadCompassRuleFile = False
               MsgBox "Format version too high."
               Exit Do
            End If

         Case 3 'FILE ID STRING
            TextLine = Trim(TextLine)
            If TextLine = "" Then
               LoadCompassRuleFile = False
               MsgBox "no File ID"
               Exit Do
            End If
            CRForm.IDstring = TextLine

         Case 4 'Z VALUE
            If Not IsNumeric(TextLine) Then
               LoadCompassRuleFile = False
               MsgBox "bad Z"
               Exit Do
            End If
            CRForm.TextElevation.text = TextLine
            CRForm.TextElevationUpdate

         Case 5 'NORTHING VALUE
            Dim theScaler As Double
            Dim origPrec As Long
            If Not IsNorthingString(TextLine, theScaler, origPrec) Then
               LoadCompassRuleFile = False
               MsgBox "bad Northing"
               Exit Do
            End If
            CRForm.TextNorthing.text = TextLine
            CRForm.TextNorthingUpdate

         Case 6 'EASTING VALUE
            If Not IsEastingString(TextLine, theScaler, origPrec) Then
               LoadCompassRuleFile = False
               MsgBox "bad Easting"
               Exit Do
            End If
            CRForm.TextEasting.text = TextLine
            CRForm.TextEastingUpdate

         Case 7 'BACK SIGHT AZIMUTH STRING
            Dim degPart As Long
            Dim minPart As Long
            Dim secPart As Double
            If Not IsDeltaString(TextLine, origPrec, degPart, minPart, secPart) Then
               LoadCompassRuleFile = False
               MsgBox "bad back az"
               Exit Do
            End If
            CRForm.FirstBSAzTextBox.text = TextLine
            CRForm.FirstBSAzTextBoxSub

         Case Else 'ALL OTHER RECORDS
            Dim RecordTypeString As String
            Dim RecordDataString As String
            If SplitRecord2(TextLine, RecordTypeString, RecordDataString) Then
               LoadCompassRuleFile = DispenseRecord(RecordTypeString, RecordDataString, CRForm, TabData)
               If Not LoadCompassRuleFile Then
                   Exit Do
               End If
            Else
               LoadCompassRuleFile = False
               Exit Do
            End If
      End Select
      LineNum = LineNum + 1
   Loop

'CLOSE FILE
   Close #FFILE

'SAVE FINAL TAB DATA
   CRForm.SetFinalData TabData
   
'IF FORMAT NUMBER BELOW 2, STORE PRELIMINARY ALSO
   If FormatNumber < 2 Then
      CRForm.SetPrelimData TabData
   End If

'LOAD CORRECT ADJUSTMENT PHASE
   CRForm.InitialAdjTabLoad

'UPDATE BACKUP VALUES
   CRForm.UpdateOldVals

'JUMP PAST ERROR CODE
   Exit Function

'ERROR HANDLING
errhnd:
   LoadCompassRuleFile = False
   ErrorMess Err.Number
   Err.Clear

End Function


Private Function DispenseRecord(RecordTypeString As String, _
                                RecordDataString As String, _
                                CRForm As FrmCompassRule, _
                                TabData As AdjTabData) As Boolean
'RETURNS TRUE IF SUCCESSFUL
'INITIALIZE FLAG
   DispenseRecord = False
   
'HANDLE DEFINED RECORD TYPES
   Select Case RecordTypeString
      Case KEY_COMPASS_RULE_SIDE_SHOT
         If Not DispenseSideShot(RecordDataString, CRForm) Then
            MsgBox "SIDE_SHOT"
            Exit Function
         End If
    
      Case KEY_COMPASS_RULE_DROP
         If Not DispenseDrop(RecordDataString, CRForm) Then
            MsgBox "DROP"
            Exit Function
         End If
    
      Case KEY_COMPASS_RULE_TRAV
         If Not DispenseTraverse(RecordDataString, CRForm) Then
            MsgBox "TRAV"
            Exit Function
         End If
   
      Case KEY_COMPASS_RULE_ELEVATION
         If Not DispenseElevation(RecordDataString, CRForm) Then
            MsgBox "ELEVATION"
            Exit Function
         End If
   
      Case KEY_COMPASS_RULE_CLOSE_TYPE
         If Not DispenseClosuretype(RecordDataString, CRForm) Then
            MsgBox "CLOSE_TYPE"
            Exit Function
         End If

      Case KEY_COMPASS_RULE_CLOSE_NORTH
         If Not DispenseClosureNorth(RecordDataString, CRForm) Then
            MsgBox "CLOSE_NORTH"
            Exit Function
         End If
   
      Case KEY_COMPASS_RULE_CLOSE_EAST
         If Not DispenseClosureEast(RecordDataString, CRForm) Then
            MsgBox "CLOSE_EAST"
            Exit Function
         End If
      
      Case KEY_COMPASS_RULE_CLOSE_OBS
         If Not DispenseClosingObs(RecordDataString, CRForm) Then
            MsgBox "CLOSE_OBS"
            Exit Function
         End If

      Case KEY_COMPASS_RULE_CLOSE_OBS_NAME_DESC
         If Not DispenseNameAndDescOption(RecordDataString, CRForm) Then
            MsgBox "CLOSE_OBS_NAME_DESC"
            Exit Function
         End If

      Case KEY_COMPASS_RULE_START_OBS_NAME_DESC
         If Not DispenseStartNameDescOption(RecordDataString, CRForm) Then
            MsgBox "START_OBS_NAME_DESC"
            Exit Function
         End If

      Case KEY_COMPASS_RULE_CLOSE_OBS_NAME
         CRForm.CloseNameTextBox.text = RecordDataString

      Case KEY_COMPASS_RULE_CLOSE_OBS_DESC
         CRForm.CloseDescTextBox.text = RecordDataString

      Case KEY_COMPASS_RULE_CLOSE_OBS_DESC
         CRForm.CloseDescTextBox.text = RecordDataString

      Case KEY_COMPASS_RULE_CLOSE_OBS_EL
         CRForm.ElevationTextBox.text = RecordDataString

      Case KEY_COMPASS_RULE_CLOSE_OBS_INCLUDE_EL
         If Not DispenseIncludeElevOption(RecordDataString, CRForm) Then
            MsgBox "CLOSE_OBS_INCLUDE_EL"
            Exit Function
         End If
         
      Case KEY_COMPASS_RULE_SOL_RULES_COURSES
         If Not DispenseSolCourseType(RecordDataString, TabData) Then
            MsgBox "SOL_RULES_COURSES"
            Exit Function
         End If

      Case KEY_COMPASS_RULE_SOL_COURSE_PREC
         If Not DispenseSolCoursePrec(RecordDataString, TabData) Then
            MsgBox "SOL_COURSE_PREC"
            Exit Function
         End If

      Case KEY_COMPASS_RULE_SOL_COURSE_DIST_PREC
         If Not DispenseSolCourseDistPrec(RecordDataString, TabData) Then
            MsgBox "SOL_COURSE_DIST_PREC"
            Exit Function
         End If

      Case KEY_COMPASS_RULE_POINT_TYPE
         If Not DispenseCompassRuleType(RecordDataString, TabData) Then
            MsgBox "POINT_TYPE"
            Exit Function
         End If
      
      Case KEY_COMPASS_RULE_APPLY
         TabData.ApplyChkBox = StringTrueFalse(RecordDataString)
      
      Case KEY_COMPASS_RULE_MOVE_ALL
         TabData.TransformationChkBox = StringTrueFalse(RecordDataString)

      Case KEY_COMPASS_RULE_MOVE_TO_NORTH
         Dim theScaler As Double
         Dim origPrec As Long
         If Not IsNorthingString(RecordDataString, theScaler, origPrec) Then
            MsgBox "MOVE_TO_NORTH"
            Exit Function
         End If
         TabData.TranslationNorthing = DoubleToNorthingString(CDbl(RecordDataString), START_COORD_PREC)

      Case KEY_COMPASS_RULE_MOVE_TO_EAST
         If Not IsEastingString(RecordDataString, theScaler, origPrec) Then
            MsgBox "MOVE_TO_EAST"
            Exit Function
         End If
         TabData.TranslationEasting = DoubleToEastingString(CDbl(RecordDataString), START_COORD_PREC)

      Case KEY_COMPASS_RULE_MOVE_TO_OBS
         If Not ProcessIndexRecord(RecordDataString, TabData.TranslationIndex) Then
            MsgBox "MOVE_TO_OBS"
            Exit Function
         End If

      Case KEY_COMPASS_RULE_TWO_POINT_NORTH
         If Not IsNorthingString(RecordDataString, theScaler, origPrec) Then
            MsgBox "TWO_POINT_NORTH"
            Exit Function
         End If
         TabData.TwoPathNorthing = DoubleToNorthingString(CDbl(RecordDataString), START_COORD_PREC)

      Case KEY_COMPASS_RULE_TWO_POINT_EAST
         If Not IsEastingString(RecordDataString, theScaler, origPrec) Then
            MsgBox "TWO_POINT_EAST"
            Exit Function
         End If
         TabData.TwoPathEasting = DoubleToEastingString(CDbl(RecordDataString), START_COORD_PREC)
      
      Case KEY_COMPASS_RULE_TWO_POINT_OBS
         If Not ProcessIndexRecord(RecordDataString, TabData.TwoPathObsIndex) Then
            MsgBox "TWO_POINT_OBS"
            Exit Function
         End If

      Case KEY_COMPASS_RULE_ANGULAR_ADJ_CHECK
         TabData.AngErrChkBox = StringTrueFalse(RecordDataString)

      Case KEY_COMPASS_RULE_ANGULAR_ADJ
         If Not DispenseAngularAdjVal(RecordDataString, TabData.AngErrTxtBox) Then
            MsgBox "ANGULAR_ADJ"
            Exit Function
         End If
      
      Case KEY_COMPASS_RULE_DATE
         CRForm.DateTextBox.text = RecordDataString
         
      Case KEY_COMPASS_RULE_PROJ
         CRForm.ProjectTextBox.text = RecordDataString
         
      Case KEY_COMPASS_RULE_ORIGIN
         CRForm.OriginTextBox.text = RecordDataString

      Case KEY_COMPASS_RULE_AZIMUTH
         CRForm.AzimuthTextBox.text = RecordDataString

      Case KEY_COMPASS_RULE_FIELDBOOK
         CRForm.FieldBookTextBox.text = RecordDataString

      Case KEY_COMPASS_RULE_NOTES
         CRForm.NotesTextBox.text = RecordDataString
         
      Case KEY_ADJUSTMENT_PHASE
         DispensePhase RecordDataString, CRForm
         
      Case KEY_COMPASS_RULE_NO_DROP
         DispenseNoDrop RecordDataString, CRForm
      
      Case KEY_SIGNAL
         DispenseSignal RecordDataString, CRForm, TabData
         
      Case KEY_COMPASS_RULE_ROTATE
         TabData.RotationChkBox = StringTrueFalse(RecordDataString)
         
      Case KEY_COMPASS_RULE_ROTATION
         Dim degPart As Long
         Dim minPart As Long
         Dim secPart As Double
         Dim isNeg As Boolean
         If Not IsPlusMinusAngleString(RecordDataString, origPrec, degPart, minPart, secPart, isNeg) Then
            MsgBox "ROTATION"
            Exit Function
         End If
         TabData.RotationTxtBox = RecordDataString
      
      Case KEY_COMPASS_RULE_DIAGRAM_AZIMUTH
         If Not IsDeltaString(RecordDataString, origPrec, degPart, minPart, secPart) Then
            MsgBox "DIAGRAM_AZIMUTH"
            Exit Function
         End If
         CRForm.DropAzimuthTextBox.text = RecordDataString
   End Select
'SIGNAL SUCCESS
   DispenseRecord = True
End Function



Private Function DispenseDrop(RecordDataString As String, CRForm As FrmCompassRule) As Boolean
   DispenseDrop = False
   Dim rawIndex As Long
   rawIndex = CRForm.RawEntriesListBox.ListCount - 1
   If rawIndex < 0 Then
      Exit Function
   End If

   Dim shotType As String
   Dim pointName As String
   Dim bSString As String
   Dim fSString As String
   Dim hDString As String
   Dim descriptionString As String
   Dim showDrop As Boolean
   Dim elevationString As String
   CRForm.GetRawListLine rawIndex, shotType, pointName, bSString, fSString, hDString, descriptionString, showDrop, elevationString
   If KEY_COMPASS_RULE_SIDE_SHOT <> shotType Then
      Exit Function
   End If


'PARSE THE STRING
   Dim ParseString As Variant
   ParseString = Split(RecordDataString, SEPARATOR_COMPASS_RULE_DROP)

   If (UBound(ParseString) - LBound(ParseString)) <> 4 Then
      Exit Function
   End If
   Dim ParseIndex As Long
   ParseIndex = LBound(ParseString)
   showDrop = StringTrueFalse(ParseString(ParseIndex))
   CRForm.FillRawListIndex rawIndex, shotType, pointName, bSString, fSString, hDString, descriptionString, showDrop
   CRForm.FillDropsListIndex rawIndex, ParseString(ParseIndex + 1), ParseString(ParseIndex + 2), ParseString(ParseIndex + 3), ParseString(ParseIndex + 4)
   DispenseDrop = True
End Function



Private Sub DispenseNoDrop(RecordDataString As String, CRForm As FrmCompassRule)

End Sub


Private Function DispenseElevation(RecordDataString As String, CRForm As FrmCompassRule) As Boolean
   DispenseElevation = False
   Dim rawIndex As Long
   rawIndex = CRForm.RawEntriesListBox.ListCount - 1
   If rawIndex < 0 Then
      Exit Function
   End If

   Dim shotType As String
   Dim pointName As String
   Dim bSString As String
   Dim fSString As String
   Dim hDString As String
   Dim descriptionString As String
   Dim showDrop As Boolean
   Dim elevationString As String
   CRForm.GetRawListLine rawIndex, shotType, pointName, bSString, fSString, hDString, descriptionString, showDrop, elevationString
   If KEY_COMPASS_RULE_TRAV <> shotType Then
      Exit Function
   End If


'CHECK THE STRING
   Dim plotElevString As String
   plotElevString = Left(RecordDataString, 1)
   If plotElevString <> PLOT_EL_TRUE And plotElevString <> PLOT_EL_FALSE Then
      Exit Function
   End If
   
   Dim elev As Double
   Dim origPrec As Long
   If IsElevationString(Mid(RecordDataString, 2), elev, origPrec) Then
      CRForm.FillRawListIndex rawIndex, shotType, pointName, bSString, fSString, hDString, descriptionString, , RecordDataString
      DispenseElevation = True
   End If
End Function




Private Sub DispensePhase(RecordDataString As String, CRForm As FrmCompassRule)
   If RecordDataString = OPT_PRELIMIARY_ADJ Then
      CRForm.PreliminaryOption = True
   Else
      CRForm.FinalOption = True
   End If
End Sub

Private Sub DispenseSignal(RecordDataString As String, CRForm As FrmCompassRule, TabData As AdjTabData)
   If RecordDataString = OPT_FINAL_ADJ Then
      CRForm.SetPrelimData TabData
   End If
End Sub


Private Function DispenseAngularAdjVal(RecordDataString As String, AngleString As String) As Boolean
'NEED TO REDO THIS FUNCTION
   DispenseAngularAdjVal = False
   Dim TheDegrees As Double
   If AngleStringToDegree(RecordDataString, TheDegrees) Then
      If TheDegrees > ANGLUAR_ADJ_LIMIT Or TheDegrees < -ANGLUAR_ADJ_LIMIT Then
         Exit Function
      End If
   Else
      Exit Function
   End If
   AngleString = RecordDataString
   DispenseAngularAdjVal = True
End Function







Private Function ProcessIndexRecord(RecordDataString As String, OutputIndex As Long)
   ProcessIndexRecord = False
   If Not IsNumeric(RecordDataString) Then
      Exit Function
   End If
   Dim index As Long
   index = CLng(RecordDataString)
   If index < -1 Then
      Exit Function
   End If
   OutputIndex = index
   ProcessIndexRecord = True
End Function










Private Function DispenseCompassRuleType(RecordDataString As String, TabData As AdjTabData) As Boolean
   DispenseCompassRuleType = False
   Select Case RecordDataString
      Case OPT_COMPASS_RULE_ONE_POINT_TYPE
         TabData.SinglePathOption = True
         TabData.TwoPathOption = False
      Case OPT_COMPASS_RULE_TWO_POINT_TYPE
         TabData.SinglePathOption = False
         TabData.TwoPathOption = True
      Case Else
         Exit Function
   End Select
   DispenseCompassRuleType = True
End Function

Private Function DispenseSolCoursePrec(RecordDataString As String, TabData As AdjTabData) As Boolean
   DispenseSolCoursePrec = False
   Select Case RecordDataString
      Case OPT_COMPASS_RULE_COURSE_PRECISION_SECOND
         TabData.OneSecondOption = True
         TabData.TenthSecondOption = False
      Case OPT_COMPASS_RULE_COURSE_PRECISION_TENTH_SEC
         TabData.OneSecondOption = False
         TabData.TenthSecondOption = True
      Case Else
         Exit Function
   End Select
   DispenseSolCoursePrec = True
End Function

Private Function DispenseSolCourseDistPrec(RecordDataString As String, TabData As AdjTabData) As Boolean
   DispenseSolCourseDistPrec = False
   Select Case RecordDataString
      Case OPT_COMPASS_RULE_COURSE_PRECISION_HUNDREDTH_FT
         TabData.hundredthFootOption = True
         TabData.ThousandthFootOption = False
      Case OPT_COMPASS_RULE_COURSE_PRECISION_THOUSANDTH_FT
         TabData.hundredthFootOption = False
         TabData.ThousandthFootOption = True
      Case Else
         Exit Function
   End Select
   DispenseSolCourseDistPrec = True
End Function

Private Function DispenseSolCourseType(RecordDataString As String, TabData As AdjTabData) As Boolean
   DispenseSolCourseType = False
   Select Case RecordDataString
      Case OPT_COMPASS_RULE_COURSE_SOLUTION_PREC
         TabData.RerunOption = True
         TabData.HoldCoordinateOption = False
      Case OPT_COMPASS_RULE_COURSE_SOLUTION_INV
         TabData.RerunOption = False
         TabData.HoldCoordinateOption = True
      Case Else
         Exit Function
   End Select
   DispenseSolCourseType = True
End Function

Private Function DispenseNameAndDescOption(RecordDataString As String, CRForm As FrmCompassRule) As Boolean
   DispenseNameAndDescOption = False
   Select Case RecordDataString
      Case OPTION_TRUE
         CRForm.NameAndDescCheckBox.value = True
      Case OPTION_FALSE
         CRForm.NameAndDescCheckBox.value = False
      Case Else
         Exit Function
   End Select
   DispenseNameAndDescOption = True
End Function

Private Function DispenseStartNameDescOption(RecordDataString As String, CRForm As FrmCompassRule) As Boolean
   DispenseStartNameDescOption = False
   Select Case RecordDataString
      Case OPTION_TRUE
         CRForm.DrawStartCheckBox.value = True
      Case OPTION_FALSE
         CRForm.DrawStartCheckBox.value = False
      Case Else
         Exit Function
   End Select
   DispenseStartNameDescOption = True
End Function

Private Function DispenseClosingObs(RecordDataString As String, CRForm As FrmCompassRule) As Boolean
'RETURNS TRUE IF SUCCESSFUL
'INITIALIZE FLAG
   DispenseClosingObs = False
   Select Case RecordDataString
      Case OPT_COMPASS_RULE_CLOSING_OBS_LAST_FS
         CRForm.LastForesightOption.value = True
      Case OPT_COMPASS_RULE_CLOSING_OBS_LAST_OC
         CRForm.LastTraverseOption.value = True
      Case Else
         Exit Function
   End Select
   DispenseClosingObs = True
End Function

Private Function DispenseIncludeElevOption(RecordDataString As String, CRForm As FrmCompassRule) As Boolean
   DispenseIncludeElevOption = False
   Select Case RecordDataString
      Case OPTION_TRUE
         CRForm.IncludeElCheckBox.value = True
      Case OPTION_FALSE
         CRForm.IncludeElCheckBox.value = False
      Case Else
         Exit Function
   End Select
   DispenseIncludeElevOption = True
End Function

Private Function DispenseClosureEast(RecordDataString As String, CRForm As FrmCompassRule) As Boolean
'RETURNS TRUE IF SUCCESSFUL
'INITIALIZE FLAG
   DispenseClosureEast = False
   Dim theScaler As Double
   Dim origPrec As Long
   If Not IsEastingString(RecordDataString, theScaler, origPrec) Then
      Exit Function
   End If
   CRForm.CloseEastTextBox.text = RecordDataString
   CRForm.CloseEastTextBoxSub
   DispenseClosureEast = True
End Function

Private Function DispenseClosureNorth(RecordDataString As String, CRForm As FrmCompassRule) As Boolean
'RETURNS TRUE IF SUCCESSFUL
'INITIALIZE FLAG
   DispenseClosureNorth = False
   Dim theScaler As Double
   Dim origPrec As Long
   If Not IsNorthingString(RecordDataString, theScaler, origPrec) Then
      Exit Function
   End If
   CRForm.CloseNorthTextBox.text = RecordDataString
   CRForm.CloseNorthTextBoxSub
   DispenseClosureNorth = True
End Function

Public Function CoordinateString4Places(InputDouble As Double) As String
   CoordinateString4Places = FormatNumber(InputDouble, 4)
End Function

Private Function DispenseClosuretype(RecordDataString As String, CRForm As FrmCompassRule) As Boolean
'RETURNS TRUE IF SUCCESSFUL
'INITIALIZE FLAG
   DispenseClosuretype = False
   Select Case RecordDataString
      Case OPT_COMPASS_RULE_CTYP_NONE
         CRForm.NoneYetOption.value = True
      Case OPT_COMPASS_RULE_CTYP_BEGIN
         CRForm.ToBeginningOption.value = True
      Case OPT_COMPASS_RULE_CTYP_2PT
         CRForm.ToPointOption.value = True
      Case Else
         Exit Function
   End Select
   DispenseClosuretype = True
End Function


Private Function DispenseTraverse(RecordDataString As String, CRForm As FrmCompassRule) As Boolean
'RETURNS TRUE IF SUCCESSFUL
'INITIALIZE FLAG
   DispenseTraverse = False

'PARSE DATA STRING
   Dim pointName As String
   Dim BSAngleString As String
   Dim FSAngleString As String
   Dim hDString As String
   Dim description As String
   If Not ParseTravSideShotData(RecordDataString, _
                                pointName, _
                                BSAngleString, _
                                FSAngleString, _
                                hDString, _
                                description, _
                                CRForm) Then
      Exit Function
   End If

'ADD IT TO THE RAW LISTBOX
   CRForm.NewRawListRow (CRForm.RawListTopIndex() + 1)

'FILL IN FIELDS
   CRForm.FillRawListIndex CRForm.RawListTopIndex(), KEY_COMPASS_RULE_TRAV, pointName, BSAngleString, FSAngleString, hDString, description

'FLAG TRAVERSE HAS BEEN ENTERED
   SetTraverseHasBeenEnteredFlag

'FLAG SUCCESS
   DispenseTraverse = True
End Function

Private Function DispenseSideShot(RecordDataString As String, CRForm As FrmCompassRule) As Boolean
'RETURNS TRUE IF SUCCESSFUL
'INITIALIZE FLAG
   DispenseSideShot = False

'CHECK IF TRAVERSE HAS BEEN ENTERED, NEED A SETUP POINT TO BE VALID
   If Not TraverseHasBeenEntered Then
      Exit Function
   End If

'PARSE DATA STRING
   Dim pointName As String
   Dim BSAngleString As String
   Dim FSAngleString As String
   Dim hDString As String
   Dim description As String
   If Not ParseTravSideShotData(RecordDataString, _
                                pointName, _
                                BSAngleString, _
                                FSAngleString, _
                                hDString, _
                                description, _
                                CRForm) Then
      Exit Function
   End If

'ADD IT TO THE RAW LISTBOX
   Dim NewRowNum As Long
   NewRowNum = CRForm.RawListTopIndex() + 1
   CRForm.NewRawListRow NewRowNum
   CRForm.FillDropsListIndex NewRowNum, " ", " ", " ", " "

'FILL IN FIELDS
   CRForm.FillRawListIndex CRForm.RawListTopIndex(), KEY_COMPASS_RULE_SIDE_SHOT, pointName, BSAngleString, FSAngleString, hDString, description

'FLAG SUCCESS
   DispenseSideShot = True
End Function


Private Function ParseTravSideShotData(RecordDataString As String, _
                                       ByRef pointName As String, _
                                       ByRef BSAngle As String, _
                                       ByRef FSAngle As String, _
                                       ByRef HD As String, _
                                       ByRef description As String, _
                                       CRForm As FrmCompassRule) As Boolean
'RETURNS TRUE IF SUCCESSFUL
'INITIALIZE FLAG
   ParseTravSideShotData = False

'PARSE THE STRING
   Dim ParseString As Variant
   ParseString = Split(RecordDataString, ",")

'CHECK FOR MINIMUM NUMBER OF COMPONENTS
   If (UBound(ParseString) - LBound(ParseString)) < 4 Then
      Exit Function
   End If

'GET POINT NAME
   Dim ThePointName As String
   ThePointName = ParseString(LBound(ParseString))
   If Len(ThePointName) > MAX_LEN_POINT_NAME Then
      Exit Function
   End If

'GET THE BACKSIGHT ANGLE
   Dim OriginalBSString As String
   OriginalBSString = ParseString(LBound(ParseString) + 1)

'CHECK IF BACKSIGHT ANGLE IS AN ANGLE, REFORMAT STRING
   Dim NewBSString As String
   If Not GoodAngleString(OriginalBSString, NewBSString, CRForm.GetAngleStyle) Then
      Exit Function
   End If

'GET THE FORESIGHT ANGLE
   Dim OriginalFSString As String
   OriginalFSString = ParseString(LBound(ParseString) + 2)

'CHECK IF FORESIGHT ANGLE IS AN ANGLE, REFORMAT STRING
   Dim NewFSString As String
   If Not GoodAngleString(OriginalFSString, NewFSString, CRForm.GetAngleStyle) Then
      Exit Function
   End If

'GET THE HD
   Dim OriginalHDString As String
   OriginalHDString = ParseString(LBound(ParseString) + 3)
   
'CHECK IF IT IS A NUMBER
   If Not IsNumeric(OriginalHDString) Then
      Exit Function
   End If
   
'CHECK IF IT IS POSITIVE
   If CDbl(OriginalHDString) <= 0 Then
      Exit Function
   End If

'REFORMAT STRING
   Dim ReformattedDistString As String
   If Not ReformatDistEntry(OriginalHDString, ReformattedDistString, True) Then
      Exit Function
   End If
'HANDLE THE DESCRIPTION FIELD
   Dim TheDescription As String
   If (UBound(ParseString) - LBound(ParseString)) > 4 Then 'RECOMBINE THE DESCRIPTION IF NEEDED
      TheDescription = ""        'START OFF THE STRING
      Dim i As Long              'INITIALIZE COUNTER/INDEX TO REPLACE THE SEPARATORS
      i = LBound(ParseString) + 4
      Do While i <= (UBound(ParseString) - 1)
         TheDescription = TheDescription & ParseString(i) & ","
         i = i + 1
      Loop
      TheDescription = TheDescription & ParseString(i)
   Else                          'NO NEED TO RECOMBINE, JUST RETURN DESCRIPTION AS IS
      TheDescription = ParseString(UBound(ParseString))
   End If

'MAKE SURE DESCRIPTION FIELD IS NOT TOO LONG
   If Len(TheDescription) > MAX_LEN_POINT_DESC Then
      Exit Function
   End If

'RETURN VALUES
   pointName = ThePointName
   BSAngle = NewBSString
   FSAngle = NewFSString
   HD = ReformattedDistString
   description = TheDescription
   
'FLAG SUCCESS
   ParseTravSideShotData = True
End Function


Private Function GoodAngleString(AngleString As String, newAngleString As String, angleStyle As Integer) As Boolean
'RETURNS TRUE IF GOOD ANGLE STRING
'INITIALIZE FLAG
   GoodAngleString = False

'CHECK IF AZIMUTH STRING
   Dim origPrec As Long
   Dim degPart As Long
   Dim minPart As Long
   Dim secPart As Double
   If Not IsDeltaString(AngleString, origPrec, degPart, minPart, secPart) Then
      Exit Function
   End If

'CONVERT IT BACK TO ANGLE STRING FORMAT
   newAngleString = DirString(degPart, minPart, secPart, origPrec, DIR_TYPE_AZIMUTH, angleStyle)

'SIGNAL SUCCESS
   GoodAngleString = True
End Function




Private Function GetToOpenCompassRuleFilename(ByRef TheFilename As String) As Boolean
'RETURNS TRUE IF SUCCESSFUL, TOOPENFILENAME AS THEFILENAME
   GetToOpenCompassRuleFilename = False

'GET SUGGESTED PATH FOR REPORT FILE
   Dim ToOpenCompassFilePath As String
   ToOpenCompassFilePath = GetSuggestedPath()

'CREATE FILTER STRING
   Dim FilterString As String
   FilterString = "*" & FILE_EXTENSION_COMPASS_RULE

'CALL COMMON DIALOG
   Dim strFName As String
   strFName = space(255)
   Dim lngfhandle As Long
   Dim lngrid As Long
   Dim retVal As Long
   retVal = mdlDialog_fileOpen(strFName, lngfhandle, lngrid, _
                               "", FilterString, ToOpenCompassFilePath, "Open File")
   Select Case retVal
      Case 0 'OPEN
         strFName = Left(strFName, InStr(1, strFName, Chr(0)) - 1)
         TheFilename = strFName
         GetToOpenCompassRuleFilename = True
      Case 1 'Cancel, no action

    End Select
End Function


Public Function OpenCompassRuleFile(ByRef TheFilename As String) As Boolean
'INITIALIZE FLAG
   OpenCompassRuleFile = False

'GET NEW FILE NAME
   Dim NewCompassRuleFilename As String
   If GetToOpenCompassRuleFilename(NewCompassRuleFilename) Then
'STORE NEW FULL FILE PATH
      SaveSetting APP_NAME, SECTION_COMPASS_RULE_2D, KEY_FILENAME, NewCompassRuleFilename
'RETURN THE FULL FILE PATH
      TheFilename = NewCompassRuleFilename
'SIGNAL THAT FILENAME IS CHOSEN
      OpenCompassRuleFile = True
   End If
End Function

Public Sub CopyToCompassRuleFile(CRForm As FrmCompassRule)
'GET NEW FILE NAME
   Dim NewCompassRuleFilename As String
   If GetCopyToCompassRuleFilename(NewCompassRuleFilename) Then
'SAVE FILE ID STRING
      Dim OriginalIDString As String
      OriginalIDString = CRForm.IDstring
      
'CREATE NEW ID STRING
      CRForm.IDstring = FileID()

'WRITE THE NEW FILE
      Dim success As Boolean
      success = WriteCompassRuleFile(NewCompassRuleFilename, CRForm)

'RESTORE FILE ID
      CRForm.IDstring = OriginalIDString
   End If
End Sub



Public Function NewCompassRuleFile(ByRef TheFilename As String, CRForm As FrmCompassRule) As Boolean
'INITIALIZE FLAG
   NewCompassRuleFile = False

'GET NEW FILE NAME
   Dim NewCompassRuleFilename As String
   If GetNewCompassRuleFilename(NewCompassRuleFilename) Then
'CREATE THE NEW FILE
      If CreateNewCompassRuleFile(NewCompassRuleFilename, CRForm) Then
'STORE NEW FULL FILE PATH
         SaveSetting APP_NAME, SECTION_COMPASS_RULE_2D, KEY_FILENAME, NewCompassRuleFilename
'RETURN THE FULL FILE PATH
         TheFilename = NewCompassRuleFilename
'SIGNAL THAT FILENAME IS CHOSEN
         NewCompassRuleFile = True
      End If
   End If
End Function


Private Function FileID() As String
'CREATES A "UNIQUE STRING FOR CREATING A NEW FILE
   Randomize
   FileID = Now & " " & CLng(Rnd * 100000)
End Function

Private Function GetCopyToCompassRuleFilename(ByRef TheFilename As String) As Boolean
'RETURNS TRUE IF SUCCESSFUL, NEWFILENAME AS THEFILENAME
   GetCopyToCompassRuleFilename = False

'GET SUGGESTED PATH FOR REPORT FILE
   Dim NewCompassFilePath As String
   NewCompassFilePath = GetSuggestedPath()

'CREATE FILTER STRING
   Dim FilterString As String
   FilterString = "*" & FILE_EXTENSION_COMPASS_RULE

'CALL COMMON DIALOG FOR CREATING FILE
   Dim retVal As Long
   Dim lngfhandle As Long
   Dim lngrid As Long
   Dim strFName As String
   strFName = space(255)
   retVal = mdlDialog_fileCreate(strFName, lngfhandle, lngrid, "", FilterString, NewCompassFilePath, "Copy to Compass Rule File")
   Select Case retVal
      Case 0 'Open
'RETURN NEW FILENAME
         strFName = Left(strFName, InStr(1, strFName, Chr(0)) - 1)
         TheFilename = strFName
         GetCopyToCompassRuleFilename = True
      Case 1 'Cancel

   End Select
End Function


Private Function GetNewCompassRuleFilename(ByRef TheFilename As String) As Boolean
'RETURNS TRUE IF SUCCESSFUL, NEWFILENAME AS THEFILENAME
   GetNewCompassRuleFilename = False

'GET SUGGESTED PATH FOR REPORT FILE
   Dim NewCompassFilePath As String
   NewCompassFilePath = GetSuggestedPath()

'CREATE FILTER STRING
   Dim FilterString As String
   FilterString = "*" & FILE_EXTENSION_COMPASS_RULE

'CALL COMMON DIALOG FOR CREATING FILE
   Dim retVal As Long
   Dim lngfhandle As Long
   Dim lngrid As Long
   Dim strFName As String
   strFName = space(255)
   retVal = mdlDialog_fileCreate(strFName, lngfhandle, lngrid, "", FilterString, NewCompassFilePath, "Create New Compass Rule File")
   Select Case retVal
      Case 0 'Open
'RETURN NEW FILENAME
         strFName = Left(strFName, InStr(1, strFName, Chr(0)) - 1)
         TheFilename = strFName
         GetNewCompassRuleFilename = True
      Case 1 'Cancel

   End Select
End Function

Public Function GetJustTheCompassRuleFilename() As String
'GET CURRENT FILENAME WITH PATH
   Dim fullFilename As String
   fullFilename = GetCompassRuleFullFilename()

'SEPARATE THE FILENAME
   Dim XSplit As Variant
   XSplit = Split(fullFilename, "\")
   GetJustTheCompassRuleFilename = XSplit(UBound(XSplit))
End Function

Private Function GetSuggestedPath() As String
'GET STORED FILENAME
   Dim FilePath As String
   FilePath = GetCompassRuleFullFilename

'PARSE INTO PATH AND FILE
   Dim xSplit2 As Variant
   xSplit2 = Split(FilePath, "\")
   xSplit2(UBound(xSplit2)) = ""
   Dim NewCompassFilePath As String
   NewCompassFilePath = Join(xSplit2, "\")
   
'RETURN PATH
   GetSuggestedPath = NewCompassFilePath
End Function

Public Function GetCompassRuleFullFilename() As String
'CREATE DEFAULT FILE NAME WHEN NO PREVIOUS PATH
   Dim DefaultFilename As String
   DefaultFilename = "C:\output" & FILE_EXTENSION_COMPASS_RULE

'GET NAME OF PREVIOUS FILE USED
   Dim CurrentFullFileName As String
   CurrentFullFileName = GetSetting(APP_NAME, SECTION_COMPASS_RULE_2D, KEY_FILENAME, DefaultFilename)

'IF PREVIOUS FILE WAS NOTHING, USE DEFAULT FILENAME
   If Trim(CurrentFullFileName) = "" Then
      GetCompassRuleFullFilename = DefaultFilename
   Else
      GetCompassRuleFullFilename = CurrentFullFileName
   End If
End Function



Private Function CreateNewCompassRuleFile(OutputFilename As String, CRForm As FrmCompassRule) As Boolean
'RETURNS TRUE IF SUCCESSFUL
   CreateNewCompassRuleFile = True

'JUMP ON ERROR
   On Error GoTo errhnd

'INITIALIZE FIELDS OF NEW FILE
   CRForm.InitNewCRForm

'CREATE NEW FILE ID
'OPEN FILE
   Dim FFILE As Long
   FFILE = FreeFile
   Open OutputFilename For Output As #FFILE

'WRITE HEADER
      Print #FFILE, Compass_Rule_File_Header

'WRITE FILE FORMAT VERSION NUMBER
      Print #FFILE, Compass_Rule_Format_Number

'WRITE FILE ID
      Print #FFILE, FileID()
      
'WRITE START POINT Z
      Print #FFILE, CRForm.StartPointZString

'WRITE START POINT NORTHING
      Print #FFILE, FormatToWriteNorth(CRForm.TextNorthing.text)

'WRITE START POINT EASTING
      Print #FFILE, FormatToWriteEast(CRForm.TextEasting.text)

'CLOSE FILE
   Close #FFILE

'JUMP PAST ERROR CODE
   Exit Function


'ERROR HANDLING
errhnd:
   CreateNewCompassRuleFile = False
   ErrorMess Err.Number
   Err.Clear
End Function

Attribute VB_Name = "CompassRulePlaceDiaPrimitive"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.


Option Explicit

Implements IPrimitiveCommandEvents

Private SetupPoint As Point3d
Private sideShotPoint As Point3d

Public Property Let SideShot(thePoint As Point3d)
   sideShotPoint = thePoint
End Property

Public Property Let Setup(thePoint As Point3d)
   SetupPoint = thePoint
End Property

Private Sub IPrimitiveCommandEvents_Cleanup()
   FrmCompassRule.Show
   FrmEnterSide.Show
   ClearCommandPromptArea
End Sub

Private Sub IPrimitiveCommandEvents_DataPoint(point As Point3d, ByVal view As view)
   FrmEnterSide.EnterDiagramPlacementPoint point
   CommandState.StartDefaultCommand
End Sub

Private Sub IPrimitiveCommandEvents_Dynamics(point As Point3d, ByVal view As view, ByVal DrawMode As MsdDrawingMode)
'DRAW TETHER LINES
   DrawTether SetupPoint, sideShotPoint, DrawMode
   DrawTether sideShotPoint, point, DrawMode

'DRAW CIRCLE
   Dim RadSize As Double
   RadSize = FrmCompassRule.calcCharSize(view, 30)
   Dim oLineStyle As LineStyle
   Set oLineStyle = ActiveDesignFile.LineStyles.Find("0")
   Dim theCircle As EllipseElement
   Set theCircle = CreateEllipseElement2(Nothing, sideShotPoint, RadSize, RadSize, Matrix3dIdentity)
   Set theCircle.LineStyle = oLineStyle
   theCircle.color = GetTetherColor()
   theCircle.Redraw DrawMode

'DRAW PARTIAL DIAGRAM
'CALCULATE METRICS
   Dim LineSpacing As Double
   Dim fontSize As Double
   Dim MarkerDiameter As Double
   Dim halfExtLineLength As Double
   Dim extLineLength As Double
   Dim legLength As Double
   Dim rotAngleRad As Double
   Dim DropAzString As String
   DropAzString = FrmCompassRule.DropAzimuthTextBox.text
   Dim diagAzDegrees As Double
   If Not AngleStringToDegree(DropAzString, diagAzDegrees) Then
      diagAzDegrees = 270#
   End If
   CalcDropMetrics diagAzDegrees, fontSize, legLength, extLineLength, halfExtLineLength, LineSpacing, rotAngleRad, MarkerDiameter

'ADD THE CROSS ELEMENTS
   Dim cellElements(0 To 3) As Element
   AddDropCrossToCell cellElements, theCircle, point, legLength

'CREATE THE CELL
   Dim TheDropCell As CellElement
   Set TheDropCell = CreateCellElement1(vbNullString, cellElements, point)
   TheDropCell.RotateAboutZ point, rotAngleRad
   TheDropCell.Redraw DrawMode
End Sub

Private Sub IPrimitiveCommandEvents_Keyin(ByVal Keyin As String)

End Sub

Private Sub IPrimitiveCommandEvents_Reset()
   CommandState.StartDefaultCommand
End Sub

Private Sub IPrimitiveCommandEvents_Start()
   ShowCommand COMMAND_NAME_COMPASS_RULE_2D
   ShowPrompt "Pick Place for Diagram"
   CommandState.DisableAccuSnap
   CommandState.StartDynamics
End Sub

Attribute VB_Name = "CompassRuleRecCorPrimitive"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.
Option Explicit

Implements IPrimitiveCommandEvents

Private SetupPoint As Point3d
Private sideShotPoint As Point3d

Public Property Let SideShot(thePoint As Point3d)
   sideShotPoint = thePoint
End Property

Public Property Let Setup(thePoint As Point3d)
   SetupPoint = thePoint
End Property


Private Sub IPrimitiveCommandEvents_Cleanup()
   FrmCompassRule.Show
   FrmEnterSide.Show
   ClearCommandPromptArea
End Sub

Private Sub IPrimitiveCommandEvents_DataPoint(point As Point3d, ByVal view As view)
   FrmEnterSide.EnterCorRecPoint point
   CommandState.StartDefaultCommand
End Sub

Private Sub IPrimitiveCommandEvents_Dynamics(point As Point3d, ByVal view As view, ByVal DrawMode As MsdDrawingMode)
'DRAW TETHER LINE
   DrawTether SetupPoint, sideShotPoint, DrawMode
   DrawTether point, sideShotPoint, DrawMode

'DRAW CIRCLE
   Dim RadSize As Double
   RadSize = FrmCompassRule.calcCharSize(view, 30)
   Dim oLineStyle As LineStyle
   Set oLineStyle = ActiveDesignFile.LineStyles.Find("0")
   Dim theCircle As EllipseElement
   Set theCircle = CreateEllipseElement2(Nothing, sideShotPoint, RadSize, RadSize, Matrix3dIdentity)
   Set theCircle.LineStyle = oLineStyle
   theCircle.color = GetTetherColor()
   theCircle.Redraw DrawMode
End Sub

Private Sub IPrimitiveCommandEvents_Keyin(ByVal Keyin As String)

End Sub

Private Sub IPrimitiveCommandEvents_Reset()
   CommandState.StartDefaultCommand
End Sub

Private Sub IPrimitiveCommandEvents_Start()
   ShowCommand COMMAND_NAME_COMPASS_RULE_2D
   ShowPrompt "Pick Record Point"
   
   CommandState.EnableAccuSnap
   CommandState.StartDynamics
End Sub

Attribute VB_Name = "CurveSolverLocateText"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.


Option Explicit

Implements ILocateCommandEvents

Public hostForm As FrmCurveSolver

Private myLC As LocateCriteria



Private Sub ILocateCommandEvents_Accept(ByVal Element As Element, point As Point3d, ByVal view As view)

End Sub



Private Sub ILocateCommandEvents_Cleanup()
   hostForm.Show
   ClearCommandPromptArea
   CommandState.EnableAccuSnap
End Sub



Private Sub ILocateCommandEvents_Dynamics(point As Point3d, ByVal view As view, ByVal DrawMode As MsdDrawingMode)
   
End Sub



Private Sub ILocateCommandEvents_LocateFailed()
End Sub



Private Sub ILocateCommandEvents_LocateFilter(ByVal Element As Element, point As Point3d, Accepted As Boolean)
   Dim myEl As Element
   Set myEl = CommandState.GetLocatedElement(False)
   If myEl.IsTextElement Then
          hostForm.EnterText myEl.AsTextElement.text
   End If
   CommandState.StartDefaultCommand
   Accepted = False
End Sub



Private Sub ILocateCommandEvents_LocateReset()
   CommandState.StartDefaultCommand
End Sub



Private Sub ILocateCommandEvents_Start()
   
   Set myLC = CommandState.CreateLocateCriteria(False)
   myLC.ExcludeAllTypes
   myLC.IncludeType msdElementTypeText
   myLC.IncludeType msdElementTypeTextNode
   myLC.IncludeType msdElementTypeCellHeader
   CommandState.SetLocateCriteria myLC
   
   ShowCommand COMMAND_NAME_CURVE_SOLVER
   ShowPrompt "Pick Text Element/Reset"

   ActiveModelReference.UnselectAllElements

   CommandState.DisableAccuSnap
End Sub

Attribute VB_Name = "CurveSolverPrimitive"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit

Implements IPrimitiveCommandEvents

Public hostForm As FrmCurveSolver


Private Sub IPrimitiveCommandEvents_Cleanup()
   hostForm.Show
   ClearCommandPromptArea
End Sub



Private Sub IPrimitiveCommandEvents_DataPoint(point As Point3d, ByVal view As view)
   hostForm.PermGraphic point, view
   If hostForm.doAdditional Then
      hostForm.doAdditional = False
      CommandState.StartDynamics
   Else
      CommandState.StartDefaultCommand
   End If
End Sub



Private Sub IPrimitiveCommandEvents_Dynamics(point As Point3d, ByVal view As view, ByVal DrawMode As MsdDrawingMode)
   Dim tempGraphicElement As Element
   Set tempGraphicElement = hostForm.TempGraphic(point, view)
   tempGraphicElement.Redraw DrawMode
End Sub



Private Sub IPrimitiveCommandEvents_Keyin(ByVal Keyin As String)
End Sub



Private Sub IPrimitiveCommandEvents_Reset()
   CommandState.StartDefaultCommand
End Sub



Private Sub IPrimitiveCommandEvents_Start()
   ShowCommand COMMAND_NAME_CURVE_SOLVER
   ShowPrompt "Pick where to place element/Reset to quit"
   CommandState.EnableAccuSnap
   CommandState.StartDynamics
End Sub

Attribute VB_Name = "DrawTraverseILocateText"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit

Implements ILocateCommandEvents

Public hostForm As FrmTraverse

Private myLC As LocateCriteria

Private Sub ILocateCommandEvents_Accept(ByVal Element As Element, point As Point3d, ByVal view As view)

End Sub



Private Sub ILocateCommandEvents_Cleanup()
   hostForm.Show
   ClearCommandPromptArea
   CommandState.EnableAccuSnap
End Sub



Private Sub ILocateCommandEvents_Dynamics(point As Point3d, ByVal view As view, ByVal DrawMode As MsdDrawingMode)
   
End Sub



Private Sub ILocateCommandEvents_LocateFailed()
End Sub



Private Sub ILocateCommandEvents_LocateFilter(ByVal Element As Element, point As Point3d, Accepted As Boolean)
   Dim myEl As Element
   Set myEl = CommandState.GetLocatedElement(False)
   If myEl.IsTextElement Then
          hostForm.EnterText myEl.AsTextElement.text
   End If
   CommandState.StartDefaultCommand
   Accepted = False
End Sub



Private Sub ILocateCommandEvents_LocateReset()
   CommandState.StartDefaultCommand
End Sub



Private Sub ILocateCommandEvents_Start()
   
   Set myLC = CommandState.CreateLocateCriteria(False)
   myLC.ExcludeAllTypes
   myLC.IncludeType msdElementTypeText
   myLC.IncludeType msdElementTypeTextNode
   myLC.IncludeType msdElementTypeCellHeader
   CommandState.SetLocateCriteria myLC
   
   ShowCommand COMMAND_NAME_AZ_AZ_INT
   ShowPrompt "Pick Text Element/Reset"

   ActiveModelReference.UnselectAllElements

   CommandState.DisableAccuSnap
End Sub

Attribute VB_Name = "DropDiagramCode"
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit

Public Const DROP_DIAGRAM_PRECISION        As Long = 2

Public Const FONT_DIAGRAM_RATIO            As Double = 6#
Public Const TRIM_DROP_LEADER              As Double = 6#    'amount to trim leader line from drop diagram origin in characters
Public Const MIN_DROP_LEADER               As Double = 2.5   'minimum leader line length for drop diagram in characters

Public Const DIAGRAM_ELEMENT_AZIMUTH       As Long = 4
Public Const DIAGRAM_ELEMENT_ARROW         As Long = 5
Public Const DIAGRAM_ELEMENT_CIRCLE        As Long = 8
Public Const DIAGRAM_ELEMENT_XTEXT         As Long = 9
Public Const DIAGRAM_ELEMENT_YTEXT         As Long = 10
Public Const DIAGRAM_ELEMENT_DESCRIPTION   As Long = 11
Public Const DIAGRAM_ELEMENT_DESCRIPTION2  As Long = 12

Public Const QUAD_EXT_SOUTH_WEST           As Integer = 5
Public Const QUAD_EXT_NORTH_WEST           As Integer = 6



'*************************************************************************************************************
'*********************************************CREATE DROP DIAGRAM*********************************************
Public Sub AddDropCrossToCell(cellElements() As Element, theTemplate As Element, originPoint As Point3d, ByVal legLength As Double)
'ADDS CROSS CELL ELEMENTS TO FIRST FOUR ELEMENTS OF ARRAY FOR COMPATABILITY
   Dim originPointCopy As Point3d
   originPointCopy = originPoint

'INITIALIZE POINTS TO ORIGIN POINT
   Dim c1 As Point3d ' cross point north
   c1 = originPointCopy
   Dim c2 As Point3d ' cross point east
   c2 = originPointCopy
   Dim c3 As Point3d ' cross point south
   c3 = originPointCopy
   Dim c4 As Point3d ' cross point west
   c4 = originPointCopy

'EXTEND THE ARMS OF THE CROSS
   c1.Y = c1.Y + legLength
   c2.X = c2.X + legLength
   c3.Y = c3.Y - legLength
   c4.X = c4.X - legLength

'ADD THEM TO THE CELL ARRAY
   Set cellElements(0) = CreateLineElement2(theTemplate, originPointCopy, c1)
   Set cellElements(1) = CreateLineElement2(theTemplate, originPointCopy, c2)
   Set cellElements(2) = CreateLineElement2(theTemplate, originPointCopy, c3)
   Set cellElements(3) = CreateLineElement2(theTemplate, originPointCopy, c4)
End Sub



Public Function CalcAzQuad(ByVal dropQuad1 As Integer, ByVal dropQuad2 As Integer) As Long
   If dropQuad1 = dropQuad2 Then
      If dropQuad1 = QUAD_NORTH_EAST Or dropQuad1 = QUAD_NORTH_WEST Then
         CalcAzQuad = QUAD_SOUTH_WEST
      Else
         CalcAzQuad = QUAD_NORTH_WEST
      End If
      Exit Function
   End If
   
   If (dropQuad1 = QUAD_NORTH_EAST And dropQuad2 = QUAD_SOUTH_EAST) Or _
      (dropQuad1 = QUAD_SOUTH_EAST And dropQuad2 = QUAD_NORTH_EAST) Then
      CalcAzQuad = QUAD_EXT_NORTH_WEST
      Exit Function
   End If
   
   If (dropQuad1 = QUAD_NORTH_EAST And dropQuad2 = QUAD_SOUTH_WEST) Or _
      (dropQuad1 = QUAD_SOUTH_WEST And dropQuad2 = QUAD_NORTH_EAST) Then
      CalcAzQuad = QUAD_EXT_NORTH_WEST
      Exit Function
   End If
   
   If (dropQuad1 = QUAD_SOUTH_WEST And dropQuad2 = QUAD_NORTH_WEST) Or _
      (dropQuad1 = QUAD_NORTH_WEST And dropQuad2 = QUAD_SOUTH_WEST) Then
      CalcAzQuad = QUAD_NORTH_EAST
      Exit Function
   End If
   
   If (dropQuad1 = QUAD_SOUTH_EAST And dropQuad2 = QUAD_NORTH_WEST) Or _
      (dropQuad1 = QUAD_NORTH_WEST And dropQuad2 = QUAD_SOUTH_EAST) Then
      CalcAzQuad = QUAD_EXT_SOUTH_WEST
      Exit Function
   End If
   
   If (dropQuad1 = QUAD_NORTH_EAST And dropQuad2 = QUAD_NORTH_WEST) Or _
      (dropQuad1 = QUAD_NORTH_WEST And dropQuad2 = QUAD_NORTH_EAST) Then
      CalcAzQuad = QUAD_SOUTH_WEST
      Exit Function
   End If
   
   If (dropQuad1 = QUAD_SOUTH_EAST And dropQuad2 = QUAD_SOUTH_WEST) Or _
      (dropQuad1 = QUAD_SOUTH_WEST And dropQuad2 = QUAD_SOUTH_EAST) Then
      CalcAzQuad = QUAD_NORTH_WEST
      Exit Function
   End If
   
   CalcAzQuad = QUAD_NORTH_EAST
End Function



Public Sub CalcDropMetrics(ByVal refAzDegrees As Double, _
                           ByRef fontSize As Double, _
                           ByRef legLength As Double, _
                           ByRef extLineLength As Double, _
                           ByRef halfExtLineLength As Double, _
                           ByRef LineSpacing As Double, _
                           ByRef rotAngleRad As Double, _
                           ByRef markerRadius As Double)
   fontSize = GetCharSize()
   legLength = fontSize * FONT_DIAGRAM_RATIO
   extLineLength = legLength * 2# / 3#
   halfExtLineLength = extLineLength / 2#
   LineSpacing = fontSize / 3#
   rotAngleRad = Radians(270) - Radians(refAzDegrees)
   markerRadius = fontSize / 3#
End Sub



Public Sub CreateDimAndNameText(ByVal XText As String, _
                                ByVal YText As String, _
                                ByVal nameString As String, _
                                ByVal DescString As String, _
                                ByVal DropQuad As Integer, _
                                originPoint As Point3d, _
                                ByVal textTemplate As TextElement, _
                                ByVal LineSpacing As Double, _
                                ByVal extLineLength As Double, _
                                ByVal fontSize As Double, _
                                ByRef DimXEl As TextElement, _
                                ByRef DimYEl As TextElement, _
                                ByRef NameTextEl As TextElement, _
                                ByRef DescTextEl As TextElement)
'MAKE WORKING COPY
   Dim originPointCopy  As Point3d
   originPointCopy = originPoint
    
'INITIALIZE INSERTION POINTS TO ORIGIN POINT
   Dim TextXaxisInsertPoint As Point3d
   TextXaxisInsertPoint = originPointCopy 'x-axis text
   Dim TextYaxisInsertPoint As Point3d
   TextYaxisInsertPoint = originPointCopy 'y-axis text
   Dim nameInsertPoint As Point3d
   nameInsertPoint = originPointCopy
   Dim descInsertPoint As Point3d
   descInsertPoint = originPointCopy

'CREATE THE TEXT ELEMENTS
   Dim XTextElement As TextElement
   Set XTextElement = CreateTextElement1(textTemplate, XText, originPointCopy, Matrix3dIdentity)
   Dim YTextElement As TextElement
   Set YTextElement = CreateTextElement1(textTemplate, YText, originPointCopy, Matrix3dIdentity)
   Dim nameTextElement As TextElement
   Set nameTextElement = CreateTextElement1(textTemplate, nameString, originPointCopy, Matrix3dIdentity)
   Dim descTextElement As TextElement
   Set descTextElement = CreateTextElement1(textTemplate, DescString, originPointCopy, Matrix3dIdentity)
    
'GET TEXT METRICS
   Dim dummy As Double
   Dim XTextLen As Double
   XTextElement.GetTotalTextSize XTextLen, dummy
   Dim YTextLen As Double
   YTextElement.GetTotalTextSize YTextLen, dummy
   
   Dim XTextOffsets As Point2d
   XTextOffsets = XTextOffset(XTextLen, DropQuad, LineSpacing, extLineLength, fontSize)
   TextXaxisInsertPoint.X = TextXaxisInsertPoint.X + XTextOffsets.X
   TextXaxisInsertPoint.Y = TextXaxisInsertPoint.Y + XTextOffsets.Y
   XTextElement.origin = TextXaxisInsertPoint

   Dim YTextOffsets As Point2d
   YTextOffsets = YTextOffset(YTextLen, DropQuad, LineSpacing, extLineLength, fontSize)
   TextYaxisInsertPoint.X = TextYaxisInsertPoint.X + YTextOffsets.X
   TextYaxisInsertPoint.Y = TextYaxisInsertPoint.Y + YTextOffsets.Y
   YTextElement.origin = TextYaxisInsertPoint
   YTextElement.RotateAboutZ TextYaxisInsertPoint, Pi / 2#
   
'POSITION TEXT ACCORDING TO QUADRANT
   Dim partialOffset As Double
   partialOffset = extLineLength + fontSize
   Select Case DropQuad 'the quadrant of the deviation
      Case QUAD_NORTH_EAST
          nameInsertPoint.X = nameInsertPoint.X + partialOffset
          nameInsertPoint.Y = nameInsertPoint.Y + partialOffset + LineSpacing + LineSpacing
          
      Case QUAD_SOUTH_EAST
          nameInsertPoint.X = nameInsertPoint.X + partialOffset
          nameInsertPoint.Y = nameInsertPoint.Y - (extLineLength + LineSpacing)
          
      Case QUAD_SOUTH_WEST
          nameInsertPoint.X = nameInsertPoint.X - partialOffset
          nameInsertPoint.Y = nameInsertPoint.Y - (extLineLength + LineSpacing)
          ChangeJustification nameTextElement, msdTextJustificationRightCenter
          ChangeJustification descTextElement, msdTextJustificationRightCenter
          
      Case QUAD_NORTH_WEST
          nameInsertPoint.X = nameInsertPoint.X - partialOffset
          nameInsertPoint.Y = nameInsertPoint.Y + partialOffset + LineSpacing + LineSpacing
          ChangeJustification nameTextElement, msdTextJustificationRightCenter
          ChangeJustification descTextElement, msdTextJustificationRightCenter
    End Select
    descInsertPoint = nameInsertPoint
    descInsertPoint.Y = nameInsertPoint.Y - (fontSize + LineSpacing)
    nameTextElement.origin = nameInsertPoint
    descTextElement.origin = descInsertPoint

'RETURN TEXT ELEMENTS
    Set DimXEl = XTextElement
    Set DimYEl = YTextElement
    Set NameTextEl = nameTextElement
    Set DescTextEl = descTextElement
End Sub



Private Function CreateDropCell(ByVal X As Double, _
                                ByVal Y As Double, _
                                ByVal LabelText As String, _
                                ByVal label2Text As String, _
                                ogRefAzimuthString As String, _
                                originPoint As Point3d) As CellElement
'MAKE SURE LABEL IS NOT EMPTY STRING.  PERHAPS NOT NEEDED.
   If LabelText = "" Then
      LabelText = STRING_SPACE
   End If

'MAKE WORKING COPY
   Dim originPointCopy As Point3d
   originPointCopy = originPoint

'CALCULATE SOUTH AZIMUTH OF DIAGRAM
   Dim diagramSAz As Double
   Dim origPrec As Long
   Dim dirType As Integer
   Dim ogQuad As Integer
   If Not DirStringToSAz(ogRefAzimuthString, diagramSAz, origPrec, dirType, ogQuad) Then
'SHOULD NEVER GET HERE, CREATE ERROR IF IT DOES
      Err.Raise ERROR_NUM_523
   End If

'CALCULATE METRICS
   Dim fontSize As Double
   Dim legLength As Double
   Dim extLineLength As Double
   Dim halfExtLineLength As Double
   Dim LineSpacing As Double
   Dim rotAngleRadians As Double
   Dim MarkerDiameter As Double
   CalcDropMetrics diagramSAz, fontSize, legLength, extLineLength, halfExtLineLength, LineSpacing, rotAngleRadians, MarkerDiameter

'CREATE TEMPLATE FOR CREATING ELEMENTS
   Dim textTemplate As TextElement
   Set textTemplate = FrmDropDiagram.GetTextTemp()

'DETERMINE QUADRANT AND CREATE STRINGS FOR EACH OFFSET LABEL
   Dim quad As Integer
   Dim XText As String
   Dim YText As String
   DropQuad X, Y, quad, XText, YText
        
'DRAW THE CROSS
   Dim cellElements(0 To DIAGRAM_ELEMENT_DESCRIPTION2) As Element
   AddDropCrossToCell cellElements, textTemplate, originPointCopy, legLength

'DRAW THE AZIMUTH AND ARROW
   Dim desiredAzQuad As Long
   If quad = QUAD_NORTH_EAST Or quad = QUAD_NORTH_WEST Then
      desiredAzQuad = QUAD_SOUTH_WEST
   Else
      desiredAzQuad = QUAD_NORTH_WEST
   End If
   Dim AzimuthTextElement As TextElement
   Dim ArrowCell As CellElement
   CreateRefAzElements desiredAzQuad, _
                       AzimuthTextElement, _
                       ArrowCell, _
                       ogRefAzimuthString, _
                       textTemplate, _
                       originPointCopy, _
                       LineSpacing, _
                       fontSize, _
                       legLength, _
                       extLineLength
   Set cellElements(DIAGRAM_ELEMENT_AZIMUTH) = AzimuthTextElement
   Set cellElements(DIAGRAM_ELEMENT_ARROW) = ArrowCell

'DRAW EXTENSION LINES
   Dim ExtLine1 As LineElement
   Dim ExtLine2 As LineElement
   Dim marker As EllipseElement
   CreateExtLinesAndMarker ExtLine1, ExtLine2, marker, quad, originPointCopy, extLineLength, MarkerDiameter, textTemplate
   Set cellElements(6) = ExtLine1
   Set cellElements(7) = ExtLine2
    
'ADD MARKER CIRCLE TO CELL ARRAY
   Set cellElements(DIAGRAM_ELEMENT_CIRCLE) = marker

'CREATE THE TEXT ELEMENTS
   Dim XTextElement As TextElement
   Dim YTextElement As TextElement
   Dim LabelTextElement As TextElement
   Dim label2TextElement As TextElement
   CreateDimAndNameText XText, _
                        YText, _
                        LabelText, _
                        label2Text, _
                        quad, _
                        originPointCopy, _
                        textTemplate, _
                        LineSpacing, _
                        extLineLength, _
                        fontSize, _
                        XTextElement, _
                        YTextElement, _
                        LabelTextElement, _
                        label2TextElement

'ADD TEXT ELEMENTS TO CELL ARRAY
    Set cellElements(DIAGRAM_ELEMENT_XTEXT) = XTextElement
    Set cellElements(DIAGRAM_ELEMENT_YTEXT) = YTextElement
    Set cellElements(DIAGRAM_ELEMENT_DESCRIPTION) = LabelTextElement
    Set cellElements(DIAGRAM_ELEMENT_DESCRIPTION2) = label2TextElement

'CREATE THE CELL
    Set CreateDropCell = CreateCellElement1(vbNullString, cellElements, originPoint)
    CreateDropCell.RotateAboutZ originPoint, rotAngleRadians
End Function



Public Sub CreateExtLinesAndMarker(ByRef ExtLine1 As LineElement, _
                                   ByRef ExtLine2 As LineElement, _
                                   ByRef MarkerCircle As EllipseElement, _
                                   ByVal quadrant As Integer, _
                                   originPoint As Point3d, _
                                   ByVal extLineLength As Double, _
                                   ByVal markerRadius As Double, _
                                   ByVal template As Element)
   Dim originPointCopy As Point3d
   originPointCopy = originPoint
   
'INITIALIZE POINTS TO ORIGIN POINT
   Dim b1 As Point3d ' extension line end
   b1 = originPointCopy
   Dim b2 As Point3d ' extension line common to both
   b2.z = originPointCopy.z
   Dim b3 As Point3d ' extension line end
   b3 = originPointCopy

'MOVE POINTS ALONG CROSS ARMS APPROPRIATE TO QUADRANT
   Select Case quadrant
      Case QUAD_NORTH_EAST
         b1.Y = b1.Y + extLineLength
         b3.X = b3.X + extLineLength
      
      Case QUAD_SOUTH_EAST
         b1.Y = b1.Y - extLineLength
         b3.X = b3.X + extLineLength

      Case QUAD_SOUTH_WEST
         b1.Y = b1.Y - extLineLength
         b3.X = b3.X - extLineLength
      
      Case QUAD_NORTH_WEST
         b1.Y = b1.Y + extLineLength
         b3.X = b3.X - extLineLength
   End Select

'FORM THE INTERSECTION POINT
   b2.Y = b1.Y
   b2.X = b3.X

'CREATE ELEMENTS
   Set ExtLine1 = CreateLineElement2(template, b2, b1)
   Set ExtLine2 = CreateLineElement2(template, b2, b3)
   Set MarkerCircle = CreateEllipseElement2(template, b2, markerRadius, markerRadius, Matrix3dIdentity)
End Sub



Public Function CreateRefDirString(ogRefAzimuthString As String) As String
   Dim origPrec As Long
   Dim sAzimuth As Double
   Dim dirType As Integer
   Dim quad As Integer
   If Not DirStringToSAz(ogRefAzimuthString, sAzimuth, origPrec, dirType, quad) Then
'SHOULD NEVER GET HERE, CREATE ERROR IF IT DOES
      Err.Raise ERROR_NUM_524
   End If
   CreateRefDirString = SAzToDirectionStr(sAzimuth, origPrec, dirType, DropDiagramDirStyle())
End Function



Public Sub CreateRefAzElements(ByVal DesiredQuadrant As Integer, _
                               ByRef DirTextEl As TextElement, _
                               ByRef ArrowElement As CellElement, _
                               ByVal ogRefAzimuthString As String, _
                               ByVal textTemplate As Element, _
                               DiagramOriginPoint As Point3d, _
                               ByVal LineSpacing As Double, _
                               ByVal fontSize As Double, _
                               ByVal legLength As Double, _
                               ByVal extLineLength As Double)
   Dim originPointCopy As Point3d
   originPointCopy = DiagramOriginPoint

   Dim directionText As String
   directionText = CreateRefDirString(ogRefAzimuthString)
   
   Dim directionTextElement As TextElement
   Set directionTextElement = CreateTextElement1(textTemplate, directionText, originPointCopy, Matrix3dIdentity)
   
   Dim dirTextMet As Point2d
   directionTextElement.GetTotalTextSize dirTextMet.X, dirTextMet.Y
   
   Dim dirInsertPoint As Point3d
   dirInsertPoint = originPointCopy

   Select Case DesiredQuadrant
      Case QUAD_NORTH_EAST
         dirInsertPoint.X = dirInsertPoint.X + LineSpacing
         dirInsertPoint.Y = dirInsertPoint.Y + ((fontSize / 2#) + LineSpacing)
         Dim ArrowInsertPoint As Point3d
         ArrowInsertPoint = dirInsertPoint
         ArrowInsertPoint.X = originPointCopy.X + (legLength / 2#) + (dirTextMet.X + LineSpacing)
         
      Case QUAD_SOUTH_EAST
         dirInsertPoint.X = dirInsertPoint.X + LineSpacing
         dirInsertPoint.Y = dirInsertPoint.Y - ((fontSize / 2#) + LineSpacing)
         ArrowInsertPoint = dirInsertPoint
         ArrowInsertPoint.X = originPointCopy.X + (legLength / 2#) + (dirTextMet.X + LineSpacing)
         
      Case QUAD_SOUTH_WEST
         dirInsertPoint.X = dirInsertPoint.X - (dirTextMet.X + LineSpacing)
         dirInsertPoint.Y = dirInsertPoint.Y - ((fontSize / 2#) + LineSpacing)
         ArrowInsertPoint = dirInsertPoint
         ArrowInsertPoint.X = originPointCopy.X + (legLength / 2#)
         
      Case QUAD_NORTH_WEST
         dirInsertPoint.X = dirInsertPoint.X - (dirTextMet.X + LineSpacing)
         dirInsertPoint.Y = dirInsertPoint.Y + ((fontSize / 2#) + LineSpacing)
         ArrowInsertPoint = dirInsertPoint
         ArrowInsertPoint.X = originPointCopy.X + (legLength / 2#)
         
      Case QUAD_EXT_SOUTH_WEST 'LEFT OF QUAD 3
         dirInsertPoint.X = dirInsertPoint.X - (dirTextMet.X + LineSpacing + ARROW_LENGTH * fontSize + fontSize)
         dirInsertPoint.Y = dirInsertPoint.Y - ((fontSize / 2#) + LineSpacing)
         ArrowInsertPoint = dirInsertPoint
         ArrowInsertPoint.X = originPointCopy.X - (LineSpacing + ARROW_LENGTH * fontSize / 2#)
         
      Case QUAD_EXT_NORTH_WEST 'LEFT OF QUAD 4
         dirInsertPoint.X = dirInsertPoint.X - (dirTextMet.X + LineSpacing + ARROW_LENGTH * fontSize + fontSize)
         dirInsertPoint.Y = dirInsertPoint.Y + ((fontSize / 2) + LineSpacing)
         ArrowInsertPoint = dirInsertPoint
         ArrowInsertPoint.X = originPointCopy.X - (LineSpacing + ARROW_LENGTH * fontSize / 2#)
   End Select

'REPOSITION THE ELEMENT
   directionTextElement.origin = dirInsertPoint

'RETURN ELEMENTs
   Set DirTextEl = directionTextElement
   Set ArrowElement = CreateArrowCellMidOrigin(ArrowInsertPoint, fontSize, textTemplate)
End Sub



Private Function DetermineQuadrant(ByVal X As Double, ByVal Y As Double) As Integer
'DETERMINE QUADRANT FOR NEW VALUES
'HP QUADRANT STYLE
   If X >= 0 And Y >= 0 Then
      DetermineQuadrant = QUAD_NORTH_EAST
   ElseIf X >= 0 And Y < 0 Then
      DetermineQuadrant = QUAD_SOUTH_EAST
   ElseIf X < 0 And Y < 0 Then
      DetermineQuadrant = QUAD_SOUTH_WEST
   Else
      DetermineQuadrant = QUAD_NORTH_WEST
   End If
End Function



Private Sub DropCalc(recordPoint As Point3d, grndPoint As Point3d, ByVal refSAzDegrees As Double, X As Double, Y As Double)
'MAKE WORKING COPY
   Dim RecPoint As Point3d
   RecPoint = recordPoint
   Dim groundPoint As Point3d
   groundPoint = grndPoint

   Dim dX As Double
   Dim dY As Double
   dX = Round(groundPoint.X - RecPoint.X, DROP_DIAGRAM_PRECISION)
   dY = Round(groundPoint.Y - RecPoint.Y, DROP_DIAGRAM_PRECISION)

   If dX = 0# And dY = 0# Then
      X = 0#
      Y = 0#
   Else
      Dim direction As Double
      Dim distance As Double
      Inverse RecPoint, groundPoint, direction, distance
      Dim angleFromEast As Double
      angleFromEast = 180 - To360(refSAzDegrees, direction)
      X = Round(Cos(Radians(angleFromEast)) * distance, DROP_DIAGRAM_PRECISION)
      Y = Round(Sin(Radians(angleFromEast)) * distance, DROP_DIAGRAM_PRECISION)
   End If
End Sub



Public Function DropDiagramDirStyle() As Integer
   DropDiagramDirStyle = STYLE_ANGLE_NO_00_SEC + STYLE_ANGLE_CARET + STYLE_ANGLE_LEAD
End Function



Private Sub DropQuad(ByVal dropX As Double, _
                     ByVal dropY As Double, _
                     ByRef quadrant As Integer, _
                     ByRef XString As String, _
                     ByRef Ystring As String)
   dropX = Round(dropX, DROP_DIAGRAM_PRECISION)
   dropY = Round(dropY, DROP_DIAGRAM_PRECISION)
   quadrant = DetermineQuadrant(dropX, dropY)
   XString = DropValString(dropX)
   Ystring = DropValString(dropY)
End Sub



Public Sub DropQuadAndText(ByRef quadrant As Integer, _
                           ByRef XText As String, _
                           ByRef YText As String, _
                           recordPoint As Point3d, _
                           grndPoint As Point3d, _
                           ByVal refSAzDegrees As Double)
'DETERMINE QUADRANT AND CREATE STRINGS FOR EACH OFFSET LABEL
   Dim dropX As Double
   Dim dropY As Double
   DropCalc recordPoint, grndPoint, refSAzDegrees, dropX, dropY
   DropQuad dropX, dropY, quadrant, XText, YText
End Sub



Public Function DropValString(ByVal dropVal As Double) As String
   dropVal = Abs(dropVal)
   If dropVal < 100 Then
      DropValString = FormatNumber(dropVal, DROP_DIAGRAM_PRECISION, vbTrue, vbFalse, vbFalse)
   Else
      DropValString = "*****"
   End If
End Function



Public Function GetDropCell(originPoint As Point3d) As CellElement
'CALL THIS FUNCTION FOR PLACING THE DROP CELL
   If FrmDropDiagram.DescriptionCheckBox.value Then
      Dim label As String
      label = FrmDropDiagram.DescriptionTextBox.text
   Else
      label = STRING_SPACE
   End If

   If FrmDropDiagram.Desc2CheckBox.value Then
      Dim Label2
      Label2 = FrmDropDiagram.Desc2TextBox.text
   Else
      Label2 = STRING_SPACE
   End If

   Dim diagramSAz As Double
   Dim origPrec As Long
   Dim dirType As Integer
   Dim quad As Integer
   If Not DirStringToSAz(FrmDropDiagram.AzimuthTextBox.text, diagramSAz, origPrec, dirType, quad) Then
'SHOULD NEVER GET HERE, CREATE ERROR IF IT DOES
      Err.Raise ERROR_NUM_525
   End If

   Dim dX As Double
   Dim dY As Double
   DropCalc FrmDropDiagram.RecPoint, FrmDropDiagram.grndPoint, diagramSAz, dX, dY
   
   Set GetDropCell = CreateDropCell(dX, dY, label, Label2, FrmDropDiagram.AzimuthTextBox.text, originPoint)
End Function



Public Function XTextOffset(ByVal XTextLen As Double, _
                            ByVal DropQuad As Integer, _
                            ByVal LineSpacing As Double, _
                            ByVal extLineLength As Double, _
                            ByVal fontSize As Double) As Point2d
   Dim YOffset As Double
   YOffset = LineSpacing + extLineLength + (fontSize / 2#)
   Select Case DropQuad 'the quadrant of the deviation
      Case QUAD_NORTH_EAST 'NorthEast
          XTextOffset.X = LineSpacing
          XTextOffset.Y = YOffset
          
      Case QUAD_SOUTH_EAST  'SouthEast
          XTextOffset.X = LineSpacing
          XTextOffset.Y = -YOffset
          
      Case QUAD_SOUTH_WEST 'SouthWest
          XTextOffset.X = -(LineSpacing + XTextLen)
          XTextOffset.Y = -YOffset
          
      Case QUAD_NORTH_WEST  'NorthWest
          XTextOffset.X = -(LineSpacing + XTextLen)
          XTextOffset.Y = YOffset
    End Select
End Function



Public Function YTextOffset(ByVal YTextLen As Double, _
                            ByVal DropQuad As Integer, _
                            ByVal LineSpacing As Double, _
                            ByVal extLineLength As Double, _
                            ByVal fontSize As Double) As Point2d

   Dim XOffset As Double
   XOffset = LineSpacing + extLineLength + fontSize / 2#
   
   Select Case DropQuad 'the quadrant of the deviation
      Case QUAD_NORTH_EAST 'NorthEast
          YTextOffset.X = XOffset
          YTextOffset.Y = LineSpacing
          
      Case QUAD_SOUTH_EAST  'SouthEast
          YTextOffset.X = XOffset
          YTextOffset.Y = -(LineSpacing + YTextLen)
          
      Case QUAD_SOUTH_WEST 'SouthWest
          YTextOffset.X = -XOffset
          YTextOffset.Y = -(LineSpacing + YTextLen)
          
      Case QUAD_NORTH_WEST  'NorthWest
          YTextOffset.X = -XOffset
          YTextOffset.Y = LineSpacing
    End Select
End Function



'*************************************************************************************************************
'*********************************************REVISE DROP DIAGRAM*********************************************
Private Sub CalcDiagramValues(ByRef refSAzDegrees As Double, PointDescription As String, Description2 As String, ByRef X As Double, ByRef Y As Double)
'GETS VARIABLES FROM THE USER FORM, CALCULATES THE VALUES FOR THE DIAGRAM
'RETURNS THE VALUES IN THE PARAMETERS

'MAKE WORKING COPY, GET VALUES FROM USER FORM
   Dim recordPoint As Point3d
   recordPoint = FrmDropDiagram.RecPoint
   Dim groundPoint As Point3d
   groundPoint = FrmDropDiagram.grndPoint

'GET SOUTH AZIMUTH FROM DIRECTION STRING IN DIALOG BOX
   Dim origPrec As Long
   Dim dirType As Integer
   Dim quad As Integer
   If Not DirStringToSAz(FrmDropDiagram.AzimuthTextBox.text, refSAzDegrees, origPrec, dirType, quad) Then
'SHOULD NEVER GET HERE, CREATE ERROR IF IT DOES
      Err.Raise ERROR_NUM_526
   End If

'MAKE AN APPROPRIATE STRING FOR THE POINT DESCRIPTION
   If FrmDropDiagram.DescriptionCheckBox.value Then
     PointDescription = FrmDropDiagram.DescriptionTextBox.text
     If PointDescription = "" Then 'make sure it's not a NULL string
        PointDescription = STRING_SPACE
     End If
   Else
      PointDescription = STRING_SPACE
   End If

   If FrmDropDiagram.Desc2CheckBox.value Then
      Description2 = FrmDropDiagram.Desc2TextBox.text
      If PointDescription = "" Then 'make sure it's not a NULL string
         Description2 = STRING_SPACE
      End If
   Else
      Description2 = STRING_SPACE
   End If

'CALCULATE THE DROP
   DropCalc recordPoint, groundPoint, refSAzDegrees, X, Y
End Sub



Private Function CalcOldQuadrant(ByVal sAzimuth As Double, cellOrig As Point3d, centerCirc As Point3d) As Integer
'DETERMINE QUADRANT CURRENTLY IN DIAGRAM

'MAKE WORKING COPY
   Dim CellOrigin As Point3d
   CellOrigin = cellOrig
   Dim centerCircle As Point3d
   centerCircle = centerCirc

'GET POSITION RELATIVE TO AZIMUTH OF THE CROSS, WHERE AZIMUTH OF THE CROSS POINTS RIGHT
   Dim azimuthToCirc As Double
   Dim distanceToCirc As Double
   Inverse CellOrigin, centerCircle, azimuthToCirc, distanceToCirc
   Dim relativeAzimuth As Double
   relativeAzimuth = To360(sAzimuth, azimuthToCirc)

'DETERMINE WHAT THAT ROTATED QUADRANT WOULD BE
   If relativeAzimuth < 90 Then
      CalcOldQuadrant = QUAD_NORTH_WEST
   ElseIf relativeAzimuth < 180 Then
      CalcOldQuadrant = QUAD_NORTH_EAST
   ElseIf relativeAzimuth < 270 Then
      CalcOldQuadrant = QUAD_SOUTH_EAST
   Else
      CalcOldQuadrant = QUAD_SOUTH_WEST
   End If
End Function



Public Function DiagramElementTypesAreOkay(cellArray() As Element) As Boolean
'CHECKS DROP DIAGRAM CELL TO MAKE SURE EACH ELEMENT IN THE ARRAY IS THE CORRECT TYPE
'RETURNS TRUE IF CORRECT

'CHECK EACH ELEMENT
   If cellArray(0).IsLineElement = False Then
      DiagramElementTypesAreOkay = False
   ElseIf cellArray(1).IsLineElement = False Then
      DiagramElementTypesAreOkay = False
   ElseIf cellArray(2).IsLineElement = False Then
      DiagramElementTypesAreOkay = False
   ElseIf cellArray(3).IsLineElement = False Then
      DiagramElementTypesAreOkay = False
   ElseIf cellArray(DIAGRAM_ELEMENT_AZIMUTH).IsTextElement = False Then
      DiagramElementTypesAreOkay = False
   ElseIf cellArray(DIAGRAM_ELEMENT_ARROW).IsCellElement = False Then
      DiagramElementTypesAreOkay = False
   ElseIf cellArray(6).IsLineElement = False Then
      DiagramElementTypesAreOkay = False
   ElseIf cellArray(7).IsLineElement = False Then
      DiagramElementTypesAreOkay = False
   ElseIf cellArray(DIAGRAM_ELEMENT_CIRCLE).IsEllipseElement = False Then
      DiagramElementTypesAreOkay = False
   ElseIf cellArray(DIAGRAM_ELEMENT_XTEXT).IsTextElement = False Then
      DiagramElementTypesAreOkay = False
   ElseIf cellArray(DIAGRAM_ELEMENT_YTEXT).IsTextElement = False Then
      DiagramElementTypesAreOkay = False
   ElseIf cellArray(DIAGRAM_ELEMENT_DESCRIPTION).IsTextElement = False Then
      DiagramElementTypesAreOkay = False
   Else
   'ALL IS GOOD
      DiagramElementTypesAreOkay = True
   End If
   
   If UBound(cellArray) = DIAGRAM_ELEMENT_DESCRIPTION2 Then
      If Not cellArray(DIAGRAM_ELEMENT_DESCRIPTION2).IsTextElement Then
         DiagramElementTypesAreOkay = False
      End If
   End If
End Function



Public Function IsDiagramCell(theElement As Element, LeaderIDString As String) As Boolean
'CHECKS TYPE AND TAGS TO SEE IF THE ELEMENT IS A DIAGRAM CELL
'RETURNS TRUE IF IT IS, AND RETURNS THE TAG VALUE AS LeaderIDString STRING
   IsDiagramCell = IsSToolsCell(TAG_NAME_DROP, theElement, LeaderIDString)
End Function



Private Function NewTextQuadrant(ByVal X As Double, ByVal Y As Double) As Integer
'DETERMINE QUADRANT FOR NEW VALUES
'HP QUADRANT STYLE
   NewTextQuadrant = DetermineQuadrant(X, Y)
End Function



Private Function NotValidIDString(ByVal IDstring As String, LeaderLine As LineElement)
'RETURNS FALSE IF VALID AND THEN COPIES VALUE TO LeaderID
   If IDstring = "" Then
      NotValidIDString = True
      Exit Function
   Else
      On Error GoTo Element_Not_Found
      Dim Target As Element
      Set Target = ActiveModelReference.GetElementByID(DLongFromString(IDstring))
      If Target.IsLineElement Then
         Set LeaderLine = Target
         NotValidIDString = False
      Else
         NotValidIDString = True
      End If
      Exit Function
   End If

Element_Not_Found:
   NotValidIDString = True
End Function



Public Sub UpdateDiagram(cellArray() As Element, PickedCell As CellElement)
'GET AND CALCULATE THE DIAGRAM VALUES
   Dim NewdX As Double
   Dim NewdY As Double
   Dim refSAzDegrees As Double
   Dim PointDescription As String
   Dim Description2 As String
   CalcDiagramValues refSAzDegrees, PointDescription, Description2, NewdX, NewdY

'DETERMINE QUADRANT OF NEW TEXT
   Dim X As Double
   X = Round(NewdX, DROP_DIAGRAM_PRECISION)
   Dim Y As Double
   Y = Round(NewdY, DROP_DIAGRAM_PRECISION)
   Dim QuadrantNew As Integer
   QuadrantNew = NewTextQuadrant(X, Y)
   
   Dim NewIsZeroZero As Boolean
   NewIsZeroZero = False
   If X = 0 And Y = 0 Then
      NewIsZeroZero = True
   End If
         
'CREATE OFFSET TEXT STRINGS
   X = Abs(X)
   Y = Abs(Y)
   Dim NewXText As String
   NewXText = FormatNumber(X, DROP_DIAGRAM_PRECISION)
   Dim NewYText As String
   NewYText = FormatNumber(Y, DROP_DIAGRAM_PRECISION)

'DETERMINE QUADRANT OF OLD TEXT
   Dim CellOrigin As Point3d
   CellOrigin = PickedCell.origin
   Dim centerCircle As Point3d
   centerCircle = cellArray(DIAGRAM_ELEMENT_CIRCLE).AsEllipseElement.CenterPoint
   Dim QuadrantOld As Integer
   QuadrantOld = CalcOldQuadrant(refSAzDegrees, CellOrigin, centerCircle)
   
   If NewIsZeroZero Then
      QuadrantNew = QuadrantOld
   End If
   
'GET METRICS
   Dim characterSize As Double
   characterSize = cellArray(DIAGRAM_ELEMENT_XTEXT).AsTextElement.TextStyle.Width
   Dim LineSpacing As Double
   LineSpacing = characterSize / 3#

'CONVERT TO DECIMAL DEGREES FOR CALCULATIONS
   Dim azimuthInDegrees As Double
   azimuthInDegrees = refSAzDegrees

'GET AZIMUTH TEXT ELEMENT
   Dim AziTextElement As TextElement
   Set AziTextElement = cellArray(DIAGRAM_ELEMENT_AZIMUTH)

'CREATE THE NEW TEXT ELEMENTS AND THIER DIMENSIONS
   Dim textTemplate As TextElement
   Set textTemplate = CreateTextElement1(AziTextElement, "template", CellOrigin, Matrix3dIdentity)
   If FrmDropDiagram.ReviseColorCheckBox.value = True Then
      textTemplate.color = FrmDropDiagram.RevisonColorComboBox.text
   End If
   Dim NewXTextElement As TextElement
   Set NewXTextElement = CreateTextElement1(textTemplate, NewXText, CellOrigin, Matrix3dIdentity)
   Dim NewYTextElement As TextElement
   Set NewYTextElement = CreateTextElement1(textTemplate, NewYText, CellOrigin, Matrix3dIdentity)
   Dim NewXTextLen As Point2d
   NewXTextElement.GetTotalTextSize NewXTextLen.X, NewXTextLen.Y
   Dim NewYTextLen As Point2d
   NewYTextElement.GetTotalTextSize NewYTextLen.X, NewYTextLen.Y
   Dim NewDescriptionText As TextElement
   Set NewDescriptionText = CreateTextElement1(textTemplate, PointDescription, CellOrigin, Matrix3dIdentity)
   Dim NewDescription2Text As TextElement
   Set NewDescription2Text = CreateTextElement1(textTemplate, Description2, CellOrigin, Matrix3dIdentity)
   
'CALCULATE ROTATIONS FOR HORIZONTAL AND VERTICAL DIMENSIONS
   Dim angleRotHorRadians As Double
   angleRotHorRadians = Radians(270 - refSAzDegrees)
   Dim angleRotVerRadians As Double
   angleRotVerRadians = Radians(360 - refSAzDegrees)

'COPY OLD AND NEW DESCRIPTIONS AND TRIM THEM FOR DOING COMPARISONS
   Dim oldDescription As String
   oldDescription = Trim(cellArray(DIAGRAM_ELEMENT_DESCRIPTION).AsTextElement.text)
   Dim newDescription As String
   newDescription = Trim(PointDescription)
   
   If UBound(cellArray) = DIAGRAM_ELEMENT_DESCRIPTION2 Then
      Dim oldDescription2 As String
      oldDescription2 = Trim(cellArray(DIAGRAM_ELEMENT_DESCRIPTION2).AsTextElement.text)
   Else
      oldDescription2 = STRING_SPACE
   End If
   Dim newDescription2 As String
   newDescription2 = Trim(Description2)

'UPDATE THE DIAGRAM CELL
   If QuadrantOld = QuadrantNew Then
'OLD AND NEW END UP IN THE SAME QUADRANT
      WhenOldQuadEqualsNewQuad cellArray, _
                               PickedCell, _
                               CellOrigin, _
                               oldDescription, _
                               newDescription, _
                               QuadrantNew, _
                               QuadrantOld, _
                               NewXTextElement, _
                               NewYTextElement, _
                               NewXTextLen, _
                               NewYTextLen, _
                               NewDescriptionText, _
                               X, _
                               Y, _
                               refSAzDegrees, _
                               angleRotHorRadians, _
                               angleRotVerRadians, _
                               characterSize, _
                               LineSpacing, _
                               NewDescription2Text
   Else
'OLD AND NEW ARE DIFFERENT QUARANTS, DRAW NEW QUADRANT
      WhenOldQuadDiffNewQuad cellArray, _
                             PickedCell, _
                             CellOrigin, _
                             oldDescription, _
                             newDescription, _
                             QuadrantNew, _
                             QuadrantOld, _
                             NewXTextElement, _
                             NewYTextElement, _
                             NewXTextLen, _
                             NewYTextLen, _
                             NewDescriptionText, _
                             X, _
                             Y, _
                             refSAzDegrees, _
                             angleRotHorRadians, _
                             angleRotVerRadians, _
                             characterSize, _
                             LineSpacing, _
                             NewDescription2Text, _
                             oldDescription2, _
                             newDescription2
   End If

'UPDATE THE DRAWING
   PickedCell.Rewrite
   PickedCell.Redraw
End Sub



Public Sub UpdateLeaderLine(cellArray() As Element, LeaderIDString As String, PickedCell As CellElement)
'CALUCULATE METRICS
   Dim charSize As Double
   charSize = GetCharSize()

'GET ANCHOR POINT FOR LEADER
   Dim GroundPoint3d As Point3d
   GroundPoint3d = FrmDropDiagram.grndPoint()

'CALCULATE DIRECTION AND DISTANCE TO CENTER OF THE DIAGRAM
   Dim leaderAz As Double
   Dim leaderDis As Double
   Inverse GroundPoint3d, PickedCell.origin, leaderAz, leaderDis

'CHECK IF THERE IS A CURRENT LINE ELEMENT TO USE
   Dim NoValidID As Boolean
   Dim LeaderLine As LineElement
   NoValidID = NotValidIDString(LeaderIDString, LeaderLine)
   
'NO LINE TO USE, CREATE NEW ONE
   If FrmDropDiagram.LeaderCheckBox.value = True And NoValidID Then  'try and make a leader if long enough
      If leaderDis > (MIN_DROP_LEADER + TRIM_DROP_LEADER) * charSize Then 'far enough, create leader
         leaderDis = leaderDis - (TRIM_DROP_LEADER * charSize)
         Dim EndLeader As Point3d
         EndLeader = CoordFwdSAz(GroundPoint3d, leaderAz, leaderDis)
         EndLeader.z = PickedCell.origin.z
         Dim linePoints(0 To 2) As Point3d
         linePoints(0) = GroundPoint3d
         linePoints(1) = EndLeader
         linePoints(2) = FrmDropDiagram.RecPoint()
         Set LeaderLine = CreateLineElement1(cellArray(1).AsLineElement, linePoints)
         
         ActiveModelReference.AddElement LeaderLine
         LeaderLine.Redraw
      End If
'ELEMENT EXISTS, TRY AND MAKE IT FIT
   ElseIf NoValidID = False Then
      If leaderDis > (MIN_DROP_LEADER + TRIM_DROP_LEADER) * charSize Then 'far enough, create leader
         leaderDis = leaderDis - (TRIM_DROP_LEADER * charSize)
         EndLeader = CoordFwdSAz(GroundPoint3d, leaderAz, leaderDis)
         EndLeader.z = PickedCell.origin.z
         Dim newLeaderLine As LineElement
         linePoints(0) = GroundPoint3d
         linePoints(1) = EndLeader
         linePoints(2) = FrmDropDiagram.RecPoint()
         Set newLeaderLine = CreateLineElement1(LeaderLine, linePoints)
         ActiveModelReference.ReplaceElement LeaderLine, newLeaderLine
         newLeaderLine.Redraw
'DELETE EXISTING ELEMENT IF NOT ENOUGH ROOM
      Else
         ActiveModelReference.RemoveElement LeaderLine
      End If
   End If
End Sub

Attribute VB_Name = "DropDiagramILocateText"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit

Implements ILocateCommandEvents

Public hostForm As FrmDropDiagram

Private myLC As LocateCriteria

Private Sub ILocateCommandEvents_Accept(ByVal Element As Element, point As Point3d, ByVal view As view)

End Sub



Private Sub ILocateCommandEvents_Cleanup()
   hostForm.Show
   ClearCommandPromptArea
   CommandState.EnableAccuSnap
End Sub



Private Sub ILocateCommandEvents_Dynamics(point As Point3d, ByVal view As view, ByVal DrawMode As MsdDrawingMode)
   
End Sub



Private Sub ILocateCommandEvents_LocateFailed()
End Sub



Private Sub ILocateCommandEvents_LocateFilter(ByVal Element As Element, point As Point3d, Accepted As Boolean)
   Dim myEl As Element
   Set myEl = CommandState.GetLocatedElement(False)
   If myEl.IsTextElement Then
          hostForm.EnterText myEl.AsTextElement.text
   End If
   CommandState.StartDefaultCommand
   Accepted = False
End Sub



Private Sub ILocateCommandEvents_LocateReset()
   CommandState.StartDefaultCommand
End Sub



Private Sub ILocateCommandEvents_Start()
   
   Set myLC = CommandState.CreateLocateCriteria(False)
   myLC.ExcludeAllTypes
   myLC.IncludeType msdElementTypeText
   myLC.IncludeType msdElementTypeTextNode
   myLC.IncludeType msdElementTypeCellHeader
   CommandState.SetLocateCriteria myLC
   
   ShowCommand COMMAND_NAME_TRVERSE
   ShowPrompt "Pick Text Element/Reset"

   ActiveModelReference.UnselectAllElements

   CommandState.DisableAccuSnap
End Sub

Attribute VB_Name = "DropDiagramLocateUpdate"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit

Implements ILocateCommandEvents


Private Sub ILocateCommandEvents_Accept(ByVal Element As Element, point As Point3d, ByVal view As view)

End Sub



Private Sub ILocateCommandEvents_Cleanup()
   FrmDropDiagram.Show
End Sub



Private Sub ILocateCommandEvents_Dynamics(point As Point3d, ByVal view As view, ByVal DrawMode As MsdDrawingMode)

End Sub



Private Sub ILocateCommandEvents_LocateFailed()
End Sub



Private Sub ILocateCommandEvents_LocateFilter(ByVal Element As Element, point As Point3d, Accepted As Boolean)
'CHECK IF CAN WRITE TO FILE AND AMEND ELEMENT
   If ActiveModelReference.IsReadOnly = True Then
      ReadOnlyErrorMess
      CommandState.StartDefaultCommand
      Exit Sub
   End If

'CHECK TYPE AND TAGS TO SEE IF IT IS A DROP DIAGRAM CELL
   Dim PickedCell As CellElement
   Dim LeaderIDString As String
   Dim IsTagCorrect As Boolean
   IsTagCorrect = IsDiagramCell(Element, LeaderIDString)
   If IsTagCorrect Then
   'SO FAR, SO GOOD.  CONTINUE.
      Set PickedCell = Element
   Else
   'NOT A REVISABLE DIAGRAM, DO NOTHING
      CommandState.StartDefaultCommand
      Exit Sub
   End If

'LOAD ARRAY WITH THE CELL ELEMENT POINTERS
   Dim cellArray() As Element
   ReDim cellArray(0)
   Dim enumerator As ElementEnumerator
   Set enumerator = PickedCell.GetSubElements()
   Do While enumerator.MoveNext
      Set cellArray(UBound(cellArray)) = enumerator.Current
      ReDim Preserve cellArray(UBound(cellArray) + 1)
   Loop
   ReDim Preserve cellArray(UBound(cellArray) - 1)

'CHECK IF THERE IS THE CORRECT NUMBER OF ELEMENTS
   Dim ArrySize As Long
   ArrySize = UBound(cellArray)
   If ArrySize <> DIAGRAM_ELEMENT_DESCRIPTION And ArrySize <> DIAGRAM_ELEMENT_DESCRIPTION2 Then
'NOT CORRECT, END
      MsgBox "problem with diagram"
      CommandState.StartDefaultCommand
      Exit Sub
   End If

'CHECK IF THE CELL ELEMENTS ARE THE CORRECT TYPES
   If DiagramElementTypesAreOkay(cellArray) = False Then
   'NOT CORRECT, END
      MsgBox "problem with diagram"
      CommandState.StartDefaultCommand
      Exit Sub
   End If

'GET WHAT DIRECTION STRING SHOULD BE
   Dim directionText As String
   directionText = CreateRefDirString(FrmDropDiagram.AzimuthTextBox.text)
   
'CHECK DIRECTION STRING
   Dim MyTextElement As TextElement
   Set MyTextElement = cellArray(DIAGRAM_ELEMENT_AZIMUTH)
   If directionText <> ReplaceDegreeSymbol2(MyTextElement.text) Then
      MsgBox "direction mismatch"
      CommandState.StartDefaultCommand
      Exit Sub
   End If

'ALL IS WELL, DELETE THE TAGS
   PickedCell.DeleteAllTags

'UPDATE THE DIAGRAM
   UpdateDiagram cellArray, PickedCell

'TAKE CARE OF LEADER LINE
   UpdateLeaderLine cellArray, LeaderIDString, PickedCell

'END COMMAND
   CommandState.StartDefaultCommand
End Sub



Private Sub ILocateCommandEvents_LocateReset()
   CommandState.StartDefaultCommand
End Sub



Private Sub ILocateCommandEvents_Start()
   ActiveModelReference.UnselectAllElements
   
   ShowCommand COMMAND_NAME_DROP_DIAGRAM
   ShowPrompt "Pick Diagram to Revise/Reset to cancel"
   
   CommandState.EnableAccuSnap
   
   FrmDropDiagram.Hide
End Sub

Attribute VB_Name = "DropDiagramPrimitive"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit

Implements IPrimitiveCommandEvents


Private Sub IPrimitiveCommandEvents_Cleanup()
   FrmDropDiagram.Show
   ClearCommandPromptArea
   CommandState.EnableAccuSnap
End Sub



Private Sub IPrimitiveCommandEvents_DataPoint(point As Point3d, ByVal view As view)
'CHECK IF CAN WRITE TO FILE
   If ActiveModelReference.IsReadOnly = True Then
'NO CAN WRITE TO FILE, GIVE ERROR
      ReadOnlyErrorMess
   Else
'CAN WRITE TO FILE, DO IT
'MAKE WORKING COPY
      Dim CurrentPosition As Point3d
      CurrentPosition = point

'ADD DIAGRAM CELL TO FILE
      Dim DropCell As CellElement
      Set DropCell = GetDropCell(CurrentPosition)
      ActiveModelReference.AddElement DropCell

'INITIALIZE THE VALUE FOR THE DIAGRAM CELL TAG
      Dim TagValue As String
      TagValue = ""

'DRAW LEADER LINE IF OPTION IS CHOSEN
      If FrmDropDiagram.LeaderCheckBox.value = True Then 'try and make a leader if long enough

'CALCULATE METRICS
         Dim charSize As Double
         charSize = GetCharSize()
                           
'CALCULATE DIRECTION AND DISTANCE ANCHOR POINT TO CURRENT POSITION
         Dim GroundPoint3d As Point3d
         GroundPoint3d = FrmDropDiagram.grndPoint()
         Dim leaderAz As Double
         Dim leaderDis As Double
         Inverse GroundPoint3d, CurrentPosition, leaderAz, leaderDis

'DRAW LEADER LINE IF FAR ENOUGH FROM THE ANCHOR POINT
         If leaderDis > (MIN_DROP_LEADER + TRIM_DROP_LEADER) * charSize Then 'far enough, create leader
            Dim template As Element
            Set template = FrmDropDiagram.GetLineTemp()
            leaderDis = leaderDis - (TRIM_DROP_LEADER * charSize)
            Dim EndLeader As Point3d
            EndLeader = CoordFwdSAz(GroundPoint3d, leaderAz, leaderDis)
            EndLeader.z = CurrentPosition.z
            
            Dim linePoints(0 To 2) As Point3d
            linePoints(0) = GroundPoint3d
            linePoints(1) = EndLeader
            linePoints(2) = FrmDropDiagram.RecPoint()
            
            Dim LeaderLine As LineElement
            Set LeaderLine = CreateLineElement1(template, linePoints)
        
'ADD IT TO THE FILE
            ActiveModelReference.AddElement LeaderLine
             
'ADD THE ID STRING TO THE DIAGRAM CELL TAG
            Dim ID As DLong
            ID = LeaderLine.ID
            TagValue = DLongToString(ID)  'embed id in element tag
            LeaderLine.Redraw
         End If
      End If
    
'TAG THE CELL
      TagMyElement DropCell, TAG_NAME_DROP, TagValue

'MAKE SURE THE DIAGRAM DISPLAYS
      DropCell.Rewrite
      
   End If
'END THIS TOOL
   CommandState.StartDefaultCommand
End Sub




Private Sub IPrimitiveCommandEvents_Dynamics(point As Point3d, ByVal view As view, ByVal DrawMode As MsdDrawingMode)
'DRAW TETHER LINE
   DrawTether FrmDropDiagram.grndPoint(), point, DrawMode
   DrawTether FrmDropDiagram.RecPoint(), point, DrawMode

'DRAW THE DIAGRAM
   Dim DropCell As CellElement
   Set DropCell = GetDropCell(point)
   DropCell.Redraw DrawMode
End Sub




Private Sub IPrimitiveCommandEvents_Keyin(ByVal Keyin As String)

End Sub




Private Sub IPrimitiveCommandEvents_Reset()
   CommandState.StartDefaultCommand
End Sub




Private Sub IPrimitiveCommandEvents_Start()
   FrmDropDiagram.Hide
   
   ShowCommand COMMAND_NAME_DROP_DIAGRAM
   ShowPrompt "Pick where to place diagram"
   
   CommandState.DisableAccuSnap
   CommandState.StartDynamics
End Sub

Attribute VB_Name = "DropDiagramUpdateQuadsDiff"
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit

Private RevisedTextTemplate As TextElement

Public Sub WhenOldQuadDiffNewQuad(cellArray() As Element, _
                                  PickedCell As CellElement, _
                                  CellOrigin As Point3d, _
                                  oldDescription As String, _
                                  newDescription As String, _
                                  QuadrantNew As Integer, _
                                  QuadrantOld As Integer, _
                                  NewXTextElement As TextElement, _
                                  NewYTextElement As TextElement, _
                                  NewXTextLen As Point2d, _
                                  NewYTextLen As Point2d, _
                                  NewDescriptionText As TextElement, _
                                  ByVal X As Double, _
                                  ByVal Y As Double, _
                                  ByVal azimuthInDegrees As Double, _
                                  ByVal angleRotHorRadians As Double, _
                                  ByVal angleRotVerRadians As Double, _
                                  ByVal characterSize As Double, _
                                  ByVal LineSpacing As Double, _
                                  NewDescription2Text As TextElement, _
                                  oldDescription2 As String, _
                                  newDescription2 As String)
'MAKE TEMPLATE FOR REVISION TEXT
   Set RevisedTextTemplate = CreateTextElement1(NewXTextElement, "template", CellOrigin, Matrix3dIdentity)

'CHECK IF SINGLE DESCRIPTION OR DOUBLE DESCRIPTION
   Dim IsDoubleDesc As Boolean
   If UBound(cellArray) = DIAGRAM_ELEMENT_DESCRIPTION2 Then
      IsDoubleDesc = True
   Else
      IsDoubleDesc = False
   End If

'CROSS OUT X-VALUE
   Dim XTextLen As Point2d
   cellArray(DIAGRAM_ELEMENT_XTEXT).AsTextElement.GetTotalTextSize XTextLen.X, XTextLen.Y
   Dim LineOutStart As Point3d
   LineOutStart = cellArray(DIAGRAM_ELEMENT_XTEXT).AsTextElement.origin
   Dim LineOutEnd As Point3d
   LineOutEnd = CoordFwdSAz(LineOutStart, azimuthInDegrees, XTextLen.X)
   Dim LineOutXElement As LineElement
   Set LineOutXElement = CreateLineElement2(RevisedTextTemplate, LineOutStart, LineOutEnd)
   PickedCell.AppendToCellOfCurrentElement LineOutXElement
         
'CROSS OUT Y-VALUE
   Dim YTextLen As Point2d
   cellArray(DIAGRAM_ELEMENT_YTEXT).AsTextElement.GetTotalTextSize YTextLen.X, YTextLen.Y
   LineOutStart = cellArray(DIAGRAM_ELEMENT_YTEXT).AsTextElement.origin
   LineOutEnd = CoordFwdSAz(LineOutStart, azimuthInDegrees - 90, YTextLen.X)
   Dim LineOutYElement As LineElement
   Set LineOutYElement = CreateLineElement2(RevisedTextTemplate, LineOutStart, LineOutEnd)
   PickedCell.AppendToCellOfCurrentElement LineOutYElement
         
'CROSS OUT OLD DESCRIPTION IF APPROPRIATE
   Dim OldTextElement As TextElement
   Set OldTextElement = cellArray(DIAGRAM_ELEMENT_DESCRIPTION)
   CrossOutOldDesc cellArray, PickedCell, OldTextElement, QuadrantOld, oldDescription, newDescription, azimuthInDegrees
   If IsDoubleDesc Then
      Set OldTextElement = cellArray(DIAGRAM_ELEMENT_DESCRIPTION2)
      CrossOutOldDesc cellArray, PickedCell, OldTextElement, QuadrantOld, oldDescription2, newDescription2, azimuthInDegrees
   End If
            
'DRAW EXTENSION LINES AND CIRCLE, CALCULATES THE NEWPI
   Dim newPI As Point3d
   Dim azimuthToNewPI As Double
   DrawExtensionLinesAndCircle cellArray, PickedCell, QuadrantNew, azimuthInDegrees, CellOrigin, NewDescriptionText, azimuthToNewPI, newPI

'CALCULATE POSITIONS FOR DESCRIPTIONS
   Dim descOffset As Double
   descOffset = characterSize + LineSpacing
   Select Case QuadrantNew
      Case QUAD_NORTH_EAST
         Dim DescInsertionPoint As Point3d
         DescInsertionPoint = CoordFwdSAz(newPI, azimuthToNewPI + 45#, characterSize)   'MOVE RIGHT
         DescInsertionPoint = CoordFwdSAz(DescInsertionPoint, azimuthToNewPI - 45#, descOffset + LineSpacing)  'MOVE UP
         Dim DescInsertion2Point As Point3d
         DescInsertion2Point = CoordFwdSAz(DescInsertionPoint, azimuthToNewPI + 135#, descOffset)  'MOVE DOWN
         
      Case QUAD_SOUTH_EAST
         DescInsertionPoint = CoordFwdSAz(newPI, azimuthToNewPI + 45#, LineSpacing)  'MOVE DOWN
         DescInsertionPoint = CoordFwdSAz(DescInsertionPoint, azimuthToNewPI - 45#, characterSize)  'MOVE RIGHT
         DescInsertion2Point = CoordFwdSAz(DescInsertionPoint, azimuthToNewPI + 45#, descOffset)  'MOVE DOWN
         
      Case QUAD_SOUTH_WEST
         DescInsertionPoint = CoordFwdSAz(newPI, azimuthToNewPI + 45#, characterSize)  'MOVE LEFT
         DescInsertionPoint = CoordFwdSAz(DescInsertionPoint, azimuthToNewPI - 45#, LineSpacing)  'MOVE DOWN
         DescInsertion2Point = CoordFwdSAz(DescInsertionPoint, azimuthToNewPI - 45#, descOffset)  'MOVE DOWN
         ChangeJustification NewDescription2Text, msdTextJustificationRightCenter
         
      Case QUAD_NORTH_WEST
         DescInsertionPoint = CoordFwdSAz(newPI, azimuthToNewPI - 45#, characterSize)   'MOVE LEFT
         DescInsertionPoint = CoordFwdSAz(DescInsertionPoint, azimuthToNewPI + 45, descOffset + LineSpacing) 'MOVE UP
         DescInsertion2Point = CoordFwdSAz(DescInsertionPoint, azimuthToNewPI - 135, descOffset) 'MOVE DOWN
         ChangeJustification NewDescription2Text, msdTextJustificationRightCenter
   End Select

'DRAW DESCRPITION 1
   NewDescriptionText.origin = DescInsertionPoint
   NewDescriptionText.RotateAboutZ DescInsertionPoint, angleRotHorRadians
   PickedCell.AppendToCellOfCurrentElement NewDescriptionText

'DRAW DESCRIPTION 2
   NewDescription2Text.origin = DescInsertion2Point
   NewDescription2Text.RotateAboutZ DescInsertion2Point, angleRotHorRadians
   PickedCell.AppendToCellOfCurrentElement NewDescription2Text

'DRAW THE X AND Y VALUES
   DrawTheDimensionText cellArray, _
                        PickedCell, _
                        NewXTextElement, _
                        NewYTextElement, _
                        NewXTextLen, _
                        NewYTextLen, _
                        QuadrantNew, _
                        azimuthInDegrees, _
                        CellOrigin, _
                        characterSize, _
                        LineSpacing, _
                        angleRotVerRadians, _
                        angleRotHorRadians, _
                        azimuthToNewPI, _
                        newPI
            
'RELOCATE AZIMUTH AND ARROW AS NEEDED
   RelocateAzimuthAndArrow cellArray, _
                           PickedCell, _
                           QuadrantOld, _
                           QuadrantNew, _
                           azimuthInDegrees, _
                           CellOrigin, _
                           characterSize, _
                           LineSpacing, _
                           angleRotVerRadians, _
                           angleRotHorRadians
End Sub



Private Sub CrossOutOldDesc(cellArray() As Element, _
                            PickedCell As CellElement, _
                            DescElement As TextElement, _
                            ByVal QuadrantOld As Integer, _
                            ByVal oldDescription As String, _
                            ByVal newDescription As String, _
                            ByVal azimuthInDegrees As Double)
'CROSS OUT OLD DESCRIPTION IF APPROPRIATE
   If Trim(oldDescription) <> "" And Trim(newDescription) <> "" Then
   'BOTH ARE NOT EMPTY STRINGS, CROSS THE OLD ONE OUT
      'CROSS OUT OLD DESCRIPTION
       
'DETERMINE WHERE TO DRAW THE CROSS-OUT LINE
      Dim DescOldStartPoint As Point3d
      DescOldStartPoint = DescElement.AsTextElement.origin
      Dim oldDescLen As Point2d
      DescElement.AsTextElement.GetTotalTextSize oldDescLen.X, oldDescLen.Y
      Select Case QuadrantOld
         Case QUAD_NORTH_EAST
            Dim DescOldEndPoint As Point3d
            DescOldEndPoint = CoordFwdSAz(DescOldStartPoint, azimuthInDegrees, oldDescLen.X)
         
         Case QUAD_SOUTH_EAST
            DescOldEndPoint = CoordFwdSAz(DescOldStartPoint, azimuthInDegrees, oldDescLen.X)
         
         Case QUAD_SOUTH_WEST
            DescOldEndPoint = CoordFwdSAz(DescOldStartPoint, azimuthInDegrees + 180#, oldDescLen.X)
         
         Case QUAD_NORTH_WEST
            DescOldEndPoint = CoordFwdSAz(DescOldStartPoint, azimuthInDegrees + 180#, oldDescLen.X)
      End Select
      
      'CREATE THE CROSS-OUT LINE
      Dim LineOutDesc As LineElement
      Set LineOutDesc = CreateLineElement2(RevisedTextTemplate, DescOldStartPoint, DescOldEndPoint)
      
      'ADD IT TO THE CELL
      PickedCell.AppendToCellOfCurrentElement LineOutDesc
   End If

End Sub

Private Sub DrawExtensionLinesAndCircle(cellArray() As Element, _
                                        PickedCell As CellElement, _
                                        QuadrantNew As Integer, _
                                        ByVal azimuthInDegrees As Double, _
                                        CellOrigin As Point3d, _
                                        NewDescriptionText As TextElement, _
                                        ByRef azimuthToNewPI As Double, _
                                        ByRef newPI As Point3d)
'DRAW EXTENSION LINES AND CIRCLE
'RETURNS THE NEWPI AND AZIMUTH TO NEWPI
   
   'CALCULATE AZIMUTH TO NEW DIMENSION INTERSECTION ON THE DIAGONAL FROM THE CENTER
   'CHANGE THE TEXT JUSTIFICATION WHERE NEEDED

   Select Case QuadrantNew
      Case QUAD_NORTH_EAST
         azimuthToNewPI = azimuthInDegrees - 45#  ' in decimal degrees
         
      Case QUAD_SOUTH_EAST
         azimuthToNewPI = azimuthInDegrees + 45#  ' in decimal degrees
         
      Case QUAD_SOUTH_WEST
         azimuthToNewPI = azimuthInDegrees + 135#  ' in decimal degrees
         ChangeJustification NewDescriptionText, msdTextJustificationRightCenter
         
      Case QUAD_NORTH_WEST
         azimuthToNewPI = azimuthInDegrees + 225#  ' in decimal degrees
         ChangeJustification NewDescriptionText, msdTextJustificationRightCenter
   End Select
   
   'DRAW THE NEW DIMENSION LINES AND MAKE THEM PART OF THE CELL
      'CALCULATE THE DISTANCE FROM THE ORIGINAL CIRCLE TO THE CENTER OF THE CROSS
   Dim centerCircle As Point3d
   centerCircle = cellArray(DIAGRAM_ELEMENT_CIRCLE).AsEllipseElement.CenterPoint
   Dim azimuthToCirc As Double
   Dim distanceToCirc As Double
   Inverse CellOrigin, centerCircle, azimuthToCirc, distanceToCirc
   
      'CALCULATE THE INTERSECTION POINT FOR THE NEW DIMENSION LINES
   newPI = CoordFwdSAz(CellOrigin, azimuthToNewPI, distanceToCirc)
   Dim tempPointEnd As Point3d
   tempPointEnd = CoordFwdSAz(newPI, azimuthToNewPI + 135#, distanceToCirc / Sqr(2#))
   
      'DRAW THE NEW DIMENSION LINE, ADD IT TO THE CELL
   Dim DimLineElement As LineElement
   Set DimLineElement = CreateLineElement2(RevisedTextTemplate, newPI, tempPointEnd)
   PickedCell.AppendToCellOfCurrentElement DimLineElement
            
      'DRAW THE OTHER NEW DIMENSION LINE, ADD IT TO THE CELL
   tempPointEnd = CoordFwdSAz(newPI, azimuthToNewPI - 135#, distanceToCirc / Sqr(2#))
   Dim OtherDimLineElement As LineElement
   Set OtherDimLineElement = CreateLineElement2(RevisedTextTemplate, newPI, tempPointEnd)
   PickedCell.AppendToCellOfCurrentElement OtherDimLineElement

   'DRAW THE CIRCLE AT THE INTERSECTION POINT
   Dim theCirc As EllipseElement
   Set theCirc = CreateEllipseElement2(RevisedTextTemplate, newPI, _
                                       cellArray(DIAGRAM_ELEMENT_CIRCLE).AsEllipseElement.PrimaryRadius, _
                                       cellArray(DIAGRAM_ELEMENT_CIRCLE).AsEllipseElement.PrimaryRadius, _
                                       Matrix3dIdentity)
      
      'ADD IT TO THE CELL
   PickedCell.AppendToCellOfCurrentElement theCirc
End Sub


Private Sub DrawTheDimensionText(cellArray() As Element, _
                                 PickedCell As CellElement, _
                                 NewXTextElement As TextElement, _
                                 NewYTextElement As TextElement, _
                                 NewXTextLen As Point2d, _
                                 NewYTextLen As Point2d, _
                                 ByVal QuadrantNew As Integer, _
                                 ByVal azimuthInDegrees As Double, _
                                 CellOrigin As Point3d, _
                                 ByVal characterSize As Double, _
                                 ByVal LineSpacing As Double, _
                                 ByVal angleRotVerRadians As Double, _
                                 ByVal angleRotHorRadians As Double, _
                                 ByVal azimuthToNewPI As Double, _
                                 newPI As Point3d)
'CALCULATE METRICS
   Dim distanceToCirc As Double
   Dim AZI As Double
   Inverse CellOrigin, newPI, AZI, distanceToCirc

'DRAW THE X AND Y VALUES
   Select Case QuadrantNew
      Case QUAD_NORTH_EAST
      'DRAW X-VALUE, ADD IT TO THE CELL
         Dim DimXInsertionPoint As Point3d
         DimXInsertionPoint = CoordFwdSAz(CellOrigin, azimuthInDegrees - 90#, distanceToCirc / Sqr(2#) + LineSpacing + characterSize / 2#)
         DimXInsertionPoint = CoordFwdSAz(DimXInsertionPoint, azimuthInDegrees, LineSpacing)
         NewXTextElement.origin = DimXInsertionPoint
         NewXTextElement.RotateAboutZ DimXInsertionPoint, angleRotHorRadians
         PickedCell.AppendToCellOfCurrentElement NewXTextElement

      'DRAW THE Y-VALUE, ADD IT TO THE CELL
         Dim DimYInsertionPoint As Point3d
         DimYInsertionPoint = CoordFwdSAz(CellOrigin, azimuthInDegrees, distanceToCirc / Sqr(2#) + LineSpacing + characterSize / 2#)
         DimYInsertionPoint = CoordFwdSAz(DimYInsertionPoint, azimuthInDegrees - 90#, LineSpacing)
         NewYTextElement.origin = DimYInsertionPoint
         NewYTextElement.RotateAboutZ DimYInsertionPoint, angleRotVerRadians
         PickedCell.AppendToCellOfCurrentElement NewYTextElement
                
      Case QUAD_SOUTH_EAST
      'DRAW X-VALUE, ADD IT TO THE CELL
         DimXInsertionPoint = CoordFwdSAz(CellOrigin, azimuthInDegrees + 90#, distanceToCirc / Sqr(2#) + LineSpacing + characterSize / 2#)
         DimXInsertionPoint = CoordFwdSAz(DimXInsertionPoint, azimuthInDegrees, LineSpacing)
         NewXTextElement.origin = DimXInsertionPoint
         NewXTextElement.RotateAboutZ DimXInsertionPoint, angleRotHorRadians
         PickedCell.AppendToCellOfCurrentElement NewXTextElement

      'DRAW THE Y-VALUE, ADD IT TO THE CELL
         DimYInsertionPoint = CoordFwdSAz(CellOrigin, azimuthInDegrees, distanceToCirc / Sqr(2#) + LineSpacing + characterSize / 2#)
         DimYInsertionPoint = CoordFwdSAz(DimYInsertionPoint, azimuthInDegrees + 90#, LineSpacing + NewYTextLen.X)
         NewYTextElement.origin = DimYInsertionPoint
         NewYTextElement.RotateAboutZ DimYInsertionPoint, angleRotVerRadians
         PickedCell.AppendToCellOfCurrentElement NewYTextElement
                                 
      Case QUAD_SOUTH_WEST
      'DRAW X-VALUE, ADD IT TO THE CELL
         DimXInsertionPoint = CoordFwdSAz(CellOrigin, azimuthInDegrees + 180#, LineSpacing + NewXTextLen.X)
         DimXInsertionPoint = CoordFwdSAz(DimXInsertionPoint, azimuthInDegrees + 90#, distanceToCirc / Sqr(2#) + LineSpacing + characterSize / 2#)
         NewXTextElement.origin = DimXInsertionPoint
         NewXTextElement.RotateAboutZ DimXInsertionPoint, angleRotHorRadians
         PickedCell.AppendToCellOfCurrentElement NewXTextElement

      'DRAW THE Y-VALUE, ADD IT TO THE CELL
         DimYInsertionPoint = CoordFwdSAz(CellOrigin, azimuthInDegrees + 180#, distanceToCirc / Sqr(2#) + LineSpacing + characterSize / 2#)
         DimYInsertionPoint = CoordFwdSAz(DimYInsertionPoint, azimuthInDegrees + 90#, LineSpacing + NewYTextLen.X)
         NewYTextElement.origin = DimYInsertionPoint
         NewYTextElement.RotateAboutZ DimYInsertionPoint, angleRotVerRadians
         PickedCell.AppendToCellOfCurrentElement NewYTextElement
                               
      Case QUAD_NORTH_WEST
      'DRAW X-VALUE, ADD IT TO THE CELL
         DimXInsertionPoint = CoordFwdSAz(newPI, azimuthToNewPI + 135#, distanceToCirc / Sqr(2#) - (NewXTextLen.X + LineSpacing))
         DimXInsertionPoint = CoordFwdSAz(DimXInsertionPoint, azimuthToNewPI + 45#, LineSpacing + characterSize / 2#)
         NewXTextElement.origin = DimXInsertionPoint
         NewXTextElement.RotateAboutZ DimXInsertionPoint, angleRotHorRadians
         PickedCell.AppendToCellOfCurrentElement NewXTextElement

      'DRAW THE Y-VALUE, ADD IT TO THE CELL
         DimYInsertionPoint = CoordFwdSAz(newPI, azimuthInDegrees + 180#, LineSpacing + characterSize / 2#)
         DimYInsertionPoint = CoordFwdSAz(DimYInsertionPoint, azimuthInDegrees + 90#, distanceToCirc / Sqr(2#) - LineSpacing)
         NewYTextElement.origin = DimYInsertionPoint
         NewYTextElement.RotateAboutZ DimYInsertionPoint, angleRotVerRadians
         PickedCell.AppendToCellOfCurrentElement NewYTextElement
   End Select
End Sub

Private Sub RelocateAzimuthAndArrow(cellArray() As Element, _
                                    PickedCell As CellElement, _
                                    ByVal QuadrantOld As Integer, _
                                    ByVal QuadrantNew As Integer, _
                                    ByVal azimuthInDegrees As Double, _
                                    CellOrigin As Point3d, _
                                    ByVal characterSize As Double, _
                                    ByVal LineSpacing As Double, _
                                    ByVal angleRotVerRadians As Double, _
                                    ByVal angleRotHorRadians As Double)

'MOVE AZIMUTH AND ARROW AS NEEDED
   If (QuadrantOld = QUAD_NORTH_EAST And QuadrantNew = QUAD_SOUTH_EAST) Or _
      (QuadrantOld = QUAD_SOUTH_EAST And QuadrantNew = QUAD_NORTH_EAST) Or _
      (QuadrantOld = QUAD_NORTH_EAST And QuadrantNew = QUAD_SOUTH_WEST) Or _
      (QuadrantOld = QUAD_SOUTH_WEST And QuadrantNew = QUAD_NORTH_EAST) Then
'MOVE TO TOP-LEFT OF LINE
   'GET AZIMUTH TEXT ELEMENT AND IT'S DIMENSIONS
      Dim AziTextElement As TextElement
      Set AziTextElement = cellArray(DIAGRAM_ELEMENT_AZIMUTH)
      Dim AziTextLen As Point2d
      AziTextElement.GetTotalTextSize AziTextLen.X, AziTextLen.Y
            
   'CALCULATE POSITION FOR NEW AZIMUTH TEXT
      Dim NewAzimuthPoint As Point3d
      NewAzimuthPoint = CoordFwdSAz(CellOrigin, azimuthInDegrees - 180#, LineSpacing + AziTextLen.X + characterSize + ARROW_LENGTH * characterSize)
      NewAzimuthPoint = CoordFwdSAz(NewAzimuthPoint, azimuthInDegrees - 90#, LineSpacing + characterSize / 2#)
   
   'CREATE THE NEW AZIMUTH TEXT, REPOSITION IT, ADD IT TO CELL
      Dim moveAzimuthText As TextElement
      Set moveAzimuthText = CreateTextElement1(AziTextElement, AziTextElement.text, NewAzimuthPoint, Matrix3dIdentity)
      moveAzimuthText.RotateAboutZ NewAzimuthPoint, angleRotHorRadians
      PickedCell.AppendToCellOfCurrentElement moveAzimuthText
            
   'CREATE THE NEW ARROW, REPOSITION IT, ADD IT TO CELL
      Dim moveArrowPoint As Point3d
      moveArrowPoint = CoordFwdSAz(NewAzimuthPoint, azimuthInDegrees, AziTextLen.X + characterSize * ARROW_LENGTH)
      Dim moveArrow As CellElement
      Set moveArrow = CreateArrowCellMidOrigin(moveArrowPoint, characterSize, AziTextElement)
      moveArrow.RotateAboutZ moveArrowPoint, angleRotHorRadians
      PickedCell.AppendToCellOfCurrentElement moveArrow

   'DELETE ORIGINAL ARROW AND AZIMUTH TEXT
      RemoveArrowAndAzimuthElements PickedCell
  
   ElseIf (QuadrantOld = QUAD_SOUTH_EAST And QuadrantNew = QUAD_NORTH_WEST) Or _
          (QuadrantOld = QUAD_NORTH_WEST And QuadrantNew = QUAD_SOUTH_EAST) Or _
          (QuadrantOld = QUAD_SOUTH_WEST And QuadrantNew = QUAD_NORTH_WEST) Or _
          (QuadrantOld = QUAD_NORTH_WEST And QuadrantNew = QUAD_SOUTH_WEST) Then
'MOVE TO BOTTOM-LEFT OF LINE
   'CALCULATE POSITION FOR NEW AZIMUTH TEXT
      Set AziTextElement = cellArray(DIAGRAM_ELEMENT_AZIMUTH)
      AziTextElement.GetTotalTextSize AziTextLen.X, AziTextLen.Y
      NewAzimuthPoint = CoordFwdSAz(CellOrigin, azimuthInDegrees, LineSpacing)
      NewAzimuthPoint = CoordFwdSAz(NewAzimuthPoint, azimuthInDegrees - 90#, LineSpacing + characterSize / 2#)
    
   'CREATE THE NEW AZIMUTH TEXT, REPOSITION IT, ADD IT TO CELL
      Set moveAzimuthText = CreateTextElement1(AziTextElement, AziTextElement.text, NewAzimuthPoint, Matrix3dIdentity)
      moveAzimuthText.RotateAboutZ NewAzimuthPoint, angleRotHorRadians
      PickedCell.AppendToCellOfCurrentElement moveAzimuthText
            
   'CREATE THE NEW ARROW, REPOSITION IT, ADD IT TO CELL
      moveArrowPoint = CoordFwdSAz(NewAzimuthPoint, azimuthInDegrees, AziTextLen.X + characterSize * 2#)
      Set moveArrow = CreateArrowCellMidOrigin(moveArrowPoint, characterSize, AziTextElement)
      moveArrow.RotateAboutZ moveArrowPoint, angleRotHorRadians
      PickedCell.AppendToCellOfCurrentElement moveArrow

   'DELETE ORIGINAL ARROW AND AZIMUTH TEXT
      RemoveArrowAndAzimuthElements PickedCell
   End If
End Sub




Private Sub RemoveArrowAndAzimuthElements(PickedCell As CellElement)
   Dim i As Integer
   i = 0
   PickedCell.ResetElementEnumeration
   Do While PickedCell.MoveToNextElement(True)
      If i = DIAGRAM_ELEMENT_AZIMUTH Or i = DIAGRAM_ELEMENT_ARROW Then
         PickedCell.DeleteCurrentElement
      End If
      i = i + 1
   Loop
End Sub

Attribute VB_Name = "DropDiagramUpdateQuadsSame"
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit

Private RevisedTextTemplate As TextElement



Private Sub NoChange(cellArray() As Element, _
                     PickedCell As CellElement, _
                     ByVal angleRotHorRadians As Double, _
                     ByVal X As Double, _
                     ByVal oldX As Double, _
                     ByVal Y As Double, _
                     ByVal oldY As Double, _
                     ByVal characterSize As Double, _
                     ByVal LineSpacing As Double, _
                     ByVal sAzDegrees As Double)
'ADDS "NO CAHNGE" TEXT TO DIAGRAM
   If X = oldX And Y = oldY Then
   'CREATE THE TEXT ELEMENT
      Dim TempTextElement As TextElement
      Set TempTextElement = CreateTextElement1(RevisedTextTemplate, "No change", PickedCell.origin, Matrix3dIdentity)
   
   'CALCULATE IT'S NEW POSITION
      Dim tempPointEnd As Point3d
      tempPointEnd = CoordFwdSAz(cellArray(2).AsLineElement.endPoint, sAzDegrees + 90, characterSize + LineSpacing)
      
   'CHANGE JUSTIFICATION
      ChangeJustification TempTextElement, msdTextJustificationCenterCenter
   
   'REPOSITION AND ROTATE IT
      TempTextElement.origin = tempPointEnd
      TempTextElement.RotateAboutZ tempPointEnd, angleRotHorRadians
      
   'ADD IT TO THE CELL
      PickedCell.AppendToCellOfCurrentElement TempTextElement
   End If
End Sub



Private Sub UpdateDescSameQuad(cellArray() As Element, _
                               PickedCell As CellElement, _
                               ByVal angleRotHorRadians As Double, _
                               ByVal QuadrantOld As Integer, _
                               oldDescription As String, _
                               newDescription As String, _
                               NewDescriptionText As TextElement, _
                               ByVal characterSize As Double, _
                               ByVal LineSpacing As Double, _
                               ByVal sAzDegrees As Double, _
                               newDesc2TextEl As TextElement)
'DETERMINE IF DIAGRAM IS DOUBLE OR SINGLE DESCRIPTION
   Dim IsDoubleDesc As Boolean
   If UBound(cellArray) = DIAGRAM_ELEMENT_DESCRIPTION2 Then
      IsDoubleDesc = True
   Else
      IsDoubleDesc = False
   End If

'CHANGE TEXT JUSTIFICATION OF NEW DESCRIPTION ACCORDING TO QUADRANT
   Select Case QuadrantOld
      Case QUAD_NORTH_EAST
         ChangeJustification NewDescriptionText, msdTextJustificationLeftCenter
         ChangeJustification newDesc2TextEl, msdTextJustificationLeftCenter
      Case QUAD_SOUTH_EAST
         ChangeJustification NewDescriptionText, msdTextJustificationLeftCenter
         ChangeJustification newDesc2TextEl, msdTextJustificationLeftCenter
      Case QUAD_SOUTH_WEST
         ChangeJustification NewDescriptionText, msdTextJustificationRightCenter
         ChangeJustification newDesc2TextEl, msdTextJustificationRightCenter
      Case QUAD_NORTH_WEST
         ChangeJustification NewDescriptionText, msdTextJustificationRightCenter
         ChangeJustification newDesc2TextEl, msdTextJustificationRightCenter
   End Select
      
'ROTATE IT TO DIAGRAM
   NewDescriptionText.RotateAboutZ NewDescriptionText.origin, angleRotHorRadians
   newDesc2TextEl.RotateAboutZ newDesc2TextEl.origin, angleRotHorRadians
      
   If StrComp(oldDescription, newDescription, vbTextCompare) <> 0 And newDescription <> "" Then
'DESCRIPTION CHANGED, REVISE IT
'IF NO OLD DESCRIPTION, THEN JUST OVERWRITE IT
      If oldDescription = "" Then
'ADD NEW DESCRIPTION IN SAME POSITION AS OLD ONE
         NewDescriptionText.origin = cellArray(DIAGRAM_ELEMENT_DESCRIPTION).AsTextElement.origin
         PickedCell.AppendToCellOfCurrentElement NewDescriptionText
      Else
'CROSS OUT OLD DESCRIPTION AND PLACE NEW ONE NEAR OLD ONE
'GET POSITION OF OLD TEXT ELEMENT TO CALCULATE NEW POSITION AND CROSS IT OUT
         Dim tempPointDesc1 As Point3d
         tempPointDesc1 = cellArray(DIAGRAM_ELEMENT_DESCRIPTION).AsTextElement.origin
         Dim oldDescLen As Point2d
         cellArray(DIAGRAM_ELEMENT_DESCRIPTION).AsTextElement.GetTotalTextSize oldDescLen.X, oldDescLen.Y
         Select Case QuadrantOld
            Case QUAD_NORTH_EAST
               Dim tempPointDesc2 As Point3d
               tempPointDesc2 = CoordFwdSAz(tempPointDesc1, sAzDegrees, oldDescLen.X)
               Dim tempPointBegin As Point3d
               tempPointBegin = CoordFwdSAz(tempPointDesc1, sAzDegrees + 270, characterSize + LineSpacing)
            Case QUAD_SOUTH_EAST
               tempPointDesc2 = CoordFwdSAz(tempPointDesc1, sAzDegrees, oldDescLen.X)
               tempPointBegin = CoordFwdSAz(tempPointDesc1, sAzDegrees + 90, characterSize + LineSpacing)
            Case QUAD_SOUTH_WEST
               tempPointDesc2 = CoordFwdSAz(tempPointDesc1, sAzDegrees + 180, oldDescLen.X)
               tempPointBegin = CoordFwdSAz(tempPointDesc1, sAzDegrees + 90, characterSize + LineSpacing)
            Case QUAD_NORTH_WEST
               tempPointDesc2 = CoordFwdSAz(tempPointDesc1, sAzDegrees + 180, oldDescLen.X)
               tempPointBegin = CoordFwdSAz(tempPointDesc1, sAzDegrees + 270, characterSize + LineSpacing)
         End Select

'DRAW THE LINE AND ADD IT TO THE CELL
         Dim LineOutDesc As LineElement
         Set LineOutDesc = CreateLineElement2(RevisedTextTemplate, tempPointDesc1, tempPointDesc2)
         PickedCell.AppendToCellOfCurrentElement LineOutDesc
      
'REPOSITION NEW TEXT AND ADD IT TO THE CELL
         NewDescriptionText.origin = tempPointBegin
         PickedCell.AppendToCellOfCurrentElement NewDescriptionText
      End If
   End If

'DESCRIPTION2
   Dim Desc2String As String
   Desc2String = Trim(newDesc2TextEl.text)

'IF NEW DESCRIPTION2 IS BLANK, THEN DO NOTHING
   If Desc2String = "" Then
      Exit Sub
   End If

   If IsDoubleDesc Then
      Dim Desc2OrigElement As TextElement
      Set Desc2OrigElement = cellArray(DIAGRAM_ELEMENT_DESCRIPTION2)
      Dim Desc2OrigString As String
      Desc2OrigString = Trim(Desc2OrigElement.AsTextElement.text)
'IF NEW DESCRIPTION IS SAME AS OLD, THEN DO NOTHING
      If Desc2String = Desc2OrigString Then
         Exit Sub
      End If
      
'IF THERE IS AN ORIGINAL DESCRIPTION2 AND IT'S BLANK, THEN JUST PUT NEW DESCRIPTION2 IN SAME PLACE
      If Desc2OrigString = "" Then
         newDesc2TextEl.origin = Desc2OrigElement.origin
      Else
'IF ORIGINAL DESCRIPTION2 IS DIFFERENT FROM THE NEW DESCRIPTION2, THEN CROSS IT OUT AND PLACE IT BELOW THE ORIGINAL
         Dim OrigDesc2Point As Point3d
         OrigDesc2Point = Desc2OrigElement.origin
         Dim OrigDescSize As Point2d
         Desc2OrigElement.GetTotalTextSize OrigDescSize.X, OrigDescSize.Y
         Select Case QuadrantOld
            Case QUAD_NORTH_EAST
               Dim OrigDesc2EndPoint As Point3d
               OrigDesc2EndPoint = CoordFwdSAz(OrigDesc2Point, sAzDegrees, OrigDescSize.X)
               Dim NewDesc2BeginPoint As Point3d
               NewDesc2BeginPoint = CoordFwdSAz(OrigDesc2Point, sAzDegrees + 90#, characterSize + LineSpacing)
               NewDesc2BeginPoint = CoordFwdSAz(NewDesc2BeginPoint, sAzDegrees, characterSize + LineSpacing)
            Case QUAD_SOUTH_EAST
               OrigDesc2EndPoint = CoordFwdSAz(OrigDesc2Point, sAzDegrees, OrigDescSize.X)
               NewDesc2BeginPoint = CoordFwdSAz(OrigDesc2Point, sAzDegrees + 90#, characterSize + LineSpacing)
            Case QUAD_SOUTH_WEST
               OrigDesc2EndPoint = CoordFwdSAz(OrigDesc2Point, sAzDegrees + 180#, OrigDescSize.X)
               NewDesc2BeginPoint = CoordFwdSAz(OrigDesc2Point, sAzDegrees + 90#, characterSize + LineSpacing)
            Case QUAD_NORTH_WEST
               OrigDesc2EndPoint = CoordFwdSAz(OrigDesc2Point, sAzDegrees + 180#, OrigDescSize.X)
               NewDesc2BeginPoint = CoordFwdSAz(OrigDesc2Point, sAzDegrees + 90#, characterSize + LineSpacing)
               NewDesc2BeginPoint = CoordFwdSAz(NewDesc2BeginPoint, sAzDegrees + 180#, characterSize + LineSpacing)
         End Select
         newDesc2TextEl.origin = NewDesc2BeginPoint
         Dim LineOutDesc2 As LineElement
         Set LineOutDesc2 = CreateLineElement2(RevisedTextTemplate, OrigDesc2Point, OrigDesc2EndPoint)
         PickedCell.AppendToCellOfCurrentElement LineOutDesc2
      End If
   Else
'IF NO ORIGINAL DESCRIPTION2 THEN PUT IT A CHARACTER PLUS A LINE SPACE BELOW THE DESCRIPTION
      NewDesc2BeginPoint = cellArray(DIAGRAM_ELEMENT_DESCRIPTION).AsTextElement.origin
      NewDesc2BeginPoint = CoordFwdSAz(NewDesc2BeginPoint, sAzDegrees + 90, characterSize + LineSpacing)
      newDesc2TextEl.origin = NewDesc2BeginPoint
   End If
   PickedCell.AppendToCellOfCurrentElement newDesc2TextEl
End Sub



Private Sub UpdateXText(cellArray() As Element, _
                        PickedCell As CellElement, _
                        NewXTextElement As TextElement, _
                        NewXTextLen As Point2d, _
                        ByVal X As Double, _
                        ByVal oldX As Double, _
                        ByVal azimuthInDegrees As Double, _
                        ByVal QuadrantOld As Integer, _
                        ByVal characterSize As Double, _
                        ByVal LineSpacing As Double, _
                        ByVal angleRotHorRadians As Double)
'GET X-TEXT AND DRAW LINE THRU IT, ADD IT TO CELL
   If X <> oldX Then
'CROSS OUT X-VALUE
      Dim XTextLen As Point2d
      cellArray(DIAGRAM_ELEMENT_XTEXT).AsTextElement.GetTotalTextSize XTextLen.X, XTextLen.Y
      Dim LineOutBegin As Point3d
      LineOutBegin = cellArray(DIAGRAM_ELEMENT_XTEXT).AsTextElement.origin
      Dim LineOutEnd As Point3d
      LineOutEnd = CoordFwdSAz(LineOutBegin, azimuthInDegrees, XTextLen.X)
      Dim LineOutElement As LineElement
      Set LineOutElement = CreateLineElement2(RevisedTextTemplate, LineOutBegin, LineOutEnd)
      PickedCell.AppendToCellOfCurrentElement LineOutElement
   
'ADD THE NEW X-DIMENSION TEXT
'CALCULATE INSERTION POINT
      Select Case QuadrantOld
         Case QUAD_NORTH_EAST
            Dim NewTextInsertionPoint As Point3d
            NewTextInsertionPoint = CoordFwdSAz(LineOutBegin, azimuthInDegrees - 90#, LineSpacing + characterSize)

         Case QUAD_SOUTH_EAST
            NewTextInsertionPoint = CoordFwdSAz(LineOutBegin, azimuthInDegrees + 90#, LineSpacing + characterSize)
                  
         Case QUAD_SOUTH_WEST
            NewTextInsertionPoint = CoordFwdSAz(LineOutBegin, azimuthInDegrees + 90#, LineSpacing + characterSize)
            NewTextInsertionPoint = CoordFwdSAz(NewTextInsertionPoint, azimuthInDegrees, XTextLen.X - NewXTextLen.X)
                  
         Case QUAD_NORTH_WEST
            NewTextInsertionPoint = CoordFwdSAz(LineOutBegin, azimuthInDegrees - 90#, LineSpacing + characterSize)
            NewTextInsertionPoint = CoordFwdSAz(NewTextInsertionPoint, azimuthInDegrees, XTextLen.X - NewXTextLen.X)
      End Select

'POSITION AND ROTATE THE NEW TEXT
      NewXTextElement.origin = NewTextInsertionPoint
      NewXTextElement.RotateAboutZ NewTextInsertionPoint, angleRotHorRadians

'ADD IT TO THE CELL
      PickedCell.AppendToCellOfCurrentElement NewXTextElement
   End If
End Sub



Private Sub UpdateYText(cellArray() As Element, _
                        PickedCell As CellElement, _
                        NewYTextElement As TextElement, _
                        NewYTextLen As Point2d, _
                        ByVal Y As Double, _
                        ByVal oldY As Double, _
                        ByVal azimuthInDegrees As Double, _
                        ByVal QuadrantOld As Integer, _
                        ByVal characterSize As Double, _
                        ByVal LineSpacing As Double, _
                        ByVal angleRotVerRadians As Double)

'GET Y-TEXT AND DRAW LINE THRU IT, ADD IT TO CELL
   If Y <> oldY Then
'CROSS OUT Y-VALUE
      Dim YTextLen As Point2d
      cellArray(DIAGRAM_ELEMENT_YTEXT).AsTextElement.GetTotalTextSize YTextLen.X, YTextLen.Y
      Dim LineOutBegin As Point3d
      LineOutBegin = cellArray(DIAGRAM_ELEMENT_YTEXT).AsTextElement.origin
      Dim LineOutEnd As Point3d
      LineOutEnd = CoordFwdSAz(LineOutBegin, azimuthInDegrees - 90#, YTextLen.X)
      Dim LineOutElement As LineElement
      Set LineOutElement = CreateLineElement2(RevisedTextTemplate, LineOutBegin, LineOutEnd)
      PickedCell.AppendToCellOfCurrentElement LineOutElement
   
'ADD THE NEW Y-DIMENSION TEXT
      Select Case QuadrantOld
         Case QUAD_NORTH_EAST
            Dim NewTextInsertionPoint As Point3d
            NewTextInsertionPoint = CoordFwdSAz(LineOutBegin, azimuthInDegrees, LineSpacing + characterSize)
            
         Case QUAD_SOUTH_EAST
            NewTextInsertionPoint = CoordFwdSAz(LineOutBegin, azimuthInDegrees, LineSpacing + characterSize)
            NewTextInsertionPoint = CoordFwdSAz(NewTextInsertionPoint, azimuthInDegrees + 90#, NewYTextLen.X - YTextLen.X)
                  
         Case QUAD_SOUTH_WEST
            NewTextInsertionPoint = CoordFwdSAz(LineOutBegin, azimuthInDegrees + 180#, LineSpacing + characterSize)
            NewTextInsertionPoint = CoordFwdSAz(NewTextInsertionPoint, azimuthInDegrees + 90#, NewYTextLen.X - YTextLen.X)
                  
         Case QUAD_NORTH_WEST
            NewTextInsertionPoint = CoordFwdSAz(LineOutBegin, azimuthInDegrees + 180#, LineSpacing + characterSize)
      End Select
      NewYTextElement.origin = NewTextInsertionPoint
      NewYTextElement.RotateAboutZ NewTextInsertionPoint, angleRotVerRadians
      PickedCell.AppendToCellOfCurrentElement NewYTextElement
   End If
End Sub



Public Sub WhenOldQuadEqualsNewQuad(cellArray() As Element, _
                                    PickedCell As CellElement, _
                                    CellOrigin As Point3d, _
                                    oldDescription As String, _
                                    newDescription As String, _
                                    QuadrantNew As Integer, _
                                    QuadrantOld As Integer, _
                                    NewXTextElement As TextElement, _
                                    NewYTextElement As TextElement, _
                                    NewXTextLen As Point2d, _
                                    NewYTextLen As Point2d, _
                                    NewDescriptionText As TextElement, _
                                    ByVal X As Double, _
                                    ByVal Y As Double, _
                                    ByVal azimuthInDegrees As Double, _
                                    ByVal angleRotHorRadians As Double, _
                                    ByVal angleRotVerRadians As Double, _
                                    ByVal characterSize As Double, _
                                    ByVal LineSpacing As Double, _
                                    newDesc2TextEl As TextElement)
'MAKE TEMPLATE FOR REVISION TEXT
   Set RevisedTextTemplate = CreateTextElement1(NewXTextElement, "template", CellOrigin, Matrix3dIdentity)

'UPDATE DESCRIPTION IF NEEDED
   UpdateDescSameQuad cellArray, _
                      PickedCell, _
                      angleRotHorRadians, _
                      QuadrantOld, _
                      oldDescription, _
                      newDescription, _
                      NewDescriptionText, _
                      characterSize, _
                      LineSpacing, _
                      azimuthInDegrees, _
                      newDesc2TextEl

'GET OLD X AND Y VALUES TO SEE IF TEXT NEEDS CROSSING OUT
   Dim oldX As Double
   oldX = CDbl(cellArray(DIAGRAM_ELEMENT_XTEXT).AsTextElement.text)
   Dim oldY As Double
   oldY = CDbl(cellArray(DIAGRAM_ELEMENT_YTEXT).AsTextElement.text)
      
'OLD X-DIMENSION TEXT IS DIFFERENT FROM NEW TEXT, CROSS IT OUT AND CHANGE IT
   UpdateXText cellArray, _
               PickedCell, _
               NewXTextElement, _
               NewXTextLen, _
               X, _
               oldX, _
               azimuthInDegrees, _
               QuadrantOld, _
               characterSize, _
               LineSpacing, _
               angleRotHorRadians
         
'OLD Y-DIMENSION TEXT IS DIFFERENT FROM NEW TEXT, CROSS IT OUT AND CHANGE IT
   UpdateYText cellArray, _
               PickedCell, _
               NewYTextElement, _
               NewYTextLen, _
               Y, _
               oldY, _
               azimuthInDegrees, _
               QuadrantOld, _
               characterSize, _
               LineSpacing, _
               angleRotVerRadians
         
'BOTH OLD AND NEW DIMENSIONS ARE THE SAME, ADD "NO CHANGE" TO CELL
   NoChange cellArray, _
            PickedCell, _
            angleRotHorRadians, _
            X, _
            oldX, _
            Y, _
            oldY, _
            characterSize, _
            LineSpacing, _
            azimuthInDegrees
End Sub

Attribute VB_Name = "FrmArcArcInt"
Attribute VB_Base = "0{1C0FDAA2-5CA4-4E50-A51F-FB346449CACC}{72F4457E-ECA6-4975-945B-B104130BC462}"
Attribute VB_GlobalNameSpace = False
Attribute VB_Creatable = False
Attribute VB_PredeclaredId = True
Attribute VB_Exposed = False
Attribute VB_TemplateDerived = False
Attribute VB_Customizable = False
















'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.



'GENERAL NOTES:
'PROGRAM ASSUMES MASTER UNIT IS FOOT OR SURVEY FOOT, SOME KIND OF FOOT


Option Explicit

Private Const COORD_PRECISION As Long = 4

Private RP1 As Point3d
Private RP2 As Point3d



'*************************************************************************************************************
'****************************************INTERACT WITH IPRIMITIVE*********************************************
Public Sub IntChosen(intersection As Point3d)
   DrawIntLines RP1, RP2, intersection
   Me.Show
End Sub



'*************************************************************************************************************
'***************************************************DISPLAY***************************************************
Private Sub updateCoordDisp1(Coord As Point3d)
   Easting1Label.Caption = DoubleToEastingString(Coord.X, COORD_PRECISION)
   Northing1Label.Caption = DoubleToNorthingString(Coord.Y, COORD_PRECISION)
End Sub



Private Sub updateCoordDisp2(Coord As Point3d)
   Easting2Label.Caption = DoubleToEastingString(Coord.X, COORD_PRECISION)
   Northing2Label.Caption = DoubleToNorthingString(Coord.Y, COORD_PRECISION)
End Sub



'*************************************************************************************************************
'************************************************MAIN TAB*****************************************************
'PICK ARC 1 RADIUS POINT BUTTON
Private Sub Pick1Button_Click()
   Me.Hide
   Dim ThePickedPoint As Point3d
   If PickSub(COMMAND_NAME_ARC_ARC_INT, "Pick Radius Point 1.", ThePickedPoint) Then
      RP1 = ThePickedPoint
      updateCoordDisp1 RP1
   End If
   Me.Show
   Rad1TextBox.SetFocus
End Sub



'ARC 1 RADIUS TEXTBOX
Private Sub Rad1TextBox_AfterUpdate()
   SaveNonnegativeEntry Rad1TextBox, SECTION_ARC_ARC_INT, KEY_RADIUS, MAX_RADIUS, MAX_PRECISION_RADIUS, False, 100.2
End Sub

Private Sub Rad1TextBox_Enter()
   SelectAllText Rad1TextBox
End Sub



'ARC 2 RADIUS POINT PICK BUTTON
Private Sub Pick2Button_Click()
   Me.Hide
   Dim ThePickedPoint As Point3d
   If PickSub(COMMAND_NAME_ARC_ARC_INT, "Pick Radius Point 2.", ThePickedPoint) Then
      RP2 = ThePickedPoint
      updateCoordDisp2 RP2
   End If
   Me.Show
   Rad2TextBox.SetFocus
End Sub



'ARC 2 RADIUS TEXTBOX
Private Sub Rad2TextBox_AfterUpdate()
   SaveNonnegativeEntry Rad2TextBox, SECTION_ARC_ARC_INT, KEY_RADIUS2, MAX_RADIUS, MAX_PRECISION_RADIUS, False, 100.2
End Sub

Private Sub Rad2TextBox_Enter()
   SelectAllText Rad2TextBox
End Sub



'DRAW SYMBOL CHECKBOX
Private Sub DrawSymbolCheckBox_Click()
   SaveCheckBoxSetting DrawSymbolCheckBox, SECTION_ARC_ARC_INT, KEY_OPTION_DRAW_SYMBOL
End Sub



'TEXT DIRECTION CHECKBOX
Private Sub TextAzCheckBox_Click()
   SaveCheckBoxSetting TextAzCheckBox, SECTION_ARC_ARC_INT, KEY_OPTION_TEXT_DIR
End Sub



'TEXT DISTANCE CHECKBOX
Private Sub TextDisCheckBox_Click()
   SaveCheckBoxSetting TextDisCheckBox, SECTION_ARC_ARC_INT, KEY_OPTION_TEXT_DIST
End Sub



'AZIMUTH OPTION
Private Sub AzOption_Click()
   SaveSetting APP_NAME, SECTION_ARC_ARC_INT, KEY_DIRECTION_TYPE, OPTION_DIR_TYPE_AZIMUTH
End Sub



'BEARING OPTION
Private Sub BearOptionButton_Click()
   SaveSetting APP_NAME, SECTION_ARC_ARC_INT, KEY_DIRECTION_TYPE, OPTION_DIR_TYPE_BEARING
End Sub



'SOLVE BUTTON
Private Sub SolveCommand_Click()
   If Not SolveIntersections() Then
      Beep
   End If
End Sub



'*************************************************************************************************************
'**********************************************SETTINGS TAB***************************************************
'TEXT ATTRIBUTES
'COLOR COMBOBOX
Private Sub ColorComboBox_AfterUpdate()
   ColorBoxOnUpdate ColorComboBox, SECTION_ARC_ARC_INT, KEY_COLOR
End Sub

'COLOR PICKER
Private Sub ChooseColorButton_Click()
   Dim MyColor As String
   If ChooseMyTableColor(MyColor) Then
      ColorComboBox.text = MyColor
      ColorComboBox_AfterUpdate
   End If
End Sub



'LEVEL COMBOBOX
Private Sub LevelComboBox_AfterUpdate()
   If Not LevelBoxOnUpdate(LevelComboBox, SECTION_ARC_ARC_INT, KEY_LEVEL) Then
      PopulateLevelBox LevelComboBox, SECTION_ARC_ARC_INT, KEY_LEVEL
      Beep
   End If
End Sub

'STYLE COMBOBOX
Private Sub StyleComboBox_AfterUpdate()
   If Not LineStyleBoxOnUpdate(StyleComboBox, SECTION_ARC_ARC_INT, KEY_STYLE) Then
      PopulateLinestyleBox StyleComboBox, SECTION_ARC_ARC_INT, KEY_STYLE
      Beep
   End If
End Sub

'WEIGHT COMBOBOX
Private Sub WeightComboBox_AfterUpdate()
   WeightBoxOnUpdate WeightComboBox, SECTION_ARC_ARC_INT, KEY_WEIGHT
End Sub

'FONT COMBOBOX
Private Sub FontComboBox_AfterUpdate()
   If Not FontBoxOnUpdate(FontComboBox, SECTION_ARC_ARC_INT, KEY_FONT) Then
      PopulateFontBox FontComboBox, SECTION_ARC_ARC_INT, KEY_FONT
      Beep
   End If
End Sub





'PLACE TEXT BUTTON
Private Sub PlaceTextButton_Click()
   CommandState.StartPrimitive New PlaceTextPrimitive
End Sub



'TEXT TEMPLATE
Public Function GetTextTemp() As TextElement
   Set GetTextTemp = CreateTextTemplate(SECTION_ARC_ARC_INT, _
                                        FontComboBox, _
                                        KEY_FONT, _
                                        LevelComboBox, _
                                        KEY_LEVEL, _
                                        WeightComboBox, _
                                        ColorComboBox, _
                                        StyleComboBox, _
                                        KEY_STYLE, , _
                                        msdTextJustificationCenterCenter)
End Function








'LINE ATTRIBUTES
'COLOR COMBOBOX
Private Sub ColorComboBox2_AfterUpdate()
   ColorBoxOnUpdate ColorComboBox2, SECTION_ARC_ARC_INT, KEY_COLOR2
End Sub

'COLOR PICKER
Private Sub ChooseColorButton2_Click()
   Dim MyColor As String
   If ChooseMyTableColor(MyColor) Then
      ColorComboBox2.text = MyColor
      ColorComboBox2_AfterUpdate
   End If
End Sub

'LEVEL COMBOBOX
Private Sub LevelComboBox2_AfterUpdate()
   If Not LevelBoxOnUpdate(LevelComboBox2, SECTION_ARC_ARC_INT, KEY_LEVEL2) Then
      PopulateLevelBox LevelComboBox2, SECTION_ARC_ARC_INT, KEY_LEVEL2
      Beep
   End If
End Sub

'STYLE COMBOBOX
Private Sub StyleComboBox2_AfterUpdate()
   If Not LineStyleBoxOnUpdate(StyleComboBox2, SECTION_ARC_ARC_INT, KEY_STYLE2) Then
      PopulateLinestyleBox StyleComboBox2, SECTION_ARC_ARC_INT, KEY_STYLE2
      Beep
   End If
End Sub

'WEIGHT COMBOBOX
Private Sub WeightComboBox2_AfterUpdate()
   WeightBoxOnUpdate WeightComboBox2, SECTION_ARC_ARC_INT, KEY_WEIGHT2
End Sub



'LINE TEMPLATE
Public Function GetLineTemp() As LineElement
   Set GetLineTemp = CreateLineTemplate(SECTION_ARC_ARC_INT, _
                                        LevelComboBox2, _
                                        KEY_LEVEL2, _
                                        WeightComboBox2, _
                                        ColorComboBox2, _
                                        StyleComboBox2, _
                                        KEY_STYLE2)
End Function



'DIRECTION PRECISION COMBOBOX
Private Sub AngPrecComboBox_Change()
   SaveSetting APP_NAME, SECTION_ARC_ARC_INT, KEY_PRECISION_ANG, AngPrecComboBox.text
End Sub



'SETTINGS BUTTON
Private Sub SettingsButton_Click()
   Setting
End Sub



'*************************************************************************************************************
'************************************************DRAWING******************************************************
Private Function SolveIntersections() As Boolean
   SolveIntersections = False

'SOLVE FOR INTERSECTION
   Dim Radius1 As Double
   Radius1 = Abs(CDbl(Rad1TextBox.text))
   Dim Arc1 As EllipseElement
   Set Arc1 = CreateEllipseElement2(Nothing, RP1, Radius1, Radius1, Matrix3dIdentity)
   
   Dim Radius2 As Double
   Radius2 = Abs(CDbl(Rad2TextBox.text))
   Dim Arc2 As EllipseElement
   Set Arc2 = CreateEllipseElement2(Nothing, RP2, Radius2, Radius2, Matrix3dIdentity)

   Dim TheIntersections() As Point3d
   TheIntersections = Arc1.GetIntersectionPoints(Arc2, Matrix3dIdentity)
   Dim LowerInt As Long
   LowerInt = LBound(TheIntersections)
   Dim UpperInt As Long
   UpperInt = UBound(TheIntersections)
   If UpperInt = -1 Then
      MsgBox "No Intersections"
      Exit Function
   End If
   If LowerInt = UpperInt Then
'ONE SOLUTION ONLY
      DrawIntLines RP1, RP2, TheIntersections(UpperInt)
   Else
'TWO SOLUTIONS, INTERACTIVELY CHOOSE INTERSECTION
      Dim pickTool As New IntersectchooserPimitive
      pickTool.RadiusPt1 = RP1
      pickTool.RadiusPt2 = RP2
      pickTool.Radius1 = Radius1
      pickTool.Radius2 = Radius2
      pickTool.IntersetionPt1 = TheIntersections(LowerInt)
      pickTool.IntersetionPt2 = TheIntersections(UpperInt)
      CommandState.StartPrimitive pickTool
      Me.Hide
   End If
   SolveIntersections = True
End Function



Private Sub DrawIntLines(radPoint1 As Point3d, radPoint2 As Point3d, intPoint As Point3d)
'FOR UNDO
   CommandState.CommandName = COMMAND_NAME_ARC_ARC_INT

'MAKE SURE CAN WRITE TO FILE
   If ActiveModelReference.IsReadOnly Then
      Exit Sub
   End If

'MAKE SURE VIEW IS OPEN
   Dim mySelectedView As view
   Set mySelectedView = GetSelectedView()
   If mySelectedView Is Nothing Then
      Exit Sub
   End If

'DRAW LINES TO INTERSECTION
   Dim lineTemplate As LineElement
   Set lineTemplate = GetLineTemp()
   Dim intersect1 As Point3d
   intersect1 = intPoint
   intersect1.z = radPoint1.z
   Dim line1 As LineElement
   Set line1 = CreateLineElement2(lineTemplate, radPoint1, intersect1)
   Dim intersect2 As Point3d
   intersect2 = intPoint
   intersect2.z = radPoint2.z
   Dim line2 As LineElement
   Set line2 = CreateLineElement2(lineTemplate, radPoint2, intersect2)

'DETERMINE IF LINES POINTING LEFT
   Dim viewRotRadians As Double
   viewRotRadians = TheViewRotRadians(mySelectedView)
   Dim line1PointsLeft As Boolean
   line1PointsLeft = linePointsLeft(InverseAzimuth(line1.startPoint, line1.endPoint), viewRotRadians)
   Dim line2PointsLeft As Boolean
   line2PointsLeft = linePointsLeft(InverseAzimuth(line2.startPoint, line2.endPoint), viewRotRadians)

'CALCULATE METRICS
   Dim characterSize As Double
   characterSize = GetCharSize()
   Dim LineSpacing As Double
   LineSpacing = characterSize / 3#
   Dim vertOffset As Double
   vertOffset = characterSize / 2# + LineSpacing

'CREATE TEXT TEMPLATE
   Dim textTemplate As TextElement
   Set textTemplate = GetTextTemp()

'DRAW SYMBOL OR SYMBOLS
   If DrawSymbolCheckBox.value Then
      Dim symLine1 As CellElement
      Set symLine1 = CreateSymbol5Cell(lineTemplate, intersect1, characterSize, viewRotRadians)
      ActiveModelReference.AddElement symLine1
      symLine1.Redraw
      If radPoint1.z <> radPoint2.z Then
         Dim symLine2 As CellElement
         Set symLine2 = CreateSymbol5Cell(lineTemplate, intersect2, characterSize, viewRotRadians)
         ActiveModelReference.AddElement symLine2
         symLine2.Redraw
      End If
   End If
   
'DRAW DIRECTION TEXT IF CHOSEN
   If TextAzCheckBox.value Then
      Dim AngPrec As Long
      AngPrec = GetAngPrec()
      Dim dirType As Integer
      dirType = GetDirType()
      Dim angleStyle As Integer
      angleStyle = STYLE_ANGLE_SPACE + STYLE_ANGLE_LEAD + STYLE_ANGLE_CARET + STYLE_ANGLE_NO_00_SEC
      Dim dirString1 As String
      dirString1 = SAzToDirectionStr(InverseAzimuth(radPoint1, intersect1), AngPrec, dirType, angleStyle)
      TextTheLine textTemplate, line1, dirString1, vertOffset, line1PointsLeft
      Dim dirString2 As String
      dirString2 = SAzToDirectionStr(InverseAzimuth(radPoint2, intersect2), AngPrec, dirType, angleStyle)
      TextTheLine textTemplate, line2, dirString2, vertOffset, line2PointsLeft
      vertOffset = -vertOffset
   End If
   
'DRAW DISTANCE TEXT IF CHOSEN
   If TextDisCheckBox.value Then
      TextTheLine textTemplate, line1, Rad1TextBox.text, vertOffset, line1PointsLeft
      TextTheLine textTemplate, line2, Rad2TextBox.text, vertOffset, line2PointsLeft
   End If
   
   ActiveModelReference.AddElement line1
   line1.Redraw
   ActiveModelReference.AddElement line2
   line2.Redraw
   
   CommandState.StartDefaultCommand
End Sub



Private Function GetDirType() As Integer
   If AzOption.value Then
      GetDirType = DIR_TYPE_AZIMUTH
   Else
      GetDirType = DIR_TYPE_BEARING
   End If
End Function



Private Function GetAngPrec() As Long
   GetAngPrec = GetAngPrec1(AngPrecComboBox.text)
End Function



'*************************************************************************************************************
'**********************************************USERFORM EVENTS************************************************
Private Sub UserForm_Initialize()
'RADIUS POINTS ARE INTENTIONALLY NOT STORED SO THAT THE USER CAN EASILY TELL
'IF IT'S BEEN PICKED OR NOT.

'INITIALIZE CHECKBOXES
   InitializeCheckBox TextAzCheckBox, SECTION_ARC_ARC_INT, KEY_OPTION_TEXT_DIR
   InitializeCheckBox TextDisCheckBox, SECTION_ARC_ARC_INT, KEY_OPTION_TEXT_DIST
   InitializeCheckBox DrawSymbolCheckBox, SECTION_ARC_ARC_INT, KEY_OPTION_DRAW_SYMBOL

'INITIALIZE RADIUS TEXTBOXES
   LoadRadiusEntry Rad1TextBox, SECTION_ARC_ARC_INT, KEY_RADIUS
   Rad1TextBox.MaxLength = MAX_LEN_RADIUS_STRING
   LoadRadiusEntry Rad2TextBox, SECTION_ARC_ARC_INT, KEY_RADIUS2
   Rad2TextBox.MaxLength = MAX_LEN_RADIUS_STRING

'INITIALIZE DISPLAY
   updateCoordDisp1 RP1
   updateCoordDisp2 RP2

'TEXT ATTRIBUTES
'LEVEL COMBOBOX
   PopulateLevelBox LevelComboBox, SECTION_ARC_ARC_INT, KEY_LEVEL
'COLOR COMBOBOX
   PopulateColorBox ColorComboBox, SECTION_ARC_ARC_INT, KEY_COLOR
'STYLE COMBOBOX
   PopulateLinestyleBox StyleComboBox, SECTION_ARC_ARC_INT, KEY_STYLE
'WEIGHT COMBOBOX
   PopulateWeightBox WeightComboBox, SECTION_ARC_ARC_INT, KEY_WEIGHT
'FONT COMBOBOX
   PopulateFontBox FontComboBox, SECTION_ARC_ARC_INT, KEY_FONT
   
'LINE ATTRIBUTES
'LEVEL COMBOBOX
   PopulateLevelBox LevelComboBox2, SECTION_ARC_ARC_INT, KEY_LEVEL2
'COLOR COMBOBOX
   PopulateColorBox ColorComboBox2, SECTION_ARC_ARC_INT, KEY_COLOR2
'STYLE COMBOBOX
   PopulateLinestyleBox StyleComboBox2, SECTION_ARC_ARC_INT, KEY_STYLE2
'WEIGHT COMBOBOX
   PopulateWeightBox WeightComboBox2, SECTION_ARC_ARC_INT, KEY_WEIGHT2


'POPULATE DIRECTION PRECISION BOX
   AngPrecComboBox.style = fmStyleDropDownList
   AngPrecComboBox.Clear
   AngPrecComboBox.AddItem OPTION_PREC_ANG_SEC
   AngPrecComboBox.AddItem OPTION_PREC_ANG_SEC1
   AngPrecComboBox.AddItem OPTION_PREC_ANG_SEC01
   AngPrecComboBox.AddItem OPTION_PREC_ANG_SEC001
   AngPrecComboBox.text = GetSetting(APP_NAME, SECTION_ARC_ARC_INT, KEY_PRECISION_ANG, OPTION_PREC_ANG_SEC)

'INITIALIZE DIRECTION TYPE
   Dim Options As String
   Options = GetSetting(APP_NAME, SECTION_ARC_ARC_INT, KEY_DIRECTION_TYPE, OPTION_DIR_TYPE_AZIMUTH)
   If Options = OPTION_DIR_TYPE_AZIMUTH Then
      AzOption.value = True
   Else
      BearOptionButton.value = True
   End If

'MOVE INTO LAST POSITION
   If GetSetting(APP_NAME, SECTION_ARC_ARC_INT, KEY_START_TOP, "") = "" Then
      Me.StartUpPosition = 1
   Else
      Me.StartUpPosition = 0
      Me.Top = CDbl(GetSetting(APP_NAME, SECTION_ARC_ARC_INT, KEY_START_TOP, WINDOW_DEFAULT_TOP))
      Me.Left = CDbl(GetSetting(APP_NAME, SECTION_ARC_ARC_INT, KEY_START_LEFT, WINDOW_DEFAULT_LEFT))
   End If

'SET COMMAND NAME IN TITLE BLOCK
   Me.Caption = COMMAND_NAME_ARC_ARC_INT
   
'SET TO MAIN PAGE
   Me.MultiPage1.value = 0
End Sub



Private Sub UserForm_QueryClose(Cancel As Integer, CloseMode As Integer)
'SAVE USERFORM POSITION
   SaveSetting APP_NAME, SECTION_ARC_ARC_INT, KEY_START_TOP, FormatNumber(Me.Top, 2)
   SaveSetting APP_NAME, SECTION_ARC_ARC_INT, KEY_START_LEFT, FormatNumber(Me.Left, 2)
End Sub



Private Sub UserForm_Terminate()
   CommandState.StartDefaultCommand
End Sub

Attribute VB_Name = "FrmArcLineInt"
Attribute VB_Base = "0{40C50600-52BE-4C24-A91B-6B01E7DCFCA5}{4C5EFA1B-D2B8-4E54-958D-0CA69E549DCD}"
Attribute VB_GlobalNameSpace = False
Attribute VB_Creatable = False
Attribute VB_PredeclaredId = True
Attribute VB_Exposed = False
Attribute VB_TemplateDerived = False
Attribute VB_Customizable = False
















'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.



'GENERAL NOTES:
'PROGRAM ASSUMES MASTER UNIT IS FOOT OR SURVEY FOOT, SOME KIND OF FOOT


Option Explicit


Private Const COORD_PRECISION  As Long = 4

Private POL1                   As Point3d
Private RP2                    As Point3d



'*************************************************************************************************************
'***************************************************DISPLAY***************************************************
Private Sub updateCoordDisp1(Coord As Point3d)
   Easting1Label.Caption = DoubleToEastingString(Coord.X, COORD_PRECISION)
   Northing1Label.Caption = DoubleToNorthingString(Coord.Y, COORD_PRECISION)
End Sub



Private Sub updateCoordDisp2(Coord As Point3d)
   Easting2Label.Caption = DoubleToEastingString(Coord.X, COORD_PRECISION)
   Northing2Label.Caption = DoubleToNorthingString(Coord.Y, COORD_PRECISION)
End Sub



'*************************************************************************************************************
'***********************************************OTHER*********************************************************
Public Sub EnterText(ByVal Entry As String)
   Az1TextBox.text = Entry
   Az1TextBox_AfterUpdate
End Sub



Private Function GetPrecision() As Long
    GetPrecision = CLng(PrecisionComboBox.text)
End Function



Public Function GetPOL() As Point3d
   GetPOL = POL1
End Function



Public Function GetRP() As Point3d
   GetRP = RP2
End Function



Public Sub IntChosen(intersection As Point3d)
   DrawIntLines POL1, RP2, intersection
End Sub



Private Function GetAngPrec() As Long
   GetAngPrec = GetAngPrec1(AngPrecComboBox.text)
End Function



'*************************************************************************************************************
'************************************************DRAWING******************************************************
Private Sub DrawIntLines(pointOnLine As Point3d, radPoint As Point3d, intPoint As Point3d)
'FOR UNDO
   CommandState.CommandName = COMMAND_NAME_ARC_LINE_INT

'MAKE SURE CAN WRITE TO FILE
   If ActiveModelReference.IsReadOnly Then
      Exit Sub
   End If

'MAKE SURE VIEW IS OPEN
   Dim mySelectedView As view
   Set mySelectedView = GetSelectedView()
   If mySelectedView Is Nothing Then
      Exit Sub
   End If

'DRAW LINES TO INTERSECTION
   Dim lineTemplate As LineElement
   Set lineTemplate = GetLineTemp()
   Dim intersect1 As Point3d
   intersect1 = intPoint
   intersect1.z = pointOnLine.z
   Dim line1 As LineElement
   Set line1 = CreateLineElement2(lineTemplate, pointOnLine, intersect1)
   Dim intersect2 As Point3d
   intersect2 = intPoint
   intersect2.z = radPoint.z
   Dim line2 As LineElement
   Set line2 = CreateLineElement2(lineTemplate, radPoint, intersect2)

'DETERMINE IF LINES POINTING LEFT
   Dim viewRotRadians As Double
   viewRotRadians = TheViewRotRadians(mySelectedView)
   Dim line1PointsLeft As Boolean
   line1PointsLeft = linePointsLeft(InverseAzimuth(line1.startPoint, line1.endPoint), viewRotRadians)
   Dim line2PointsLeft As Boolean
   line2PointsLeft = linePointsLeft(InverseAzimuth(line2.startPoint, line2.endPoint), viewRotRadians)

'CALCULATE METRICS
   Dim characterSize As Double
   characterSize = GetCharSize()
   Dim LineSpacing As Double
   LineSpacing = characterSize / 3#
   Dim vertOffset As Double
   vertOffset = characterSize / 2# + LineSpacing

'CREATE TEXT TEMPLATE
   Dim textTemplate As TextElement
   Set textTemplate = GetTextTemp()

'DRAW SYMBOL(S) IF REQUESTED
   If DrawSymbolCheckBox.value Then
'ROTATION IS IRRELEVANT SINCE SYMBOLS IS A CIRCLE
      Dim symLine1 As CellElement
      Set symLine1 = CreateSymbol5Cell(lineTemplate, intersect1, characterSize, viewRotRadians)
      ActiveModelReference.AddElement symLine1
      symLine1.Redraw
'DRAW SECOND SYMBOL IF TWO DIFFERENT INTERSECTIONS POINTS
      If intersect2.z <> intersect1.z Then
         Dim symLine2 As CellElement
         Set symLine2 = CreateSymbol5Cell(lineTemplate, intersect2, characterSize, viewRotRadians)
         ActiveModelReference.AddElement symLine2
         symLine2.Redraw
      End If
   End If

'DRAW DIRECTION IF CHECKED
   If TextAzCheckBox.value Then
      TextTheLine textTemplate, line1, ReplaceDegreeSymbol2(Az1TextBox.text), vertOffset, line1PointsLeft
'DETERMINE TYPE OF DIRECTION USED
      Dim origPrec As Long
      Dim degPart As Long
      Dim minPart As Long
      Dim secPart As Double
      Dim dirType As Integer
      Dim quad As Integer
      If Not IsDirString(Az1TextBox, origPrec, degPart, minPart, secPart, dirType, quad) Then
         dirType = DIR_TYPE_AZIMUTH
      End If
      Dim sAzRadLine As Double
      sAzRadLine = InverseAzimuth(intersect1, RP2)
      Dim DirString As String
      DirString = SAzToDirectionStr(sAzRadLine, GetAngPrec(), dirType, STYLE_ANGLE_CARET Or STYLE_ANGLE_SPACE Or STYLE_ANGLE_LEAD)
      TextTheLine textTemplate, line2, DirString, vertOffset, line2PointsLeft
'MOVE OFFSSET TO UNDER LINE SINCE JUST USED THE TOP
      vertOffset = -vertOffset
   End If

'DRAW DISTANCE IF CHECKED
   If TextDisCheckBox.value Then
      TextTheLine textTemplate, line1, FormatNumber(line1.length, GetPrecision(), vbTrue, vbFalse, vbTrue), vertOffset, line1PointsLeft
      TextTheLine textTemplate, line2, Rad2TextBox.text, vertOffset, line2PointsLeft
   End If

   ActiveModelReference.AddElement line1
   line1.Redraw
   ActiveModelReference.AddElement line2
   line2.Redraw

'END UNDO
   CommandState.StartDefaultCommand
End Sub
'*************************************************************************************************************
'************************************************MAIN TAB*****************************************************
'LINE 1 POINT ON LINE PICK BUTTON
Private Sub Pick1Button_Click()
   Me.Hide

   Dim ThePickedPoint As Point3d
   If PickSub(COMMAND_NAME_ARC_LINE_INT, "Pick Point on Line.", ThePickedPoint) Then
      POL1 = ThePickedPoint
      updateCoordDisp1 POL1
   End If

   Me.Show
   Az1TextBox.SetFocus
End Sub



'LINE 1 DIRECTION TEXTBOX
Private Sub Az1TextBox_AfterUpdate()
   SaveDirEntry Az1TextBox, SECTION_ARC_LINE_INT, KEY_DIRECTION, STYLE_ANGLE_SPACE Or STYLE_ANGLE_LEAD
End Sub

Private Sub Az1TextBox_Enter()
   SelectAllText Az1TextBox
End Sub



'PICK BUTTON
Private Sub PickDirButton_Click()
   Dim pickTool As New ArcLineIntLocateText
   Set pickTool.hostForm = Me
   CommandState.StartLocate pickTool
   Me.Hide
End Sub



'ARC 2 RADIUS POINT PICK BUTTON
Private Sub Pick2Button_Click()
   Me.Hide
   Dim ThePickedPoint As Point3d
   If PickSub(COMMAND_NAME_ARC_LINE_INT, "Pick Radius Point.", ThePickedPoint) Then
      RP2 = ThePickedPoint
      updateCoordDisp2 RP2
   End If
   Me.Show
   Rad2TextBox.SetFocus
End Sub



'ARC 2 RADIUS TEXTBOX
Private Sub Rad2TextBox_AfterUpdate()
   SaveNonnegativeEntry Rad2TextBox, SECTION_ARC_LINE_INT, KEY_RADIUS2, MAX_RADIUS, MAX_PRECISION_RADIUS, False, 100.2
End Sub

Private Sub Rad2TextBox_Enter()
   SelectAllText Rad2TextBox
End Sub



'DRAW SYMBOL CHECKBOX
Private Sub DrawSymbolCheckBox_Click()
   SaveCheckBoxSetting DrawSymbolCheckBox, SECTION_ARC_LINE_INT, KEY_OPTION_DRAW_SYMBOL
End Sub



'TEXT DIRECTION CHECKBOX
Private Sub TextAzCheckBox_Click()
   SaveCheckBoxSetting TextAzCheckBox, SECTION_ARC_LINE_INT, KEY_OPTION_TEXT_DIR
End Sub



'TEXT DISTANCE CHECKBOX
Private Sub TextDisCheckBox_Click()
   SaveCheckBoxSetting TextDisCheckBox, SECTION_ARC_LINE_INT, KEY_OPTION_TEXT_DIST
End Sub



'AZIMUTH OPTION
Private Sub AzOption_Click()
   SaveSetting APP_NAME, SECTION_ARC_LINE_INT, KEY_DIRECTION_TYPE, OPTION_DIR_TYPE_AZIMUTH
End Sub



'BEARING OPTION
Private Sub BearOptionButton_Click()
   SaveSetting APP_NAME, SECTION_ARC_LINE_INT, KEY_DIRECTION_TYPE, OPTION_DIR_TYPE_BEARING
End Sub



'SOLVE BUTTON
Private Sub SolveCommand_Click()
   Dim azimith1good As Boolean
   Dim sAzLine1 As Double
   Dim origPrec As Long
   Dim dirType As Integer
   Dim quad As Integer
   If Not DirStringToSAz(Az1TextBox.text, sAzLine1, origPrec, dirType, quad) Then
      Beep
      MsgBox "Direction Unknown"
   End If
'TRY TO SOLVE
   Dim Ray1 As Ray3d
   Ray1 = sAzToRay(POL1, sAzLine1)
   Dim Ray2 As Ray3d
   Dim sAz2 As Double
   sAz2 = sAzLine1 + 90#
   MakeSure360 sAzLine1
   Ray2 = sAzToRay(RP2, sAz2)
   Dim Inter1 As Point3d
   Dim Inter2 As Point3d
   Dim Frac1 As Double
   Dim Frac2 As Double
   If Not Ray3dRay3dIntersectXY(Ray1, Ray2, Inter1, Frac1, Inter2, Frac2) Then
      Beep
      MsgBox "Cannot solve."
      Exit Sub
   End If
   Dim distRPToRay As Double
   distRPToRay = InverseHD(RP2, Inter1)
   Dim Radius2 As Double
   Radius2 = Abs(CDbl(Rad2TextBox.text))
   If distRPToRay = Radius2 Then
'INTERSECTION IS ONLY SOLUTION, DRAW IT
      DrawIntLines POL1, RP2, Inter1
      Exit Sub
   ElseIf distRPToRay > Radius2 Then
'NO INTERSECTIONS, EXIT
      Beep
      MsgBox "Cannot solve."
      Exit Sub
   ElseIf distRPToRay = 0 Then
'INTERSECTION IS RADIUS POINT, CANNOT USE TRIANGLE TO SOLVE
      Dim halfChord As Double
      halfChord = Radius2
   Else
'USE RIGHT TRIANGLE TO SOLVE
      Dim X As Double
      X = distRPToRay / Radius2
      Dim missingAngle As Double
      missingAngle = Atn(-X / Sqr(-X * X + 1)) + 2 * Atn(1)
      halfChord = Sin(missingAngle) * Radius2
   End If
   Dim IntersectionA As Point3d
   IntersectionA = CoordFwdSAz(Inter1, sAzLine1, halfChord)
   sAzLine1 = sAzLine1 + 180#
   MakeSure360 sAzLine1
   Dim IntersectionB As Point3d
   IntersectionB = CoordFwdSAz(Inter2, sAzLine1, halfChord)
'CHECK SOLUTION
   Dim chkDist As Double
   chkDist = InverseHD(RP2, IntersectionB)
   If Round(chkDist, StrPrec(Rad2TextBox.text)) <> Radius2 Then
      MsgBox "Program blunder"
      Exit Sub
   End If
'GRAPHICALLY CHOOSE INTERSECTION
   Me.Hide
   Dim choosetool As New arcLineIntpickPrimitive
   choosetool.IntersectionA = IntersectionA
   choosetool.IntersectionB = IntersectionB
   CommandState.StartPrimitive choosetool
End Sub



'*************************************************************************************************************
'**********************************************SETTINGS TAB***************************************************
'TEXT ATTRIBUTES
'COLOR COMBOBOX
Private Sub ColorComboBox_AfterUpdate()
   ColorBoxOnUpdate ColorComboBox, SECTION_ARC_LINE_INT, KEY_COLOR
End Sub

'COLOR PICKER
Private Sub ChooseColorButton_Click()
   Dim MyColor As String
   If ChooseMyTableColor(MyColor) Then
      ColorComboBox.text = MyColor
      ColorComboBox_AfterUpdate
   End If
End Sub



'LEVEL COMBOBOX
Private Sub LevelComboBox_AfterUpdate()
   If Not LevelBoxOnUpdate(LevelComboBox, SECTION_ARC_LINE_INT, KEY_LEVEL) Then
      PopulateLevelBox LevelComboBox, SECTION_ARC_LINE_INT, KEY_LEVEL
      Beep
   End If
End Sub

'STYLE COMBOBOX
Private Sub StyleComboBox_AfterUpdate()
   If Not LineStyleBoxOnUpdate(StyleComboBox, SECTION_ARC_LINE_INT, KEY_STYLE) Then
      PopulateLinestyleBox StyleComboBox, SECTION_ARC_LINE_INT, KEY_STYLE
      Beep
   End If
End Sub


'WEIGHT COMBOBOX
Private Sub WeightComboBox_AfterUpdate()
   WeightBoxOnUpdate WeightComboBox, SECTION_ARC_LINE_INT, KEY_WEIGHT
End Sub

'FONT COMBOBOX
Private Sub FontComboBox_AfterUpdate()
   If Not FontBoxOnUpdate(FontComboBox, SECTION_ARC_LINE_INT, KEY_FONT) Then
      PopulateFontBox FontComboBox, SECTION_ARC_LINE_INT, KEY_FONT
      Beep
   End If
End Sub



'TEXT TEMPLATE
Private Function GetTextTemp() As TextElement
   Set GetTextTemp = CreateTextTemplate(SECTION_ARC_LINE_INT, _
                                        FontComboBox, _
                                        KEY_FONT, _
                                        LevelComboBox, _
                                        KEY_LEVEL, _
                                        WeightComboBox, _
                                        ColorComboBox, _
                                        StyleComboBox, _
                                        KEY_STYLE, , _
                                        msdTextJustificationCenterCenter)
End Function



'LINE ATTRIBUTES
'COLOR COMBOBOX
Private Sub ColorComboBox2_AfterUpdate()
   ColorBoxOnUpdate ColorComboBox2, SECTION_ARC_LINE_INT, KEY_COLOR2
End Sub

'COLOR PICKER
Private Sub ChooseColorButton2_Click()
   Dim MyColor As String
   If ChooseMyTableColor(MyColor) Then
      ColorComboBox2.text = MyColor
      ColorComboBox2_AfterUpdate
   End If
End Sub

'LEVEL COMBOBOX
Private Sub LevelComboBox2_AfterUpdate()
   If Not LevelBoxOnUpdate(LevelComboBox2, SECTION_ARC_LINE_INT, KEY_LEVEL2) Then
      PopulateLevelBox LevelComboBox2, SECTION_ARC_LINE_INT, KEY_LEVEL2
      Beep
   End If
End Sub

'STYLE COMBOBOX
Private Sub StyleComboBox2_AfterUpdate()
   If Not LineStyleBoxOnUpdate(StyleComboBox2, SECTION_ARC_LINE_INT, KEY_STYLE2) Then
      PopulateLinestyleBox StyleComboBox2, SECTION_ARC_LINE_INT, KEY_STYLE2
      Beep
   End If
End Sub

'WEIGHT COMBOBOX
Private Sub WeightComboBox2_AfterUpdate()
   WeightBoxOnUpdate WeightComboBox2, SECTION_ARC_LINE_INT, KEY_WEIGHT2
End Sub



'LINE TEMPLATE
Private Function GetLineTemp() As LineElement
   Set GetLineTemp = CreateLineTemplate(SECTION_ARC_LINE_INT, _
                                        LevelComboBox2, _
                                        KEY_LEVEL2, _
                                        WeightComboBox2, _
                                        ColorComboBox2, _
                                        StyleComboBox2, _
                                        KEY_STYLE2)
End Function



'PRECISION COMBOBOX
Private Sub PrecisionComboBox_Change()
   SaveSetting APP_NAME, SECTION_ARC_LINE_INT, KEY_PRECISION, FormatNumber(PrecisionComboBox.listIndex, 0)
End Sub



'DIRECTION PRECISION COMBOBOX
Private Sub AngPrecComboBox_Change()
   SaveSetting APP_NAME, SECTION_ARC_LINE_INT, KEY_PRECISION_ANG, AngPrecComboBox.text
End Sub



'SETTINGS BUTTON
Private Sub SettingsButton_Click()
   Setting
End Sub




'*************************************************************************************************************
'**********************************************USERFORM EVENTS************************************************
Private Sub UserForm_Initialize()
'NOTE THAT POINTS ON LINE ARE INTENTIONALLY NOT STORED.  THE REASON IS THAT
'IT ALLOW THE USER TO EASILY KNOW THAT THE POINT HAS NOT BEEN PICKED YET.

'INITIALIZE CHECK BOXES
   InitializeCheckBox TextAzCheckBox, SECTION_ARC_LINE_INT, KEY_OPTION_TEXT_DIR
   InitializeCheckBox TextDisCheckBox, SECTION_ARC_LINE_INT, KEY_OPTION_TEXT_DIST
   InitializeCheckBox DrawSymbolCheckBox, SECTION_ARC_LINE_INT, KEY_OPTION_DRAW_SYMBOL

'INITIALIZE AZIMUTH TEXTBOX
   LoadDirEntry Az1TextBox, SECTION_ARC_LINE_INT, KEY_DIRECTION
   Az1TextBox.MaxLength = MAX_LEN_DIR_STRING
   Az1TextBox_AfterUpdate

'INITIALIZE RADIUS TEXTBOX
   LoadRadiusEntry Rad2TextBox, SECTION_ARC_LINE_INT, KEY_RADIUS2
   Rad2TextBox.MaxLength = MAX_LEN_RADIUS_STRING

'INITIALIZE DISPLAY
   updateCoordDisp1 POL1
   updateCoordDisp2 RP2

'TEXT ATTRIBUTES
'LEVEL COMBOBOX
   PopulateLevelBox LevelComboBox, SECTION_ARC_LINE_INT, KEY_LEVEL
'COLOR COMBOBOX
   PopulateColorBox ColorComboBox, SECTION_ARC_LINE_INT, KEY_COLOR
'STYLE COMBOBOX
   PopulateLinestyleBox StyleComboBox, SECTION_ARC_LINE_INT, KEY_STYLE
'WEIGHT COMBOBOX
   PopulateWeightBox WeightComboBox, SECTION_ARC_LINE_INT, KEY_WEIGHT
'FONT COMBOBOX
   PopulateFontBox FontComboBox, SECTION_ARC_LINE_INT, KEY_FONT
   
'LINE ATTRIBUTES
'LEVEL COMBOBOX
   PopulateLevelBox LevelComboBox2, SECTION_ARC_LINE_INT, KEY_LEVEL2
'COLOR COMBOBOX
   PopulateColorBox ColorComboBox2, SECTION_ARC_LINE_INT, KEY_COLOR2
'STYLE COMBOBOX
   PopulateLinestyleBox StyleComboBox2, SECTION_ARC_LINE_INT, KEY_STYLE2
'WEIGHT COMBOBOX
   PopulateWeightBox WeightComboBox2, SECTION_ARC_LINE_INT, KEY_WEIGHT2

'POPULATE PRECISION COMBOBOX
   PrecisionComboBox.style = fmStyleDropDownList
   PrecisionComboBox.Clear
   PrecisionComboBox.AddItem "2"
   PrecisionComboBox.AddItem "3"
   PrecisionComboBox.AddItem "4"

'SET INITIAL PRECISION (INDEX)
   PrecisionComboBox.listIndex = CLng(GetSetting(APP_NAME, SECTION_ARC_LINE_INT, KEY_PRECISION, "0"))

'POPULATE DIRECTION PRECISION BOX
   AngPrecComboBox.style = fmStyleDropDownList
   AngPrecComboBox.Clear
   AngPrecComboBox.AddItem OPTION_PREC_ANG_SEC
   AngPrecComboBox.AddItem OPTION_PREC_ANG_SEC1
   AngPrecComboBox.AddItem OPTION_PREC_ANG_SEC01
   AngPrecComboBox.AddItem OPTION_PREC_ANG_SEC001
   AngPrecComboBox.text = GetSetting(APP_NAME, SECTION_ARC_LINE_INT, KEY_PRECISION_ANG, OPTION_PREC_ANG_SEC)

'MOVE INTO LAST POSITION
   If GetSetting(APP_NAME, SECTION_ARC_LINE_INT, KEY_START_TOP, "") = "" Then
      Me.StartUpPosition = 1
   Else
      Me.StartUpPosition = 0
      Me.Top = CDbl(GetSetting(APP_NAME, SECTION_ARC_LINE_INT, KEY_START_TOP, WINDOW_DEFAULT_TOP))
      Me.Left = CDbl(GetSetting(APP_NAME, SECTION_ARC_LINE_INT, KEY_START_LEFT, WINDOW_DEFAULT_LEFT))
   End If
   
'START ON MAIN PAGE
   Me.MultiPage1.value = 0

'SET COMMAND NAME IN TITLE BLOCK
   Me.Caption = COMMAND_NAME_ARC_LINE_INT
End Sub



Private Sub UserForm_QueryClose(Cancel As Integer, CloseMode As Integer)
'SAVE USERFORM POSITION
   SaveSetting APP_NAME, SECTION_ARC_LINE_INT, KEY_START_TOP, FormatNumber(Me.Top, 2)
   SaveSetting APP_NAME, SECTION_ARC_LINE_INT, KEY_START_LEFT, FormatNumber(Me.Left, 2)
End Sub



Private Sub UserForm_Terminate()
   CommandState.StartDefaultCommand
End Sub

Attribute VB_Name = "FrmAzAzInt"
Attribute VB_Base = "0{2C2ECEA6-F8D9-4F7D-8392-6F00782C39E5}{2EDF52D3-81B3-4829-BEE5-1B30AF1A8F61}"
Attribute VB_GlobalNameSpace = False
Attribute VB_Creatable = False
Attribute VB_PredeclaredId = True
Attribute VB_Exposed = False
Attribute VB_TemplateDerived = False
Attribute VB_Customizable = False
















'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.



'GENERAL NOTES:
'PROGRAM ASSUMES MASTER UNIT IS FOOT OR SURVEY FOOT, SOME KIND OF FOOT

Option Explicit

Private Const COORD_DISP_PREC          As Long = 4
Private Const TEXTBOX_DIRECTION_1      As Integer = 1
Private Const TEXTBOX_DIRECTION_2      As Integer = 2

Private textBoxNumber                  As Integer

Private POL1                           As Point3d
Private POL2                           As Point3d

'*************************************************************************************************************
'**********************************************INTRFACE WITH ILOCATE******************************************
Public Sub EnterText(ByVal Entry As String)
   Select Case textBoxNumber
      Case TEXTBOX_DIRECTION_1
         Az1TextBox.text = Entry
         Az1TextBox_AfterUpdate
      Case TEXTBOX_DIRECTION_2
         Az2TextBox.text = Entry
         Az2TextBox_AfterUpdate
   End Select
End Sub



Private Sub PickSubToo(boxNumber As Integer)
   textBoxNumber = boxNumber
   Dim pickTool As New AzAzIntLocateText
   Set pickTool.hostForm = Me
   CommandState.StartLocate pickTool
   Me.Hide
End Sub



'*************************************************************************************************************
'***************************************************DISPLAY***************************************************
Private Sub updateCoordDisp1(Coord As Point3d)
   Easting1Label.Caption = DoubleToEastingString(Coord.X, COORD_DISP_PREC)
   Northing1Label.Caption = DoubleToNorthingString(Coord.Y, COORD_DISP_PREC)
End Sub



Private Sub updateCoordDisp2(Coord As Point3d)
   Easting2Label.Caption = DoubleToEastingString(Coord.X, COORD_DISP_PREC)
   Northing2Label.Caption = DoubleToNorthingString(Coord.Y, COORD_DISP_PREC)
End Sub



'*************************************************************************************************************
'***********************************************OTHER*********************************************************
Private Function GetPrecision() As Long
    GetPrecision = CLng(PrecisionComboBox.text)
End Function



'*************************************************************************************************************
'************************************************MAIN TAB*****************************************************
'LINE 1 POINT ON LINE PICK BUTTON
Private Sub Pick1Button_Click()
   FrmAzAzInt.Hide

   Dim ThePickedPoint As Point3d
   If PickSub(COMMAND_NAME_AZ_AZ_INT, "Pick Point on Line 1.", ThePickedPoint) Then
      POL1 = ThePickedPoint
      updateCoordDisp1 POL1
   End If

   FrmAzAzInt.Show
   Az1TextBox.SetFocus
End Sub



'LINE 1 DIRECTION TEXTBOX
Private Sub Az1TextBox_AfterUpdate()
   SaveDirEntry Az1TextBox, SECTION_AZ_AZ_INT, KEY_DIRECTION, STYLE_ANGLE_SPACE Or STYLE_ANGLE_LEAD
End Sub

Private Sub Az1TextBox_Enter()
   SelectAllText Az1TextBox
End Sub



'LINE 1 DIRECTION PICK BUTTON
Private Sub PickDirButton_Click()
   PickSubToo TEXTBOX_DIRECTION_1
End Sub



'LINE 2 POINT ON LINE PICK BUTTON
Private Sub Pick2Button_Click()
   FrmAzAzInt.Hide

   Dim ThePickedPoint As Point3d
   If PickSub(COMMAND_NAME_AZ_AZ_INT, "Pick Point on Line 2.", ThePickedPoint) Then
      POL2 = ThePickedPoint
      updateCoordDisp2 POL2
   End If

   FrmAzAzInt.Show
End Sub



'LINE 2 DIRECTION TEXT BOX
Private Sub Az2TextBox_AfterUpdate()
   SaveDirEntry Az2TextBox, SECTION_AZ_AZ_INT, KEY_DIRECTION2, STYLE_ANGLE_SPACE Or STYLE_ANGLE_LEAD
End Sub

Private Sub Az2TextBox_Enter()
   SelectAllText Az2TextBox
End Sub



'LINE 2 DIRECTION PICK BUTTON
Private Sub PickDir2Button_Click()
   PickSubToo TEXTBOX_DIRECTION_2
End Sub



'DRAW SYMBOL CHECKBOX
Private Sub DrawSymbolCheckBox_Click()
   SaveCheckBoxSetting DrawSymbolCheckBox, SECTION_AZ_AZ_INT, KEY_OPTION_DRAW_SYMBOL
End Sub



'TEXT DIRECTIONS CHECKBOX
Private Sub TextAzCheckBox_Click()
   SaveCheckBoxSetting TextAzCheckBox, SECTION_AZ_AZ_INT, KEY_OPTION_TEXT_DIR
End Sub



'TEXT DISTANCES CHECKBOX
Private Sub TextDisCheckBox_Click()
   SaveCheckBoxSetting TextDisCheckBox, SECTION_AZ_AZ_INT, KEY_OPTION_TEXT_DIST
End Sub



'SOLVE BUTTON
Private Sub SolveCommand_Click()
   CommandState.CommandName = COMMAND_NAME_AZ_AZ_INT
   Dim azimith1good As Boolean
   Dim sAzLine1 As Double
   Dim origPrec As Long
   Dim dirType As Integer
   Dim quad As Integer
   azimith1good = DirStringToSAz(Az1TextBox.text, sAzLine1, origPrec, dirType, quad)

   Dim azimith2good As Boolean
   Dim sAzLine2 As Double
   azimith2good = DirStringToSAz(Az2TextBox.text, sAzLine2, origPrec, dirType, quad)

   If (azimith1good And azimith2good) Then
'TRY TO SOLVE
      Dim Ray1 As Ray3d
      Ray1 = sAzToRay(POL1, sAzLine1)
      Dim Ray2 As Ray3d
      Ray2 = sAzToRay(POL2, sAzLine2)
      
      Dim Inter1 As Point3d
      Dim Inter2 As Point3d
      Dim Frac1 As Double
      Dim Frac2 As Double
      If Ray3dRay3dIntersectXY(Ray1, Ray2, Inter1, Frac1, Inter2, Frac2) Then
'ADD GRAPHIC ELEMENTS
         If DrawIntersection(Inter1, Az1TextBox.text, Inter2, Az2TextBox.text) Then
         End If
      Else
         Beep
         MsgBox "Cannot solve."
      End If
   Else
'NEED TO ENTER AZIMUTH
      Beep
      MsgBox "Insufficient facts."
   End If
   CommandState.StartDefaultCommand
End Sub



'*************************************************************************************************************
'**********************************************SETTINGS TAB***************************************************
'TEXT ATTRIBUTES
'COLOR COMBOBOX
Private Sub ColorComboBox_AfterUpdate()
   ColorBoxOnUpdate ColorComboBox, SECTION_AZ_AZ_INT, KEY_COLOR
End Sub

'COLOR PICKER
Private Sub ChooseColorButton_Click()
   Dim MyColor As String
   If ChooseMyTableColor(MyColor) Then
      ColorComboBox.text = MyColor
      ColorComboBox_AfterUpdate
   End If
End Sub



'LEVEL COMBOBOX
Private Sub LevelComboBox_AfterUpdate()
   If Not LevelBoxOnUpdate(LevelComboBox, SECTION_AZ_AZ_INT, KEY_LEVEL) Then
      PopulateLevelBox LevelComboBox, SECTION_AZ_AZ_INT, KEY_LEVEL
      Beep
   End If
End Sub

'STYLE COMBOBOX
Private Sub StyleComboBox_AfterUpdate()
   If Not LineStyleBoxOnUpdate(StyleComboBox, SECTION_AZ_AZ_INT, KEY_STYLE) Then
      PopulateLinestyleBox StyleComboBox, SECTION_AZ_AZ_INT, KEY_STYLE
      Beep
   End If
End Sub

'WEIGHT COMBOBOX
Private Sub WeightComboBox_AfterUpdate()
   WeightBoxOnUpdate WeightComboBox, SECTION_AZ_AZ_INT, KEY_WEIGHT
End Sub

'FONT COMBOBOX
Private Sub FontComboBox_AfterUpdate()
   If Not FontBoxOnUpdate(FontComboBox, SECTION_AZ_AZ_INT, KEY_FONT) Then
      PopulateFontBox FontComboBox, SECTION_AZ_AZ_INT, KEY_FONT
      Beep
   End If
End Sub



'TEXT TEMPLATE
Private Function GetTextTemp() As TextElement
   Set GetTextTemp = CreateTextTemplate(SECTION_AZ_AZ_INT, _
                                        FontComboBox, _
                                        KEY_FONT, _
                                        LevelComboBox, _
                                        KEY_LEVEL, _
                                        WeightComboBox, _
                                        ColorComboBox, _
                                        StyleComboBox, _
                                        KEY_STYLE, , _
                                        msdTextJustificationCenterCenter)
End Function



'LINE ATTRIBUTES
'COLOR COMBOBOX
Private Sub ColorComboBox2_AfterUpdate()
   ColorBoxOnUpdate ColorComboBox2, SECTION_AZ_AZ_INT, KEY_COLOR2
End Sub

'COLOR PICKER
Private Sub ChooseColorButton2_Click()
   Dim MyColor As String
   If ChooseMyTableColor(MyColor) Then
      ColorComboBox2.text = MyColor
      ColorComboBox2_AfterUpdate
   End If
End Sub

'LEVEL COMBOBOX
Private Sub LevelComboBox2_AfterUpdate()
   If Not LevelBoxOnUpdate(LevelComboBox2, SECTION_AZ_AZ_INT, KEY_LEVEL2) Then
      PopulateLevelBox LevelComboBox2, SECTION_AZ_AZ_INT, KEY_LEVEL2
      Beep
   End If
End Sub

'STYLE COMBOBOX
Private Sub StyleComboBox2_AfterUpdate()
   If Not LineStyleBoxOnUpdate(StyleComboBox2, SECTION_AZ_AZ_INT, KEY_STYLE2) Then
      PopulateLinestyleBox StyleComboBox2, SECTION_AZ_AZ_INT, KEY_STYLE2
      Beep
   End If
End Sub

'WEIGHT COMBOBOX
Private Sub WeightComboBox2_AfterUpdate()
   WeightBoxOnUpdate WeightComboBox2, SECTION_AZ_AZ_INT, KEY_WEIGHT2
End Sub



'LINE TEMPLATE
Private Function GetLineTemp() As LineElement
   Set GetLineTemp = CreateLineTemplate(SECTION_AZ_AZ_INT, _
                                        LevelComboBox2, _
                                        KEY_LEVEL2, _
                                        WeightComboBox2, _
                                        ColorComboBox2, _
                                        StyleComboBox2, _
                                        KEY_STYLE2)
End Function



'PRECISION COMBOBOX
Private Sub PrecisionComboBox_Change()
   SaveSetting APP_NAME, SECTION_AZ_AZ_INT, KEY_PRECISION, FormatNumber(PrecisionComboBox.listIndex, 0)
End Sub



'SETTINGS BUTTON
Private Sub SettingsButton_Click()
   Setting
End Sub



'*************************************************************************************************************
'************************************************DRAWING******************************************************
Private Function DrawIntersection(Inter1 As Point3d, _
                                  DMS1Sring As String, _
                                  Inter2 As Point3d, _
                                  DMS2String As String) As Boolean
   DrawIntersection = False
   If ActiveModelReference.IsReadOnly Then
      Exit Function
   End If

'GET ACTIVE VIEW IF ANY
   Dim mySelectedView As view
   Set mySelectedView = GetSelectedView()

'QUIT IF NO VIEW OPEN
   If mySelectedView Is Nothing Then
      Beep
      Exit Function
   End If

'DRAW LINES TO INTERSECTION
   Dim lineTemplate As Element
   Set lineTemplate = GetLineTemp()
   Dim line1 As LineElement
   Set line1 = CreateLineElement2(lineTemplate, POL1, Inter1)
   Dim line2 As LineElement
   Set line2 = CreateLineElement2(lineTemplate, POL2, Inter2)

'DETERMINE IF LINES POINTING LEFT
   Dim viewRotRadians As Double
   viewRotRadians = TheViewRotRadians(mySelectedView)
   Dim line1PointsLeft As Boolean
   line1PointsLeft = linePointsLeft(InverseAzimuth(line1.startPoint, line1.endPoint), viewRotRadians)
   Dim line2PointsLeft As Boolean
   line2PointsLeft = linePointsLeft(InverseAzimuth(line2.startPoint, line2.endPoint), viewRotRadians)

'CALCULATE METRICS
   Dim characterSize As Double
   characterSize = GetCharSize()
   Dim LineSpacing As Double
   LineSpacing = characterSize / 3#
   Dim vertOffset As Double
   vertOffset = characterSize / 2# + LineSpacing

'CREATE TEXT TEMPLATE
   Dim textTemplate As TextElement
   Set textTemplate = GetTextTemp()

'DRAW SYMBOL(S) IF REQUESTED
   If DrawSymbolCheckBox.value Then
'ROTATION IS IRRELEVANT SINCE SYMBOLS IS A CIRCLE
      Dim symLine1 As CellElement
      Set symLine1 = CreateSymbol5Cell(lineTemplate, Inter1, characterSize, viewRotRadians)
      ActiveModelReference.AddElement symLine1
      symLine1.Redraw
'DRAW SECOND SYMBOL IF TWO DIFFERENT INTERSECTIONS POINTS
      If Inter1.z <> Inter2.z Then
         Dim symLine2 As CellElement
         Set symLine2 = CreateSymbol5Cell(lineTemplate, Inter2, characterSize, viewRotRadians)
         ActiveModelReference.AddElement symLine2
         symLine2.Redraw
      End If
   End If

'DRAW DIRECTION IF CHECKED
   If TextAzCheckBox.value Then
      TextTheLine textTemplate, line1, ReplaceDegreeSymbol2(Az1TextBox.text), vertOffset, line1PointsLeft
      TextTheLine textTemplate, line2, ReplaceDegreeSymbol2(Az2TextBox.text), vertOffset, line2PointsLeft
'MOVE OFFSSET TO UNDER LINE SINCE JUST USED THE TOP
      vertOffset = -vertOffset
   End If

'DRAW DISTANCE IF CHECKED
   If TextDisCheckBox.value Then
      TextTheLine textTemplate, line1, FormatNumber(line1.length, GetPrecision(), vbTrue, vbFalse, vbTrue), vertOffset, line1PointsLeft
      TextTheLine textTemplate, line2, FormatNumber(line2.length, GetPrecision(), vbTrue, vbFalse, vbTrue), vertOffset, line2PointsLeft
   End If

   ActiveModelReference.AddElement line1
   line1.Redraw
   ActiveModelReference.AddElement line2
   line2.Redraw
   DrawIntersection = True
End Function



'*************************************************************************************************************
'**********************************************USERFORM EVENTS************************************************
Private Sub UserForm_Initialize()
'NOTE THAT POINTS ON LINE ARE INTENTIONALLY NOT STORED.  THE REASON IS THAT
'IT ALLOW THE USER TO EASILY KNOW THAT THE POINT HAS NOT BEEN PICKED YET.

'INITIALIZE CHECK BOXES
   InitializeCheckBox TextAzCheckBox, SECTION_AZ_AZ_INT, KEY_OPTION_TEXT_DIR
   InitializeCheckBox TextDisCheckBox, SECTION_AZ_AZ_INT, KEY_OPTION_TEXT_DIST
   InitializeCheckBox DrawSymbolCheckBox, SECTION_AZ_AZ_INT, KEY_OPTION_DRAW_SYMBOL

'INITIALIZE AZIMUTH TEXT BOXES
   LoadDirEntry Az1TextBox, SECTION_AZ_AZ_INT, KEY_DIRECTION
   Az1TextBox.MaxLength = MAX_LEN_DIR_STRING
   Az1TextBox_AfterUpdate
   LoadDirEntry Az2TextBox, SECTION_AZ_AZ_INT, KEY_DIRECTION2
   Az2TextBox.MaxLength = MAX_LEN_DIR_STRING
   Az2TextBox_AfterUpdate

'INITIALIZE DISPLAY
   updateCoordDisp1 POL1
   updateCoordDisp2 POL2

'TEXT ATTRIBUTES
'LEVEL COMBOBOX
   PopulateLevelBox LevelComboBox, SECTION_AZ_AZ_INT, KEY_LEVEL
'COLOR COMBOBOX
   PopulateColorBox ColorComboBox, SECTION_AZ_AZ_INT, KEY_COLOR
'STYLE COMBOBOX
   PopulateLinestyleBox StyleComboBox, SECTION_AZ_AZ_INT, KEY_STYLE
'WEIGHT COMBOBOX
   PopulateWeightBox WeightComboBox, SECTION_AZ_AZ_INT, KEY_WEIGHT
'FONT COMBOBOX
   PopulateFontBox FontComboBox, SECTION_AZ_AZ_INT, KEY_FONT
   
'LINE ATTRIBUTES
'LEVEL COMBOBOX
   PopulateLevelBox LevelComboBox2, SECTION_AZ_AZ_INT, KEY_LEVEL2
'COLOR COMBOBOX
   PopulateColorBox ColorComboBox2, SECTION_AZ_AZ_INT, KEY_COLOR2
'STYLE COMBOBOX
   PopulateLinestyleBox StyleComboBox2, SECTION_AZ_AZ_INT, KEY_STYLE2
'WEIGHT COMBOBOX
   PopulateWeightBox WeightComboBox2, SECTION_AZ_AZ_INT, KEY_WEIGHT2

'POPULATE PRECISION COMBOBOX
   PrecisionComboBox.style = fmStyleDropDownList
   PrecisionComboBox.Clear
   PrecisionComboBox.AddItem "2"
   PrecisionComboBox.AddItem "3"
   PrecisionComboBox.AddItem "4"

'SET INITIAL PRECISION (INDEX)
   PrecisionComboBox.listIndex = CLng(GetSetting(APP_NAME, SECTION_AZ_AZ_INT, KEY_PRECISION, "0"))

'MOVE INTO LAST POSITION
   If GetSetting(APP_NAME, SECTION_AZ_AZ_INT, KEY_START_TOP, "") = "" Then
      Me.StartUpPosition = 1
   Else
      Me.StartUpPosition = 0
      Me.Top = CDbl(GetSetting(APP_NAME, SECTION_AZ_AZ_INT, KEY_START_TOP, WINDOW_DEFAULT_TOP))
      Me.Left = CDbl(GetSetting(APP_NAME, SECTION_AZ_AZ_INT, KEY_START_LEFT, WINDOW_DEFAULT_LEFT))
   End If
   
'START ON MAIN PAGE
   Me.MultiPage1.value = 0

'SET COMMAND NAME IN TITLE BLOCK
   Me.Caption = COMMAND_NAME_AZ_AZ_INT
End Sub


Private Sub UserForm_QueryClose(Cancel As Integer, CloseMode As Integer)
'SAVE USERFORM POSITION
   SaveSetting APP_NAME, SECTION_AZ_AZ_INT, KEY_START_TOP, FormatNumber(Me.Top, 2)
   SaveSetting APP_NAME, SECTION_AZ_AZ_INT, KEY_START_LEFT, FormatNumber(Me.Left, 2)
End Sub


Private Sub UserForm_Terminate()
   CommandState.StartDefaultCommand
End Sub

Attribute VB_Name = "FrmChooseColor"
Attribute VB_Base = "0{B8F95F91-7B6A-444D-91E4-8BB2C712D181}{53A59830-A7FE-4332-B491-0C2CC21BFD51}"
Attribute VB_GlobalNameSpace = False
Attribute VB_Creatable = False
Attribute VB_PredeclaredId = True
Attribute VB_Exposed = False
Attribute VB_TemplateDerived = False
Attribute VB_Customizable = False
















'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit

Private Sub ChoseColor(TheColor As String)
   PutWasChosen True
   PutTheColorString TheColor
   Unload Me
End Sub


Private Sub ByLevelButton_Click()
   ChoseColor BY_LEVEL
End Sub

Private Sub UserForm_Initialize()
   PutWasChosen False
   InitializeColors

'MOVE INTO LAST POSITION
   If GetSetting(APP_NAME, SECTION_CHOOSE_COLOR, KEY_START_TOP, "") = "" Then
      Me.StartUpPosition = 1
   Else
      Me.StartUpPosition = 0
      Me.Top = CDbl(GetSetting(APP_NAME, SECTION_CHOOSE_COLOR, KEY_START_TOP, WINDOW_DEFAULT_TOP))
      Me.Left = CDbl(GetSetting(APP_NAME, SECTION_CHOOSE_COLOR, KEY_START_LEFT, WINDOW_DEFAULT_LEFT))
   End If
   
'SET CAPTION FOR TITLE BAR
   Me.Caption = COMMAND_NAME_CHOOSE_COLOR

'SET PROMPTS
   ShowCommand COMMAND_NAME_CHOOSE_COLOR
   ShowPrompt "Pick color"
   ShowStatus ""
End Sub

Private Sub UserForm_QueryClose(Cancel As Integer, CloseMode As Integer)
'SAVE USERFORM POSITION
   SaveSetting APP_NAME, SECTION_CHOOSE_COLOR, KEY_START_TOP, FormatNumber(Me.Top, 2)
   SaveSetting APP_NAME, SECTION_CHOOSE_COLOR, KEY_START_LEFT, FormatNumber(Me.Left, 2)
End Sub

Public Sub ExtractRGB(ByVal longColor As Long, intRed As Byte, intGreen As Byte, intBlue As Byte)
'CODE FROM MICROSTATION VBA HELP FILE
    Dim lngColor As Long

    lngColor = longColor
    intRed = lngColor Mod &H100
    lngColor = lngColor \ &H100
    intGreen = lngColor Mod &H100
    lngColor = lngColor \ &H100
    intBlue = lngColor Mod &H100
End Sub

Private Function TableNumberToRGB(ByVal ColorNumber As Long) As Long
    Dim ct As ColorTable
    Dim ArrayRGBLongs() As Long
    Dim color As Long
    Dim r As Byte, g As Byte, b As Byte
    
    ' Get a copy of the colortable that is currently attached to the active design file
    Set ct = Application.ActiveDesignFile.ExtractColorTable
    
    ' Get the rgb color at index
    color = ct.GetColorAtIndex(ColorNumber)
    ExtractRGB color, r, g, b
    
    'RETURN RGB
    TableNumberToRGB = RGB(r, g, b)
End Function

Private Sub InitializeColors()
   Color0.BackColor = TableNumberToRGB(0)
   Color1.BackColor = TableNumberToRGB(1)
   Color2.BackColor = TableNumberToRGB(2)
   Color3.BackColor = TableNumberToRGB(3)
   Color4.BackColor = TableNumberToRGB(4)
   Color5.BackColor = TableNumberToRGB(5)
   Color6.BackColor = TableNumberToRGB(6)
   Color7.BackColor = TableNumberToRGB(7)
   Color8.BackColor = TableNumberToRGB(8)
   Color9.BackColor = TableNumberToRGB(9)
   Color10.BackColor = TableNumberToRGB(10)
   Color11.BackColor = TableNumberToRGB(11)
   Color12.BackColor = TableNumberToRGB(12)
   Color13.BackColor = TableNumberToRGB(13)
   Color14.BackColor = TableNumberToRGB(14)
   Color15.BackColor = TableNumberToRGB(15)
   Color16.BackColor = TableNumberToRGB(16)
   Color17.BackColor = TableNumberToRGB(17)
   Color18.BackColor = TableNumberToRGB(18)
   Color19.BackColor = TableNumberToRGB(19)
   Color20.BackColor = TableNumberToRGB(20)
   Color21.BackColor = TableNumberToRGB(21)
   Color22.BackColor = TableNumberToRGB(22)
   Color23.BackColor = TableNumberToRGB(23)
   Color24.BackColor = TableNumberToRGB(24)
   Color25.BackColor = TableNumberToRGB(25)
   Color26.BackColor = TableNumberToRGB(26)
   Color27.BackColor = TableNumberToRGB(27)
   Color28.BackColor = TableNumberToRGB(28)
   Color29.BackColor = TableNumberToRGB(29)
   Color30.BackColor = TableNumberToRGB(30)
   Color31.BackColor = TableNumberToRGB(31)
   Color32.BackColor = TableNumberToRGB(32)
   Color33.BackColor = TableNumberToRGB(33)
   Color34.BackColor = TableNumberToRGB(34)
   Color35.BackColor = TableNumberToRGB(35)
   Color36.BackColor = TableNumberToRGB(36)
   Color37.BackColor = TableNumberToRGB(37)
   Color38.BackColor = TableNumberToRGB(38)
   Color39.BackColor = TableNumberToRGB(39)
   Color40.BackColor = TableNumberToRGB(40)
   Color41.BackColor = TableNumberToRGB(41)
   Color42.BackColor = TableNumberToRGB(42)
   Color43.BackColor = TableNumberToRGB(43)
   Color44.BackColor = TableNumberToRGB(44)
   Color45.BackColor = TableNumberToRGB(45)
   Color46.BackColor = TableNumberToRGB(46)
   Color47.BackColor = TableNumberToRGB(47)
   Color48.BackColor = TableNumberToRGB(48)
   Color49.BackColor = TableNumberToRGB(49)
   Color50.BackColor = TableNumberToRGB(50)
   Color51.BackColor = TableNumberToRGB(51)
   Color52.BackColor = TableNumberToRGB(52)
   Color53.BackColor = TableNumberToRGB(53)
   Color54.BackColor = TableNumberToRGB(54)
   Color55.BackColor = TableNumberToRGB(55)
   Color56.BackColor = TableNumberToRGB(56)
   Color57.BackColor = TableNumberToRGB(57)
   Color58.BackColor = TableNumberToRGB(58)
   Color59.BackColor = TableNumberToRGB(59)
   Color60.BackColor = TableNumberToRGB(60)
   Color61.BackColor = TableNumberToRGB(61)
   Color62.BackColor = TableNumberToRGB(62)
   Color63.BackColor = TableNumberToRGB(63)
   Color64.BackColor = TableNumberToRGB(64)
   Color65.BackColor = TableNumberToRGB(65)
   Color66.BackColor = TableNumberToRGB(66)
   Color67.BackColor = TableNumberToRGB(67)
   Color68.BackColor = TableNumberToRGB(68)
   Color69.BackColor = TableNumberToRGB(69)
   Color70.BackColor = TableNumberToRGB(70)
   Color71.BackColor = TableNumberToRGB(71)
   Color72.BackColor = TableNumberToRGB(72)
   Color73.BackColor = TableNumberToRGB(73)
   Color74.BackColor = TableNumberToRGB(74)
   Color75.BackColor = TableNumberToRGB(75)
   Color76.BackColor = TableNumberToRGB(76)
   Color77.BackColor = TableNumberToRGB(77)
   Color78.BackColor = TableNumberToRGB(78)
   Color79.BackColor = TableNumberToRGB(79)
   Color80.BackColor = TableNumberToRGB(80)
   Color81.BackColor = TableNumberToRGB(81)
   Color82.BackColor = TableNumberToRGB(82)
   Color83.BackColor = TableNumberToRGB(83)
   Color84.BackColor = TableNumberToRGB(84)
   Color85.BackColor = TableNumberToRGB(85)
   Color86.BackColor = TableNumberToRGB(86)
   Color87.BackColor = TableNumberToRGB(87)
   Color88.BackColor = TableNumberToRGB(88)
   Color89.BackColor = TableNumberToRGB(89)
   Color90.BackColor = TableNumberToRGB(90)
   Color91.BackColor = TableNumberToRGB(91)
   Color92.BackColor = TableNumberToRGB(92)
   Color93.BackColor = TableNumberToRGB(93)
   Color94.BackColor = TableNumberToRGB(94)
   Color95.BackColor = TableNumberToRGB(95)
   Color96.BackColor = TableNumberToRGB(96)
   Color97.BackColor = TableNumberToRGB(97)
   Color98.BackColor = TableNumberToRGB(98)
   Color99.BackColor = TableNumberToRGB(99)
   Color100.BackColor = TableNumberToRGB(100)
   Color101.BackColor = TableNumberToRGB(101)
   Color102.BackColor = TableNumberToRGB(102)
   Color103.BackColor = TableNumberToRGB(103)
   Color104.BackColor = TableNumberToRGB(104)
   Color105.BackColor = TableNumberToRGB(105)
   Color106.BackColor = TableNumberToRGB(106)
   Color107.BackColor = TableNumberToRGB(107)
   Color108.BackColor = TableNumberToRGB(108)
   Color109.BackColor = TableNumberToRGB(109)
   Color110.BackColor = TableNumberToRGB(110)
   Color111.BackColor = TableNumberToRGB(111)
   Color112.BackColor = TableNumberToRGB(112)
   Color113.BackColor = TableNumberToRGB(113)
   Color114.BackColor = TableNumberToRGB(114)
   Color115.BackColor = TableNumberToRGB(115)
   Color116.BackColor = TableNumberToRGB(116)
   Color117.BackColor = TableNumberToRGB(117)
   Color118.BackColor = TableNumberToRGB(118)
   Color119.BackColor = TableNumberToRGB(119)
   Color120.BackColor = TableNumberToRGB(120)
   Color121.BackColor = TableNumberToRGB(121)
   Color122.BackColor = TableNumberToRGB(122)
   Color123.BackColor = TableNumberToRGB(123)
   Color124.BackColor = TableNumberToRGB(124)
   Color125.BackColor = TableNumberToRGB(125)
   Color126.BackColor = TableNumberToRGB(126)
   Color127.BackColor = TableNumberToRGB(127)
   Color128.BackColor = TableNumberToRGB(128)
   Color129.BackColor = TableNumberToRGB(129)
   Color130.BackColor = TableNumberToRGB(130)
   Color131.BackColor = TableNumberToRGB(131)
   Color132.BackColor = TableNumberToRGB(132)
   Color133.BackColor = TableNumberToRGB(133)
   Color134.BackColor = TableNumberToRGB(134)
   Color135.BackColor = TableNumberToRGB(135)
   Color136.BackColor = TableNumberToRGB(136)
   Color137.BackColor = TableNumberToRGB(137)
   Color138.BackColor = TableNumberToRGB(138)
   Color139.BackColor = TableNumberToRGB(139)
   Color140.BackColor = TableNumberToRGB(140)
   Color141.BackColor = TableNumberToRGB(141)
   Color142.BackColor = TableNumberToRGB(142)
   Color143.BackColor = TableNumberToRGB(143)
   Color144.BackColor = TableNumberToRGB(144)
   Color145.BackColor = TableNumberToRGB(145)
   Color146.BackColor = TableNumberToRGB(146)
   Color147.BackColor = TableNumberToRGB(147)
   Color148.BackColor = TableNumberToRGB(148)
   Color149.BackColor = TableNumberToRGB(149)
   Color150.BackColor = TableNumberToRGB(150)
   Color151.BackColor = TableNumberToRGB(151)
   Color152.BackColor = TableNumberToRGB(152)
   Color153.BackColor = TableNumberToRGB(153)
   Color154.BackColor = TableNumberToRGB(154)
   Color155.BackColor = TableNumberToRGB(155)
   Color156.BackColor = TableNumberToRGB(156)
   Color157.BackColor = TableNumberToRGB(157)
   Color158.BackColor = TableNumberToRGB(158)
   Color159.BackColor = TableNumberToRGB(159)
   Color160.BackColor = TableNumberToRGB(160)
   Color161.BackColor = TableNumberToRGB(161)
   Color162.BackColor = TableNumberToRGB(162)
   Color163.BackColor = TableNumberToRGB(163)
   Color164.BackColor = TableNumberToRGB(164)
   Color165.BackColor = TableNumberToRGB(165)
   Color166.BackColor = TableNumberToRGB(166)
   Color167.BackColor = TableNumberToRGB(167)
   Color168.BackColor = TableNumberToRGB(168)
   Color169.BackColor = TableNumberToRGB(169)
   Color170.BackColor = TableNumberToRGB(170)
   Color171.BackColor = TableNumberToRGB(171)
   Color172.BackColor = TableNumberToRGB(172)
   Color173.BackColor = TableNumberToRGB(173)
   Color174.BackColor = TableNumberToRGB(174)
   Color175.BackColor = TableNumberToRGB(175)
   Color176.BackColor = TableNumberToRGB(176)
   Color177.BackColor = TableNumberToRGB(177)
   Color178.BackColor = TableNumberToRGB(178)
   Color179.BackColor = TableNumberToRGB(179)
   Color180.BackColor = TableNumberToRGB(180)
   Color181.BackColor = TableNumberToRGB(181)
   Color182.BackColor = TableNumberToRGB(182)
   Color183.BackColor = TableNumberToRGB(183)
   Color184.BackColor = TableNumberToRGB(184)
   Color185.BackColor = TableNumberToRGB(185)
   Color186.BackColor = TableNumberToRGB(186)
   Color187.BackColor = TableNumberToRGB(187)
   Color188.BackColor = TableNumberToRGB(188)
   Color189.BackColor = TableNumberToRGB(189)
   Color190.BackColor = TableNumberToRGB(190)
   Color191.BackColor = TableNumberToRGB(191)
   Color192.BackColor = TableNumberToRGB(192)
   Color193.BackColor = TableNumberToRGB(193)
   Color194.BackColor = TableNumberToRGB(194)
   Color195.BackColor = TableNumberToRGB(195)
   Color196.BackColor = TableNumberToRGB(196)
   Color197.BackColor = TableNumberToRGB(197)
   Color198.BackColor = TableNumberToRGB(198)
   Color199.BackColor = TableNumberToRGB(199)
   Color200.BackColor = TableNumberToRGB(200)
   Color201.BackColor = TableNumberToRGB(201)
   Color202.BackColor = TableNumberToRGB(202)
   Color203.BackColor = TableNumberToRGB(203)
   Color204.BackColor = TableNumberToRGB(204)
   Color205.BackColor = TableNumberToRGB(205)
   Color206.BackColor = TableNumberToRGB(206)
   Color207.BackColor = TableNumberToRGB(207)
   Color208.BackColor = TableNumberToRGB(208)
   Color209.BackColor = TableNumberToRGB(209)
   Color210.BackColor = TableNumberToRGB(210)
   Color211.BackColor = TableNumberToRGB(211)
   Color212.BackColor = TableNumberToRGB(212)
   Color213.BackColor = TableNumberToRGB(213)
   Color214.BackColor = TableNumberToRGB(214)
   Color215.BackColor = TableNumberToRGB(215)
   Color216.BackColor = TableNumberToRGB(216)
   Color217.BackColor = TableNumberToRGB(217)
   Color218.BackColor = TableNumberToRGB(218)
   Color219.BackColor = TableNumberToRGB(219)
   Color220.BackColor = TableNumberToRGB(220)
   Color221.BackColor = TableNumberToRGB(221)
   Color222.BackColor = TableNumberToRGB(222)
   Color223.BackColor = TableNumberToRGB(223)
   Color224.BackColor = TableNumberToRGB(224)
   Color225.BackColor = TableNumberToRGB(225)
   Color226.BackColor = TableNumberToRGB(226)
   Color227.BackColor = TableNumberToRGB(227)
   Color228.BackColor = TableNumberToRGB(228)
   Color229.BackColor = TableNumberToRGB(229)
   Color230.BackColor = TableNumberToRGB(230)
   Color231.BackColor = TableNumberToRGB(231)
   Color232.BackColor = TableNumberToRGB(232)
   Color233.BackColor = TableNumberToRGB(233)
   Color234.BackColor = TableNumberToRGB(234)
   Color235.BackColor = TableNumberToRGB(235)
   Color236.BackColor = TableNumberToRGB(236)
   Color237.BackColor = TableNumberToRGB(237)
   Color238.BackColor = TableNumberToRGB(238)
   Color239.BackColor = TableNumberToRGB(239)
   Color240.BackColor = TableNumberToRGB(240)
   Color241.BackColor = TableNumberToRGB(241)
   Color242.BackColor = TableNumberToRGB(242)
   Color243.BackColor = TableNumberToRGB(243)
   Color244.BackColor = TableNumberToRGB(244)
   Color245.BackColor = TableNumberToRGB(245)
   Color246.BackColor = TableNumberToRGB(246)
   Color247.BackColor = TableNumberToRGB(247)
   Color248.BackColor = TableNumberToRGB(248)
   Color249.BackColor = TableNumberToRGB(249)
   Color250.BackColor = TableNumberToRGB(250)
   Color251.BackColor = TableNumberToRGB(251)
   Color252.BackColor = TableNumberToRGB(252)
   Color253.BackColor = TableNumberToRGB(253)
   Color254.BackColor = TableNumberToRGB(254)
   Color255.BackColor = RGB(0, 0, 0)
End Sub

Private Sub Color0_Click()
   ChoseColor "0"
End Sub

Private Sub Color1_Click()
   ChoseColor "1"
End Sub

Private Sub Color2_Click()
   ChoseColor "2"
End Sub

Private Sub Color3_Click()
   ChoseColor "3"
End Sub

Private Sub Color4_Click()
   ChoseColor "4"
End Sub

Private Sub Color5_Click()
   ChoseColor "5"
End Sub

Private Sub Color6_Click()
   ChoseColor "6"
End Sub

Private Sub Color7_Click()
   ChoseColor "7"
End Sub

Private Sub Color8_Click()
   ChoseColor "8"
End Sub

Private Sub Color9_Click()
   ChoseColor "9"
End Sub

Private Sub Color10_Click()
   ChoseColor "10"
End Sub

Private Sub Color11_Click()
   ChoseColor "11"
End Sub

Private Sub Color12_Click()
   ChoseColor "12"
End Sub

Private Sub Color13_Click()
   ChoseColor "13"
End Sub

Private Sub Color14_Click()
   ChoseColor "14"
End Sub

Private Sub Color15_Click()
   ChoseColor "15"
End Sub

Private Sub Color16_Click()
   ChoseColor "16"
End Sub

Private Sub Color17_Click()
   ChoseColor "17"
End Sub

Private Sub Color18_Click()
   ChoseColor "18"
End Sub

Private Sub Color19_Click()
   ChoseColor "19"
End Sub

Private Sub Color20_Click()
   ChoseColor "20"
End Sub

Private Sub Color21_Click()
   ChoseColor "21"
End Sub

Private Sub Color22_Click()
   ChoseColor "22"
End Sub

Private Sub Color23_Click()
   ChoseColor "23"
End Sub

Private Sub Color24_Click()
   ChoseColor "24"
End Sub

Private Sub Color25_Click()
   ChoseColor "25"
End Sub

Private Sub Color26_Click()
   ChoseColor "26"
End Sub

Private Sub Color27_Click()
   ChoseColor "27"
End Sub

Private Sub Color28_Click()
   ChoseColor "28"
End Sub

Private Sub Color29_Click()
   ChoseColor "29"
End Sub

Private Sub Color30_Click()
   ChoseColor "30"
End Sub

Private Sub Color31_Click()
   ChoseColor "31"
End Sub

Private Sub Color32_Click()
   ChoseColor "32"
End Sub

Private Sub Color33_Click()
   ChoseColor "33"
End Sub

Private Sub Color34_Click()
   ChoseColor "34"
End Sub

Private Sub Color35_Click()
   ChoseColor "35"
End Sub

Private Sub Color36_Click()
   ChoseColor "36"
End Sub

Private Sub Color37_Click()
   ChoseColor "37"
End Sub

Private Sub Color38_Click()
   ChoseColor "38"
End Sub

Private Sub Color39_Click()
   ChoseColor "39"
End Sub

Private Sub Color40_Click()
   ChoseColor "40"
End Sub

Private Sub Color41_Click()
   ChoseColor "41"
End Sub

Private Sub Color42_Click()
   ChoseColor "42"
End Sub

Private Sub Color43_Click()
   ChoseColor "43"
End Sub

Private Sub Color44_Click()
   ChoseColor "44"
End Sub

Private Sub Color45_Click()
   ChoseColor "45"
End Sub

Private Sub Color46_Click()
   ChoseColor "46"
End Sub

Private Sub Color47_Click()
   ChoseColor "47"
End Sub

Private Sub Color48_Click()
   ChoseColor "48"
End Sub

Private Sub Color49_Click()
   ChoseColor "49"
End Sub

Private Sub Color50_Click()
   ChoseColor "50"
End Sub

Private Sub Color51_Click()
   ChoseColor "51"
End Sub

Private Sub Color52_Click()
   ChoseColor "52"
End Sub

Private Sub Color53_Click()
   ChoseColor "53"
End Sub

Private Sub Color54_Click()
   ChoseColor "54"
End Sub

Private Sub Color55_Click()
   ChoseColor "55"
End Sub

Private Sub Color56_Click()
   ChoseColor "56"
End Sub

Private Sub Color57_Click()
   ChoseColor "57"
End Sub

Private Sub Color58_Click()
   ChoseColor "58"
End Sub

Private Sub Color59_Click()
   ChoseColor "59"
End Sub

Private Sub Color60_Click()
   ChoseColor "60"
End Sub

Private Sub Color61_Click()
   ChoseColor "61"
End Sub

Private Sub Color62_Click()
   ChoseColor "62"
End Sub

Private Sub Color63_Click()
   ChoseColor "63"
End Sub

Private Sub Color64_Click()
   ChoseColor "64"
End Sub

Private Sub Color65_Click()
   ChoseColor "65"
End Sub

Private Sub Color66_Click()
   ChoseColor "66"
End Sub

Private Sub Color67_Click()
   ChoseColor "67"
End Sub

Private Sub Color68_Click()
   ChoseColor "68"
End Sub

Private Sub Color70_Click()
   ChoseColor "70"
End Sub

Private Sub Color71_Click()
   ChoseColor "71"
End Sub

Private Sub Color72_Click()
   ChoseColor "72"
End Sub

Private Sub Color73_Click()
   ChoseColor "73"
End Sub

Private Sub Color74_Click()
   ChoseColor "74"
End Sub

Private Sub Color75_Click()
   ChoseColor "75"
End Sub

Private Sub Color76_Click()
   ChoseColor "76"
End Sub

Private Sub Color77_Click()
   ChoseColor "77"
End Sub

Private Sub Color78_Click()
   ChoseColor "78"
End Sub

Private Sub Color79_Click()
   ChoseColor "79"
End Sub

Private Sub Color80_Click()
   ChoseColor "80"
End Sub

Private Sub Color81_Click()
   ChoseColor "81"
End Sub

Private Sub Color82_Click()
   ChoseColor "82"
End Sub

Private Sub Color83_Click()
   ChoseColor "83"
End Sub

Private Sub Color84_Click()
   ChoseColor "84"
End Sub

Private Sub Color85_Click()
   ChoseColor "85"
End Sub

Private Sub Color86_Click()
   ChoseColor "86"
End Sub

Private Sub Color87_Click()
   ChoseColor "87"
End Sub

Private Sub Color88_Click()
   ChoseColor "88"
End Sub

Private Sub Color89_Click()
   ChoseColor "89"
End Sub

Private Sub Color90_Click()
   ChoseColor "90"
End Sub

Private Sub Color91_Click()
   ChoseColor "91"
End Sub

Private Sub Color92_Click()
   ChoseColor "92"
End Sub

Private Sub Color93_Click()
   ChoseColor "93"
End Sub

Private Sub Color94_Click()
   ChoseColor "94"
End Sub

Private Sub Color95_Click()
   ChoseColor "95"
End Sub

Private Sub Color96_Click()
   ChoseColor "96"
End Sub

Private Sub Color97_Click()
   ChoseColor "97"
End Sub

Private Sub Color98_Click()
   ChoseColor "98"
End Sub

Private Sub Color99_Click()
   ChoseColor "99"
End Sub

Private Sub Color100_Click()
   ChoseColor "100"
End Sub

Private Sub Color101_Click()
   ChoseColor "101"
End Sub

Private Sub Color102_Click()
   ChoseColor "102"
End Sub

Private Sub Color103_Click()
   ChoseColor "103"
End Sub

Private Sub Color104_Click()
   ChoseColor "104"
End Sub

Private Sub Color105_Click()
   ChoseColor "105"
End Sub

Private Sub Color106_Click()
   ChoseColor "106"
End Sub

Private Sub Color107_Click()
   ChoseColor "107"
End Sub

Private Sub Color108_Click()
   ChoseColor "108"
End Sub

Private Sub Color109_Click()
   ChoseColor "109"
End Sub

Private Sub Color110_Click()
   ChoseColor "110"
End Sub

Private Sub Color111_Click()
   ChoseColor "111"
End Sub

Private Sub Color112_Click()
   ChoseColor "112"
End Sub

Private Sub Color113_Click()
   ChoseColor "113"
End Sub

Private Sub Color114_Click()
   ChoseColor "114"
End Sub

Private Sub Color115_Click()
   ChoseColor "115"
End Sub

Private Sub Color116_Click()
   ChoseColor "116"
End Sub

Private Sub Color117_Click()
   ChoseColor "117"
End Sub

Private Sub Color118_Click()
   ChoseColor "118"
End Sub

Private Sub Color119_Click()
   ChoseColor "119"
End Sub

Private Sub Color120_Click()
   ChoseColor "120"
End Sub

Private Sub Color121_Click()
   ChoseColor "121"
End Sub

Private Sub Color122_Click()
   ChoseColor "122"
End Sub

Private Sub Color123_Click()
   ChoseColor "123"
End Sub

Private Sub Color124_Click()
   ChoseColor "124"
End Sub

Private Sub Color125_Click()
   ChoseColor "125"
End Sub

Private Sub Color126_Click()
   ChoseColor "126"
End Sub

Private Sub Color127_Click()
   ChoseColor "127"
End Sub

Private Sub Color128_Click()
   ChoseColor "128"
End Sub

Private Sub Color129_Click()
   ChoseColor "129"
End Sub

Private Sub Color130_Click()
   ChoseColor "130"
End Sub

Private Sub Color131_Click()
   ChoseColor "131"
End Sub

Private Sub Color132_Click()
   ChoseColor "132"
End Sub

Private Sub Color133_Click()
   ChoseColor "133"
End Sub

Private Sub Color134_Click()
   ChoseColor "134"
End Sub

Private Sub Color135_Click()
   ChoseColor "135"
End Sub

Private Sub Color136_Click()
   ChoseColor "136"
End Sub

Private Sub Color137_Click()
   ChoseColor "137"
End Sub

Private Sub Color138_Click()
   ChoseColor "138"
End Sub

Private Sub Color139_Click()
   ChoseColor "139"
End Sub

Private Sub Color140_Click()
   ChoseColor "140"
End Sub

Private Sub Color141_Click()
   ChoseColor "141"
End Sub

Private Sub Color142_Click()
   ChoseColor "142"
End Sub

Private Sub Color143_Click()
   ChoseColor "143"
End Sub

Private Sub Color144_Click()
   ChoseColor "144"
End Sub

Private Sub Color145_Click()
   ChoseColor "145"
End Sub

Private Sub Color146_Click()
   ChoseColor "146"
End Sub

Private Sub Color147_Click()
   ChoseColor "147"
End Sub

Private Sub Color148_Click()
   ChoseColor "148"
End Sub

Private Sub Color149_Click()
   ChoseColor "149"
End Sub

Private Sub Color150_Click()
   ChoseColor "150"
End Sub

Private Sub Color151_Click()
   ChoseColor "151"
End Sub

Private Sub Color152_Click()
   ChoseColor "152"
End Sub

Private Sub Color153_Click()
   ChoseColor "153"
End Sub

Private Sub Color154_Click()
   ChoseColor "154"
End Sub

Private Sub Color155_Click()
   ChoseColor "155"
End Sub

Private Sub Color156_Click()
   ChoseColor "156"
End Sub

Private Sub Color157_Click()
   ChoseColor "157"
End Sub

Private Sub Color158_Click()
   ChoseColor "158"
End Sub

Private Sub Color159_Click()
   ChoseColor "159"
End Sub

Private Sub Color160_Click()
   ChoseColor "160"
End Sub

Private Sub Color161_Click()
   ChoseColor "161"
End Sub

Private Sub Color162_Click()
   ChoseColor "162"
End Sub

Private Sub Color163_Click()
   ChoseColor "163"
End Sub

Private Sub Color164_Click()
   ChoseColor "164"
End Sub

Private Sub Color165_Click()
   ChoseColor "165"
End Sub

Private Sub Color166_Click()
   ChoseColor "166"
End Sub

Private Sub Color167_Click()
   ChoseColor "167"
End Sub

Private Sub Color168_Click()
   ChoseColor "168"
End Sub

Private Sub Color170_Click()
   ChoseColor "170"
End Sub

Private Sub Color171_Click()
   ChoseColor "171"
End Sub

Private Sub Color172_Click()
   ChoseColor "172"
End Sub

Private Sub Color173_Click()
   ChoseColor "173"
End Sub

Private Sub Color174_Click()
   ChoseColor "174"
End Sub

Private Sub Color175_Click()
   ChoseColor "175"
End Sub

Private Sub Color176_Click()
   ChoseColor "176"
End Sub

Private Sub Color177_Click()
   ChoseColor "177"
End Sub

Private Sub Color178_Click()
   ChoseColor "178"
End Sub

Private Sub Color179_Click()
   ChoseColor "179"
End Sub

Private Sub Color180_Click()
   ChoseColor "180"
End Sub

Private Sub Color181_Click()
   ChoseColor "181"
End Sub

Private Sub Color182_Click()
   ChoseColor "182"
End Sub

Private Sub Color183_Click()
   ChoseColor "183"
End Sub

Private Sub Color184_Click()
   ChoseColor "184"
End Sub

Private Sub Color185_Click()
   ChoseColor "185"
End Sub

Private Sub Color186_Click()
   ChoseColor "186"
End Sub

Private Sub Color187_Click()
   ChoseColor "187"
End Sub

Private Sub Color188_Click()
   ChoseColor "188"
End Sub

Private Sub Color189_Click()
   ChoseColor "189"
End Sub

Private Sub Color190_Click()
   ChoseColor "190"
End Sub

Private Sub Color191_Click()
   ChoseColor "191"
End Sub

Private Sub Color192_Click()
   ChoseColor "192"
End Sub

Private Sub Color193_Click()
   ChoseColor "193"
End Sub

Private Sub Color194_Click()
   ChoseColor "194"
End Sub

Private Sub Color195_Click()
   ChoseColor "195"
End Sub

Private Sub Color196_Click()
   ChoseColor "196"
End Sub

Private Sub Color197_Click()
   ChoseColor "197"
End Sub

Private Sub Color198_Click()
   ChoseColor "198"
End Sub

Private Sub Color199_Click()
   ChoseColor "199"
End Sub

Private Sub Color200_Click()
   ChoseColor "200"
End Sub

Private Sub Color201_Click()
   ChoseColor "201"
End Sub

Private Sub Color202_Click()
   ChoseColor "202"
End Sub

Private Sub Color203_Click()
   ChoseColor "203"
End Sub

Private Sub Color204_Click()
   ChoseColor "204"
End Sub

Private Sub Color205_Click()
   ChoseColor "205"
End Sub

Private Sub Color206_Click()
   ChoseColor "206"
End Sub

Private Sub Color207_Click()
   ChoseColor "207"
End Sub

Private Sub Color208_Click()
   ChoseColor "208"
End Sub

Private Sub Color209_Click()
   ChoseColor "209"
End Sub

Private Sub Color210_Click()
   ChoseColor "210"
End Sub

Private Sub Color211_Click()
   ChoseColor "211"
End Sub

Private Sub Color212_Click()
   ChoseColor "212"
End Sub

Private Sub Color213_Click()
   ChoseColor "213"
End Sub

Private Sub Color214_Click()
   ChoseColor "214"
End Sub

Private Sub Color215_Click()
   ChoseColor "215"
End Sub

Private Sub Color216_Click()
   ChoseColor "216"
End Sub

Private Sub Color217_Click()
   ChoseColor "217"
End Sub

Private Sub Color218_Click()
   ChoseColor "218"
End Sub

Private Sub Color219_Click()
   ChoseColor "219"
End Sub

Private Sub Color220_Click()
   ChoseColor "220"
End Sub

Private Sub Color221_Click()
   ChoseColor "221"
End Sub

Private Sub Color222_Click()
   ChoseColor "222"
End Sub

Private Sub Color223_Click()
   ChoseColor "223"
End Sub

Private Sub Color224_Click()
   ChoseColor "224"
End Sub

Private Sub Color225_Click()
   ChoseColor "225"
End Sub

Private Sub Color226_Click()
   ChoseColor "226"
End Sub

Private Sub Color227_Click()
   ChoseColor "227"
End Sub

Private Sub Color228_Click()
   ChoseColor "228"
End Sub

Private Sub Color229_Click()
   ChoseColor "229"
End Sub

Private Sub Color230_Click()
   ChoseColor "230"
End Sub

Private Sub Color231_Click()
   ChoseColor "231"
End Sub

Private Sub Color232_Click()
   ChoseColor "232"
End Sub

Private Sub Color233_Click()
   ChoseColor "233"
End Sub

Private Sub Color234_Click()
   ChoseColor "234"
End Sub

Private Sub Color235_Click()
   ChoseColor "235"
End Sub

Private Sub Color236_Click()
   ChoseColor "236"
End Sub

Private Sub Color237_Click()
   ChoseColor "237"
End Sub

Private Sub Color238_Click()
   ChoseColor "238"
End Sub

Private Sub Color239_Click()
   ChoseColor "239"
End Sub

Private Sub Color240_Click()
   ChoseColor "240"
End Sub

Private Sub Color241_Click()
   ChoseColor "241"
End Sub

Private Sub Color242_Click()
   ChoseColor "242"
End Sub

Private Sub Color243_Click()
   ChoseColor "243"
End Sub

Private Sub Color244_Click()
   ChoseColor "244"
End Sub

Private Sub Color245_Click()
   ChoseColor "245"
End Sub

Private Sub Color246_Click()
   ChoseColor "246"
End Sub

Private Sub Color247_Click()
   ChoseColor "247"
End Sub

Private Sub Color248_Click()
   ChoseColor "248"
End Sub

Private Sub Color249_Click()
   ChoseColor "249"
End Sub

Private Sub Color250_Click()
   ChoseColor "250"
End Sub

Private Sub Color251_Click()
   ChoseColor "251"
End Sub

Private Sub Color252_Click()
   ChoseColor "252"
End Sub

Private Sub Color253_Click()
   ChoseColor "253"
End Sub

Private Sub Color254_Click()
   ChoseColor "254"
End Sub

Private Sub Color255_Click()
   ChoseColor "255"
End Sub


Private Sub UserForm_Terminate()
   ClearCommandPromptArea
End Sub

Attribute VB_Name = "FrmCompassRule"
Attribute VB_Base = "0{00971C62-F556-4165-B701-5BF3C9D09F48}{253D30A8-AB13-472E-B815-0AF6F77EA18A}"
Attribute VB_GlobalNameSpace = False
Attribute VB_Creatable = False
Attribute VB_PredeclaredId = True
Attribute VB_Exposed = False
Attribute VB_TemplateDerived = False
Attribute VB_Customizable = False




'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit

Private PreliminaryAdj           As AdjTabData
Private FinalAdj                 As AdjTabData
Private WasPreliminary           As Boolean

Private InsertMode               As Boolean 'FLAGS WHEN INSERTING VERSUS EDITING TRAVERSE OR SIDE SHOT
Private fileIsLoaded             As Boolean 'SET TO TRUE WHEN FILE IS LOADED

Private FileIDString             As String 'STRING TO IDENTIFY GRAPHIC ELEMENTS CREATED WITH THIS FILE
Private CurrentFileName          As String 'SAVE NAME OF CURRENT FILE

Private OldStartAzimuth          As String 'BACK UP STRING FOR STARTING BACK SIGHT AZIMUTH

Private OldStartingNorthing      As String 'BACK UP STRING FOR STARTING POINT NORTHING ENTRY FIELD
Private OldStartingEasting       As String 'BACK UP STRING FOR STARTING POINT EASTING ENTRY FIELD

Private OldClosingNorthing       As String 'BACK UP STRING FOR CLOSING POINT NORTHING ENTRY FIELD
Private OldClosingEasting        As String 'BACK UP STRING FOR CLOSING POINT EASTING ENTRY FIELD

Private OldTwoPointNorthing      As String 'BACK UP STRING FOR MOVE TO POINT NORTHING ENTRY FIELD
Private OldTwoPointEasting       As String 'BACK UP STRING FOR MOVE TO POINT EASTING ENTRY FIELD
 
Private OldMoveToNorthing        As String 'BACK UP STRING FOR MOVE TO POINT NORTHING ENTRY FIELD
Private OldMoveToEasting         As String 'BACK UP STRING FOR MOVE TO POINT EASTING ENTRY FIELD

Private OldAngularError          As String 'BACK UP STRING FOR ANGULAR ERROR
Private OldRotation              As String 'BACK UP STRING FOR ROTATION
Private OldDiagramAzimuth        As String 'BACK UP STRING FOR DROP DIAGRAM AZIMUTH

Private Const IS_CHOSEN_STRING           As String = "Is Chosen"
Private Const NOT_CHOSEN_STRING          As String = "Not Chosen"
Private Const NOT_APPLICABLE_STRING      As String = "N/A"
Private Const COMPASS_RULE_APPLIED       As String = "Compass Rule Applied"
Private Const POOR_STRING                As String = "Poor"
Private Const PERFECT_STRING             As String = "Perfect"
Private Const SHOW_DROP_INDICATOR        As String = "X"

Private Const TEXT_COLOR_RED = &HFF&
Private Const TEXT_COLOR_BLACK = &H80000012


Private Const RAW_COLUMN_ENTRY_TYPE      As Long = 0
Private Const RAW_COLUMN_POINT_NAME      As Long = 1
Private Const RAW_COLUMN_BACK_SIGHT      As Long = 2
Private Const RAW_COLUMN_FORE_SIGHT      As Long = 3
Private Const RAW_COLUMN_HD              As Long = 4
Private Const RAW_COLUMN_DESCRIPTION     As Long = 5
Private Const RAW_COLUMN_SHOW_DROP       As Long = 6
Private Const RAW_COLUMN_ELEVATION       As Long = 6


Private Const TRAV_COLUMN_REF_NUM        As Long = 0
Private Const TRAV_COLUMN_POINT_NAME     As Long = 1
Private Const TRAV_COLUMN_BACK_SIGHT     As Long = 3
Private Const TRAV_COLUMN_FORE_SIGHT     As Long = 4
Private Const TRAV_COLUMN_HD             As Long = 5
Private Const TRAV_COLUMN_DESCRIPTION    As Long = 2


Private Const SIDE_COLUMN_REF_NUM        As Long = 0
Private Const SIDE_COLUMN_POINT_NAME     As Long = 4
Private Const SIDE_COLUMN_BACK_SIGHT     As Long = 1
Private Const SIDE_COLUMN_FORE_SIGHT     As Long = 2
Private Const SIDE_COLUMN_HD             As Long = 3
Private Const SIDE_COLUMN_DESCRIPTION    As Long = 5
Private Const SIDE_COLUMN_SHOW_DROP      As Long = 6

Private Const DROPS_COLUMN_RECORD_NORTH  As Long = 0
Private Const DROPS_COLUMN_RECORD_EAST   As Long = 1
Private Const DROPS_COLUMN_DIAGRAM_NORTH As Long = 2
Private Const DROPS_COLUMN_DIAGRAM_EAST  As Long = 3

Private Const REPORT_COORD_PRECISION     As Long = 4
Private Const OFFSET_PRECISION           As Long = 2

Private Const PAD_NAME = 19
Private Const PAD_AZ = 30
Private Const PAD_DIST = 20
Private Const PAD_DESC = 24
Private Const Side_Report_Prec_Angle = 4
Private Const Side_Report_Prec_Distance = 2

Private Const INITIAL_COORD_VAL          As String = "0.0000"

Private Const DEFAULT_ELEVATION_STRING As String = "0.00"


Public Sub ParseTravElString(travElString As String, ByRef plotElev As Boolean, ByRef elevationString As String)
   elevationString = Mid(travElString, 2)
   If PLOT_EL_TRUE = Left(travElString, 1) Then
      plotElev = True
   Else
      plotElev = False
   End If
End Sub



Private Function DefaultAzString() As String
   DefaultAzString = DegreesToAngleString(0#, 4, GetAngleStyle())
End Function



Private Function AngleStringPrecision(AngleString As String) As Long
   Dim sAzimuth As Double
   Dim dirType As Integer
   Dim quad As Integer
   If Not DirStringToSAz(AngleString, sAzimuth, AngleStringPrecision, dirType, quad) Then
'SHOULD NEVER GET HERE, CREATE ERROR IF IT DOES
      Err.Raise ERROR_NUM_527
   End If
End Function



Private Sub SetComboIndex(ByVal index As Long, ByRef TheBox As ComboBox)
   Dim topIndex As Long
   topIndex = TheBox.ListCount - 1
   If index > topIndex Or index < -1 Then
      index = -1
   End If
   TheBox.listIndex = index
End Sub


Public Function calcCharSize(ByVal TheView As view, ByVal PixelsPerChar As Integer) As Double
'FOR USING FIXED SCREEN SIZED CHARACTERS
   PixelsPerChar = Abs(PixelsPerChar)
   calcCharSize = CalcMasterUnitPerPixel(TheView) * PixelsPerChar
End Function




Private Function CalcMasterUnitPerPixel(ByVal TheView As view) As Double
   Dim Extents As Point3d
   Dim ViewOrigin As Point3d
   Dim ViewRotation As Matrix3d

'MAKE WORKING COPY
   Extents = TheView.Extents
   ViewOrigin = TheView.origin
   ViewRotation = TheView.rotation

'CALCULATE MEASUREMENT POINT
   Dim MeasurePoint As Point3d
   Dim MetricX As Double
   Dim Vector As Point3d
   
   MetricX = Extents.X * 0.99  'so the pixel does not fall off the edge
      
   'CALCULATE FOR VIEW ROTATION
   Vector = Point3dFromMatrix3dInverseTimesPoint3d(ViewRotation, Point3dFromXYZ(MetricX, 0, 0))
   MeasurePoint.X = ViewOrigin.X + Vector.X
   MeasurePoint.Y = ViewOrigin.Y + Vector.Y
   MeasurePoint.z = ViewOrigin.z + Vector.z
   
'CONVERT TO PIXELS
   Dim PixelPosition As Point2d

   PixelPosition = TheView.GetPixelPosition(MeasurePoint, True)

'CALCULATE THE RATIO
   CalcMasterUnitPerPixel = MetricX / Max(PixelPosition.X, 1) 'make sure you don't divide by zero
End Function



'**************************************************************************************
'///////////////////////////////////OLD VALUES\\\\\\\\\\\\\\\\\\\\\\\\\\\\\\\\\\\\\\\\\
'**************************************************************************************
Public Sub UpdateOldVals()
   RotationTextBoxSub
   OldAngularError = AngularAdjustmentTextBox.text
End Sub


'**************************************************************************************
'///////////////////////////////////PROPERTIES\\\\\\\\\\\\\\\\\\\\\\\\\\\\\\\\\\\\\\\\\
'**************************************************************************************
Property Get GetAngleStyle() As Integer
   GetAngleStyle = STYLE_ANGLE_LEAD Or STYLE_ANGLE_SPACE
End Property


Property Get OldClosingNorth() As String
   OldClosingNorth = OldClosingNorthing
End Property

Property Let OldClosingNorth(NorthText As String)
   OldClosingNorthing = NorthText
End Property

Property Get OldClosingEast() As String
   OldClosingEast = OldClosingEasting
End Property

Property Let OldClosingEast(EastText As String)
   OldClosingEasting = EastText
End Property


Property Get OldTwoPointNorth() As String
   OldTwoPointNorth = OldTwoPointNorthing
End Property

Property Let OldTwoPointNorth(NorthText As String)
   OldTwoPointNorthing = NorthText
End Property

Property Get OldTwoPointEast() As String
   OldTwoPointEast = OldTwoPointEasting
End Property

Property Let OldTwoPointEast(EastText As String)
   OldMoveToEasting = EastText
End Property


Property Get OldMoveToNorth() As String
   OldMoveToNorth = OldMoveToNorthing
End Property

Property Let OldMoveToNorth(NorthText As String)
   OldMoveToNorthing = NorthText
End Property

Property Get OldMoveToEast() As String
   OldMoveToEast = OldMoveToEasting
End Property

Property Let OldMoveToEast(EastText As String)
   OldMoveToEasting = EastText
End Property


Property Get OldAngleError() As String
   OldAngleError = OldAngularError
End Property

Property Let OldAngleError(angleText As String)
   OldAngularError = angleText
End Property

Property Get IsInsertMode() As Boolean
   IsInsertMode = InsertMode
End Property

Property Let FileLoaded(IsLoaded As Boolean)
'SET/CLEAR FLAG FOR FILE BEING LOADED OR NOT
   fileIsLoaded = IsLoaded
End Property

Property Get FileLoaded() As Boolean
'GET STATE OF FILE FLAG
   FileLoaded = fileIsLoaded
End Property

Property Let CurrentFile(TheCurrentFilename As String)
'SAVE CURRENT FILE NAME
   CurrentFileName = TheCurrentFilename
End Property

Property Get CurrentFile() As String
'RETRIEVE CURRENT FILE NAME
    CurrentFile = CurrentFileName
End Property

Property Let IDstring(TagString As String)
'STORE THE FILE ID STRING FOR GRAPHIC ELEMENT TAGGING
   FileIDString = TagString
End Property

Property Get IDstring() As String
'RECALL THE FILE ID STRING FOR GRAPHIC ELEMENT TAGGING
   IDstring = FileIDString
End Property

Property Get StartPointZString() As String
'RECALL THE STARTING POINT Z STRING
   StartPointZString = TextElevation.text
End Property


Property Get FirstBSAzimuthString() As String
'RECALL THE BACK SIGHT STRING
   FirstBSAzimuthString = FirstBSAzTextBox.text
End Property

Property Get DefaultFSName() As String
'GET DEFAULT FS NAME
   Dim index As Long
   index = TraversesListBox.listIndex
   If index = (TraversesListBox.ListCount - 1) Then
      DefaultFSName = CloseNameTextBox.text
   Else
      DefaultFSName = TraversesListBox.List(index + 1, TRAV_COLUMN_POINT_NAME)
   End If
End Property

Property Get ForesightExists() As Boolean
   If TraversesListBox.listIndex = TraversesListBox.ListCount - 1 Then
      ForesightExists = False
   Else
      ForesightExists = True
   End If
End Property

Property Let LastFSName(name As String)
'SET THE NAME OF THE FORESIGHT FROM THE LAST TRAVERSE
   CloseNameTextBox.text = name
End Property


'**************************************************************************************
'//////////////////////////////STORE-RECALL ADJUSMENT TAB\\\\\\\\\\\\\\\\\\\\\\\\\\\\\\
'**************************************************************************************
Private Sub StoAdjTab(Data As AdjTabData)
   Dim TabData As AdjTabData
   TabData.ApplyChkBox = ApplyAdjustmentCheckBox.value
   TabData.AngErrChkBox = AngularAdjustmentCheckBox.value
   TabData.AngErrTxtBox = AngularAdjustmentTextBox.value
   TabData.SinglePathOption = SingleCompassRuleOption.value
   TabData.TwoPathOption = TwoPointAdjustmentOption.value
   TabData.TwoPathObsIndex = ChooseTwoPtObsComboBox.listIndex
   TabData.TwoPathNorthing = TwoPtNorthTextBox.text
   TabData.TwoPathEasting = TwoPtEastTextBox.text
   TabData.RerunOption = HoldingCoursesOption.value
   TabData.OneSecondOption = SecondOption.value
   TabData.TenthSecondOption = TenthSecondOption.value
   TabData.hundredthFootOption = HundredthOption.value
   TabData.ThousandthFootOption = ThousandthOption.value
   TabData.HoldCoordinateOption = InverseCourseOption.value
   TabData.TransformationChkBox = TranslationCheckBox.value
   TabData.TranslationIndex = ChooseMoveObsComboBox.listIndex
   TabData.TranslationNorthing = MoveToNorthTextBox.text
   TabData.TranslationEasting = MoveToEastTextBox.text
   TabData.RotationChkBox = RotationCheckBox.value
   TabData.RotationTxtBox = RotationTextBox.text
   Data = TabData
End Sub

Private Sub RclAdjTab(Data As AdjTabData)
   Dim LoadedState As Boolean
   LoadedState = fileIsLoaded
   fileIsLoaded = False
   Dim TabData As AdjTabData
   TabData = Data
   ApplyAdjustmentCheckBox.value = TabData.ApplyChkBox
   AngularAdjustmentCheckBox.value = TabData.AngErrChkBox
   AngularAdjustmentTextBox.value = TabData.AngErrTxtBox
   SingleCompassRuleOption.value = TabData.SinglePathOption
   TwoPointAdjustmentOption.value = TabData.TwoPathOption
   SetComboIndex TabData.TwoPathObsIndex, ChooseTwoPtObsComboBox
   TwoPtNorthTextBox.text = TabData.TwoPathNorthing
   OldTwoPointNorthing = TabData.TwoPathNorthing
   TwoPtEastTextBox.text = TabData.TwoPathEasting
   OldTwoPointEasting = TabData.TwoPathEasting
   HoldingCoursesOption.value = TabData.RerunOption
   SecondOption.value = TabData.OneSecondOption
   TenthSecondOption.value = TabData.TenthSecondOption
   HundredthOption.value = TabData.hundredthFootOption
   ThousandthOption.value = TabData.ThousandthFootOption
   InverseCourseOption.value = TabData.HoldCoordinateOption
   TranslationCheckBox.value = TabData.TransformationChkBox
   SetComboIndex TabData.TranslationIndex, ChooseMoveObsComboBox
   MoveToNorthTextBox.text = TabData.TranslationNorthing
   OldMoveToNorthing = TabData.TranslationNorthing
   MoveToEastTextBox.text = TabData.TranslationEasting
   OldMoveToEasting = TabData.TranslationEasting
   RotationCheckBox.value = TabData.RotationChkBox
   RotationTextBox.text = TabData.RotationTxtBox
   fileIsLoaded = LoadedState
End Sub

Public Sub StoPrelimTab()
   StoAdjTab PreliminaryAdj
End Sub

Public Sub StoFinalTab()
   StoAdjTab FinalAdj
End Sub

Private Sub RclPrelimTab()
   RclAdjTab PreliminaryAdj
End Sub

Private Sub RclFinalTab()
   RclAdjTab FinalAdj
End Sub


Public Function GetPrelimData() As AdjTabData
   GetPrelimData = PreliminaryAdj
End Function

Public Function GetFinalData() As AdjTabData
   GetFinalData = FinalAdj
End Function

Public Sub SetPrelimData(TabData As AdjTabData)
   PreliminaryAdj = TabData
End Sub

Public Sub SetFinalData(TabData As AdjTabData)
   FinalAdj = TabData
End Sub


Private Function GetHiddenTabData() As AdjTabData
   If PreliminaryOption.value Then
      GetHiddenTabData = FinalAdj
   Else
      GetHiddenTabData = PreliminaryAdj
   End If
End Function

Private Sub SetHiddenTabData(HiddenTabData As AdjTabData)
   If PreliminaryOption.value Then
      FinalAdj = HiddenTabData
   Else
      PreliminaryAdj = HiddenTabData
   End If
End Sub


Public Sub InitialAdjTabLoad()
   fillMoveAllObsCombo
   InitTravListboxSub
   fillTwoPtObsCombo

   WasPreliminary = PreliminaryOption.value
   If PreliminaryOption.value Then
      RclAdjTab PreliminaryAdj
   Else
      RclAdjTab FinalAdj
   End If
   PhaseColor
   ApplyStates
End Sub



'**************************************************************************************
'////////////////////////////////////REPORTS\\\\\\\\\\\\\\\\\\\\\\\\\\\\\\\\\\\\\\\\\\\
'**************************************************************************************
'++++++++++++++REPORT GENERATION++++++++++++++
Private Sub GenerateReport(ByRef TheFullFilename As String)
'CALC THE RAW
   Dim ThePointsArray As Variant
   Dim TheAzStringsArray As Variant
   ReDim TheAzStringsArray(0 To 0)
   ThePointsArray = CalcRaw(True, TheAzStringsArray)

   Dim RawArray As Variant
   RawArray = ThePointsArray

'APPLY APPROPRIATE ADJUSTMENTS
'COMPASS RULE
   CompassRulePointsArray ThePointsArray

   Dim CompassRuledArray As Variant
   CompassRuledArray = ThePointsArray
   
'COORDINATE TRANSFORMATION IF ANY
   TransformPointsArray ThePointsArray

'OPEN FILE FOR WRITE
   Dim FFILE As Long
   FFILE = FreeFile
   Open TheFullFilename For Output As #FFILE

'WRITE HEADINGS AND SETTINGS
   ReportTopPart FFILE

'WRITE FILENAME
   ReportFilename FFILE
   Print #FFILE, " "

'WRITE RAW TRAVERSE COURSES
   ReportRawTrav FFILE, RawArray, TheAzStringsArray
   Print #FFILE, " "

'WRITE CLOSING POINT DATA
   ReportClosingPoint FFILE
   Print #FFILE, " "

'WRITE RAW TRAVERSE STATSTICS
   ReportRawStats FFILE
   Print #FFILE, " "

'WRITE RAW SIDESHOTS
   ReportRawSideShots FFILE, RawArray
   Print #FFILE, " "

'WRITE COMPASS RULE ADJUSTED COURSES IF APPLICABLE
   If ApplyAdjustmentCheckBox.value = True Then
      Print #FFILE, ApplyAdjustmentCheckBox.Caption & ": " & IS_CHOSEN_STRING
   Else
      Print #FFILE, ApplyAdjustmentCheckBox.Caption & ": " & NOT_CHOSEN_STRING
   End If
   If CompassRuleStatusLabel.Caption = COMPASS_RULE_APPLIED Then
'WRITE ADJUSTMENT SETTINGS
      Print #FFILE, "Compass rule adjustment applied."
      Print #FFILE, " "
      ReportAdjustmentSettings FFILE, RawArray
      Print #FFILE, " "
'WRITE COMPASS RULE ADJUSTED COURSES
      ReportCompassRuledTrav FFILE, CompassRuledArray
      Print #FFILE, " "
'WRITE COMPASS RULE ADJUSTED RERUN CLOSURE(S)
      ReportRerunMisclosure FFILE
'WRITE COMPASS ADJUSTED SIDESHOTS
      ReportAdjustedSideShots FFILE, CompassRuledArray
   Else
      Print #FFILE, "Compass rule adjustment NOT applied."
   End If
   Print #FFILE, " "

'WRITE TRANSLATION
   ReportTransformed FFILE, RawArray, ThePointsArray
   Print #FFILE, " "

'WRITE VERSION
   ReportGeneratedWith FFILE
   
'CLOSE OUTPUT FILE
   Close #FFILE
End Sub



Private Sub ReportTransformed(ByVal FFILE As Long, TheRawArray As Variant, TheTransformedArray As Variant)
   If TranslationCheckBox.value = True Then
      Print #FFILE, TranslationCheckBox.Caption & ": " & IS_CHOSEN_STRING
   Else
      Print #FFILE, TranslationCheckBox.Caption & ": " & NOT_CHOSEN_STRING
      Exit Sub
   End If
   
   If TranslationCheckBox.enabled = False Then
      Print #FFILE, TranslationCheckBox.Caption & ": " & NOT_APPLICABLE_STRING
      Exit Sub
   End If
   
   If RotationCheckBox.value Then
      Print #FFILE, RotationCheckBox.Caption & ": " & IS_CHOSEN_STRING & ": " & RotationTextBox.text
   Else
      Print #FFILE, RotationCheckBox.Caption & ": " & NOT_CHOSEN_STRING
   End If
   
   If RotationCheckBox.value = False And TranslationCheckBox.value = False Then
      Exit Sub
   End If
   
'REPORT ROTATED TRAVERSE COURSES
   If RotationCheckBox.value Then
      Print #FFILE, "*****************"
      Print #FFILE, "*ROTATED COURSES*"
      Print #FFILE, "*****************"
      ReportAdjustedRuledTrav FFILE, TheTransformedArray, False
      Print #FFILE, " "
   End If
   
   Print #FFILE, MoveAllHoldingObsLabel.Caption & ": " & ChooseMoveObsComboBox.text
   If ChooseMoveObsComboBox.listIndex < 0 Then
      Print #FFILE, "Cannot Translate"
      If RotationCheckBox.value = False Then
         Exit Sub
      End If
   Else
      Dim RawObsPoint As Point3d
      RawObsPoint = TheRawArray(ChooseMoveObsComboBox.listIndex)
      Print #FFILE, "    " & PaddedNorthingString(RawObsPoint.Y, REPORT_COORD_PRECISION) & _
                    STRING_SPACE & PaddedEastingString(RawObsPoint.X, REPORT_COORD_PRECISION)
      Print #FFILE, "  " & TranslationCoordLabel.Caption & ":"
      Print #FFILE, "    " & PaddedNorthingString(GetNorthing(MoveToNorthTextBox), REPORT_COORD_PRECISION) & _
                    STRING_SPACE & PaddedEastingString(GetEasting(MoveToEastTextBox), REPORT_COORD_PRECISION)
      Print #FFILE, " "
   End If
   
   Print #FFILE, "********************************"
   Print #FFILE, "*ROTATED/TRANSLATED COORDINATES*"
   Print #FFILE, "********************************"
   Dim rawIndex As Long
   For rawIndex = 0 To (RawEntriesListBox.ListCount - 1)
      Dim thePoint As Point3d
      thePoint = TheTransformedArray(rawIndex)
      Dim shotType As String
      Dim pointName As String
      Dim bSString As String
      Dim fSString As String
      Dim hDString As String
      Dim descriptionString As String
      Dim showDrop As Boolean
      Dim elevationString As String
      GetRawListLine rawIndex, shotType, pointName, bSString, fSString, hDString, descriptionString, showDrop, elevationString
'SIDE SHOT
      If shotType = KEY_COMPASS_RULE_SIDE_SHOT Then
         Print #FFILE, "SIDE: " & PadTheEnd(pointName, PAD_NAME) & PadTheEnd(descriptionString, PAD_DESC) & _
                       PaddedNorthingString(thePoint.Y, REPORT_COORD_PRECISION) & STRING_SPACE & PaddedEastingString(thePoint.X, REPORT_COORD_PRECISION)
      End If

'TRAVERSE
      If shotType = KEY_COMPASS_RULE_TRAV Then
         Print #FFILE, "TRAV: " & PadTheEnd(pointName, PAD_NAME) & PadTheEnd(descriptionString, PAD_DESC) & _
                       PaddedNorthingString(thePoint.Y, REPORT_COORD_PRECISION) & STRING_SPACE & PaddedEastingString(thePoint.X, REPORT_COORD_PRECISION)
      End If
   Next rawIndex
   If LastForesightOption.value = True Then
      thePoint = TheTransformedArray(UBound(TheTransformedArray))
      If ToBeginningOption.value = True Then
         GetRawListLine 0, shotType, pointName, bSString, fSString, hDString, descriptionString, showDrop, elevationString
      Else
         pointName = CloseNameTextBox.text
         descriptionString = CloseDescTextBox.text
      End If
      Print #FFILE, "TRAV: " & PadTheEnd(pointName, PAD_NAME) & PadTheEnd(descriptionString, PAD_DESC) & _
                    PaddedNorthingString(thePoint.Y, REPORT_COORD_PRECISION) & STRING_SPACE & PaddedEastingString(thePoint.X, REPORT_COORD_PRECISION)
   End If
End Sub



Private Sub DefaultPrec(ByRef anglePrec As Long, ByRef distPrec As Long)
   If HoldingCoursesOption.value = True Then
      If SecondOption.value = True Then
         anglePrec = 4
      Else
         anglePrec = 5
      End If
      If HundredthOption.value = True Then
         distPrec = 2
      Else
         distPrec = 3
      End If
   Else
      If Inv1secOption.value = True Then
         anglePrec = 4
      Else
         anglePrec = 5
      End If
      If hundredthFootOption.value = True Then
         distPrec = 2
      Else
         distPrec = 3
      End If
   End If
End Sub



Private Sub ReportRawSideShots(ByVal FFILE As Long, TheRawArray As Variant)
   If IncludeSideShotsCheckBox.value = True Then
      Print #FFILE, "SIDE SHOTS FROM RAW TRAVERSES"
      ReportSideShotsSub FFILE, TheRawArray
   End If
End Sub



Private Sub ReportAdjustedSideShots(ByVal FFILE As Long, TheCompassRuledArray As Variant)
   If IncludeSideShotsCheckBox.value = True Then
      Print #FFILE, "SIDE SHOTS AFTER COMPASS RULE ADJUSTED TRAVERSES"
      ReportSideShotsSub FFILE, TheCompassRuledArray
   End If
End Sub



Private Sub ReportSideShotsSub(ByVal FFILE As Long, ThePointsArray As Variant)
   Dim EndIndex As Long
   EndIndex = RawEntriesListBox.ListCount - 1
   Dim rawIndex As Long
   For rawIndex = 0 To EndIndex
      Dim thePoint As Point3d
      thePoint = ThePointsArray(rawIndex)
      Dim shotType As String
      Dim pointName As String
      Dim bSString As String
      Dim fSString As String
      Dim hDString As String
      Dim descriptionString As String
      Dim showDrop As Boolean
      Dim elevationString As String
      GetRawListLine rawIndex, shotType, pointName, bSString, fSString, hDString, descriptionString, showDrop, elevationString
      
'SIDE SHOT
      If shotType = KEY_COMPASS_RULE_SIDE_SHOT Then
         Dim WasAtTrav As Boolean
         If WasAtTrav Then
            Dim TravName As String
            Dim TravDesc As String
            Print #FFILE, "TRAV: " & PadTheEnd(TravName, PAD_NAME)
         End If
         Dim TravPoint As Point3d
         Dim sAzDegrees As Double
         Dim distance As Double
         Inverse TravPoint, thePoint, sAzDegrees, distance
         Dim azString As String
         azString = SAzToAzimuthStr(sAzDegrees, Side_Report_Prec_Angle, STYLE_ANGLE_SPACE + STYLE_ANGLE_LEAD)
         Print #FFILE, "   SIDE: Az: " & _
                           azString & _
                           "  Dist: " & _
                           FormatNumber(distance, Side_Report_Prec_Distance, vbTrue, vbFalse, vbTrue)
         Print #FFILE, "        " & _
                       PadTheEnd(pointName, PAD_NAME) & _
                       PadTheEnd(descriptionString, PAD_DESC) & _
                       PaddedNorthingString(thePoint.Y, REPORT_COORD_PRECISION) & _
                       " " & _
                       PaddedEastingString(thePoint.X, REPORT_COORD_PRECISION)
         If rawIndex <> EndIndex Then
            Print #FFILE, " "
         End If
         WasAtTrav = False
      End If

'TRAVERSE
      If shotType = KEY_COMPASS_RULE_TRAV Then
         TravPoint = thePoint
         TravName = pointName
         TravDesc = descriptionString
         WasAtTrav = True
      End If
   Next rawIndex
End Sub



Private Sub ReportRerunMisclosure(ByVal FFILE As Long)
   If HoldingCoursesOption.value = True Then
      Print #FFILE, "PRECISION RERUN MISCLOSURE"
   End If
   If RerunMisNorthingLabel.enabled Then
      Print #FFILE, RerunMisNorthingLabel.Caption & " " & RerunMisNorthLabel.Caption
      Print #FFILE, RerunMisEastingLabel.Caption & " " & RerunMisEastLabel.Caption
      Print #FFILE, RerunMisDistanceLabel.Caption & " " & RerunMisDisLabel.Caption
      Print #FFILE, " "
   End If
   If IntermediatePointLabel.enabled Then
      Print #FFILE, IntermediatePointLabel.Caption
      Print #FFILE, RerunIntNorthingMisLabel.Caption & " " & RerunIntNorthMisLabel.Caption
      Print #FFILE, RerunIntEastingMisLabel.Caption & " " & RerunIntEastMisLabel.Caption
      Print #FFILE, RerunIntDistanceMisLabel.Caption & " " & RerunIntDistMisLabel.Caption
      Print #FFILE, " "
   End If
End Sub



Private Sub ReportCompassRuledTrav(ByVal FFILE As Long, TheCompassRuledArray As Variant)
   Print #FFILE, "********************************"
   Print #FFILE, "*COMPASS RULE ADJUSTED TRAVERSE*"
   Print #FFILE, "********************************"
   ReportAdjustedRuledTrav FFILE, TheCompassRuledArray, True
End Sub



Private Sub ReportAdjustedRuledTrav(ByVal FFILE As Long, TheAdjustedArray As Variant, ByVal ShowCoord As Boolean)
   Dim thisAngleStyle As Integer
   thisAngleStyle = STYLE_ANGLE_SPACE Or STYLE_ANGLE_LEAD
   Dim lastForesight As Boolean
   lastForesight = LastForesightOption.value
   Dim anglePrec As Long
   Dim distPrec As Long
   DefaultPrec anglePrec, distPrec
   
      
   Dim BackPoint As Point3d
   BackPoint = TheAdjustedArray(0)
   Dim EndIndex As Long
   EndIndex = TraversesListBox.ListCount - 1
   
   Dim TravIndex As Long
   For TravIndex = 0 To EndIndex
      Dim refNum As Long
      Dim PreviousRefNum As Long
      Dim pointName As String
      Dim bSString As String
      Dim fSString As String
      Dim hDString As String
      Dim descriptionString As String
      GetTravListLine TravIndex, refNum, pointName, bSString, fSString, hDString, descriptionString
      Dim thePoint As Point3d
      thePoint = TheAdjustedArray(refNum)
      
      If TravIndex <> 0 Then
         Dim InvSAzDegrees As Double
         Dim InvDist As Double
         Inverse BackPoint, thePoint, InvSAzDegrees, InvDist
         Dim azString As String
         azString = SAzToAzimuthStr(InvSAzDegrees, anglePrec, thisAngleStyle)

         Print #FFILE, STRING_SPACE
         Print #FFILE, PadLead("Az: " & azString, PAD_AZ) & _
                       PadLead("Dist: " & _
                       FormatNumber(InvDist, distPrec, vbTrue, vbFalse, vbTrue), PAD_DIST)
         Print #FFILE, STRING_SPACE
      
      End If
      
      Dim PointString As String
      PointString = PadTheEnd(pointName, PAD_NAME) & PadTheEnd(descriptionString, PAD_DESC)
      If ShowCoord Then
         PointString = PointString & PaddedNorthingString(thePoint.Y, REPORT_COORD_PRECISION) & " " & PaddedEastingString(thePoint.X, REPORT_COORD_PRECISION)
      End If
      Print #FFILE, PointString
      
      BackPoint = thePoint
      
      If (TravIndex = EndIndex) And lastForesight Then
         If ToBeginningOption.value = True Then
            GetTravListLine 0, refNum, pointName, bSString, fSString, hDString, descriptionString
         Else
            pointName = CloseNameTextBox.text
            descriptionString = CloseDescTextBox.text
         End If
         thePoint = TheAdjustedArray(UBound(TheAdjustedArray))
         Inverse BackPoint, thePoint, InvSAzDegrees, InvDist
         azString = SAzToAzimuthStr(InvSAzDegrees, anglePrec, thisAngleStyle)
         Print #FFILE, STRING_SPACE
         Print #FFILE, PadLead("Az: " & azString, PAD_AZ) & _
                       PadLead("Dist: " & _
                       FormatNumber(InvDist, distPrec, vbTrue, vbFalse, vbTrue), PAD_DIST)
         Print #FFILE, STRING_SPACE
         PointString = PadTheEnd(pointName, PAD_NAME) & PadTheEnd(descriptionString, PAD_DESC)
         If ShowCoord Then
            PointString = PointString & PaddedNorthingString(thePoint.Y, REPORT_COORD_PRECISION) & STRING_SPACE & PaddedEastingString(thePoint.X, REPORT_COORD_PRECISION)
         End If
         Print #FFILE, PointString
      End If
   Next TravIndex
End Sub



Private Sub ReportAdjustmentSettings(ByVal FFILE As Long, TheRawArray As Variant)
   Print #FFILE, "COMPASS RULE ADJUSTMENT SETTINGS"
   If AngularAdjustmentCheckBox.value = True Then
      Print #FFILE, AngularAdjustmentCheckBox.Caption & ": " & IS_CHOSEN_STRING & " : " & AngularAdjustmentTextBox.text
   Else
      Print #FFILE, AngularAdjustmentCheckBox.Caption & ": " & NOT_CHOSEN_STRING
   End If
   Dim CompassRuleTypeString As String
   CompassRuleTypeString = "Compass Rule Type: "
   If SingleCompassRuleOption.value = True Then
      CompassRuleTypeString = CompassRuleTypeString & SingleCompassRuleOption.Caption
      Print #FFILE, CompassRuleTypeString
   ElseIf TwoPointAdjustmentOption.value = True Then
      CompassRuleTypeString = CompassRuleTypeString & TwoPointAdjustmentOption.Caption
      Print #FFILE, CompassRuleTypeString
      Print #FFILE, TwoPtHoldingObsLabel.Caption & ": " & ChooseTwoPtObsComboBox.text
      Dim IntObsPoint As Point3d
      IntObsPoint = TheRawArray(TwoPtObsComboRefNum())
      Print #FFILE, "    " & PaddedNorthingString(IntObsPoint.Y, REPORT_COORD_PRECISION) & PaddedEastingString(IntObsPoint.X, REPORT_COORD_PRECISION)
      Print #FFILE, "  " & TwoPtMoveToLabel.Caption & ":"
      Print #FFILE, "    " & PaddedNorthingString(GetNorthing(TwoPtNorthTextBox), REPORT_COORD_PRECISION) & _
                             PaddedEastingString(GetEasting(TwoPtEastTextBox), REPORT_COORD_PRECISION)
   End If
   Dim SolutionRulesString As String
   SolutionRulesString = SolutionFrame.Caption
   If HoldingCoursesOption.value = True Then
      SolutionRulesString = SolutionRulesString & ": " & HoldingCoursesOption.Caption
      Print #FFILE, SolutionRulesString
            Dim precString As String
      precString = "         Angle: "
      If TenthSecondOption.value Then
         precString = precString & TenthSecondOption.Caption
      ElseIf SecondOption.value Then
         precString = precString & SecondOption.Caption
      End If
      precString = precString & "  Dist.: "
      If HundredthOption.value Then
         precString = precString & HundredthOption.Caption
      ElseIf ThousandthOption.value Then
         precString = precString & ThousandthOption.Caption
      End If
      Print #FFILE, precString
   ElseIf InverseCourseOption.value = True Then
      SolutionRulesString = SolutionRulesString & ": " & InverseCourseOption.Caption
      Print #FFILE, SolutionRulesString
      Print #FFILE, InversePrecisionFrame.Caption & ":"
      precString = "         Angle: "
      If InvTenthSecOption.value Then
         precString = precString & InvTenthSecOption.Caption
      ElseIf Inv1secOption.value Then
         precString = precString & Inv1secOption.Caption
      End If
      precString = precString & "  Dist.: "
      If hundredthFootOption.value Then
         precString = precString & hundredthFootOption.Caption
      ElseIf ThousandthFootOption.value Then
         precString = precString & ThousandthFootOption.Caption
      End If
      Print #FFILE, precString
   End If
End Sub



Private Sub ReportRawTrav(ByVal FFILE As Long, TheRawArray As Variant, RawAzimStringsArray As Variant)
   Dim lastForesight As Boolean
   lastForesight = LastForesightOption.value
   Print #FFILE, "**************"
   Print #FFILE, "*RAW TRAVERSE*"
   Print #FFILE, "**************"
   Dim EndIndex As Long
   EndIndex = TraversesListBox.ListCount - 1
   Dim TravIndex As Long
   For TravIndex = 0 To EndIndex
      Dim refNum As Long
      Dim PreviousRefNum As Long
      Dim pointName As String
      Dim bSString As String
      Dim fSString As String
      Dim hDString As String
      Dim descriptionString As String
      GetTravListLine TravIndex, refNum, pointName, bSString, fSString, hDString, descriptionString
      Dim thePoint As Point3d
      thePoint = TheRawArray(refNum)
      If TravIndex <> 0 Then
         Print #FFILE, " "
      End If
      Print #FFILE, PadTheEnd(pointName, 19) & PadTheEnd(descriptionString, 24) & _
                    PaddedNorthingString(thePoint.Y, REPORT_COORD_PRECISION) & STRING_SPACE & PaddedEastingString(thePoint.X, REPORT_COORD_PRECISION)
      Dim azString As String
      azString = RawAzimStringsArray(TravIndex)
      
      If (TravIndex <> EndIndex) Or lastForesight Then
         Print #FFILE, " "
         Print #FFILE, PadLead("Az: " & azString, 30) & PadLead("Dist: " & hDString, 20)
      End If
      If (TravIndex = EndIndex) And lastForesight Then
         If ToBeginningOption.value = True Then
            GetTravListLine 0, refNum, pointName, bSString, fSString, hDString, descriptionString
         Else
            pointName = CloseNameTextBox.text
            descriptionString = CloseDescTextBox.text
         End If
         thePoint = TheRawArray(UBound(TheRawArray))
         Print #FFILE, " "
         Print #FFILE, PadTheEnd(pointName, 19) & PadTheEnd(descriptionString, 24) & _
                       PaddedNorthingString(thePoint.Y, REPORT_COORD_PRECISION) & STRING_SPACE & PaddedEastingString(thePoint.X, REPORT_COORD_PRECISION)
      End If
   Next TravIndex
End Sub



Private Sub ReportFilename(ByVal FFILE As Long)
   If ReportFilenameCheckBox.value = True Then
      Dim filename As String
      filename = Me.CurrentFile
      If IncludePathCheckBox.value = False Then
         Dim xSplit2 As Variant
         xSplit2 = Split(filename, "\")
         filename = xSplit2(UBound(xSplit2))
      End If
      Print #FFILE, " Filename: " & filename
   End If
End Sub



Private Sub ReportGeneratedWith(ByVal FFILE As Long)
   Print #FFILE, "Generated with: " & APP_VERSION & APP_UPDATE
End Sub



Private Sub ReportTopPart(ByVal FFILE As Long)
   Print #FFILE, "* * * * * * * * * * SURVEYOR TOOLS NEO COMPASS RULE 2D REPORT * * * * * * * * * *"
   Print #FFILE, " "
   Print #FFILE, "     Date: " & DateTextBox.text
   Print #FFILE, "  Project: " & ProjectTextBox.text
   Print #FFILE, "   Origin: " & OriginTextBox.text
   Print #FFILE, "  Azimuth: " & AzimuthTextBox.text
   Print #FFILE, "Fieldbook: " & FieldBookTextBox.text
   Print #FFILE, "    Notes: " & NotesTextBox.text
   Dim mode As String
   If NORTH_AZIMUTH_MODE Then
      mode = "North"
   Else
      mode = "South"
   End If
   Print #FFILE, "Azi. mode: " & mode
End Sub



Private Sub ReportClosingPoint(ByVal FFILE As Long)
   Print #FFILE, "CLOSING POINT"
   If NoneYetOption.value = True Then
      Dim CloseType As String
      CloseType = NoneYetOption.Caption
   ElseIf ToBeginningOption.value = True Then
      CloseType = ToBeginningOption.Caption
   ElseIf ToPointOption.value = True Then
      CloseType = ToPointOption.Caption & _
                  STRING_SPACE & _
                  PaddedNorthingString(GetNorthing(CloseNorthTextBox), REPORT_COORD_PRECISION) & _
                  STRING_SPACE & _
                  PaddedEastingString(GetEasting(CloseEastTextBox), REPORT_COORD_PRECISION)
   Else
      CloseType = "error"
   End If
   If LastForesightOption.value = True Then
      Dim CloseObs As String
      CloseObs = LastForesightOption.Caption
   Else
      CloseObs = LastTraverseOption.Caption
   End If
   Print #FFILE, "             Closure type: " & CloseType
   Print #FFILE, "Closing point observation: " & CloseObs
End Sub



Private Sub ReportRawStats(ByVal FFILE As Long)
   Print #FFILE, "RAW TRAVERSE STATISTICS"
   Print #FFILE, "    Number of setups: " & SetupsNumLabel.Caption
   Print #FFILE, "Number of side shots: " & SideshotsNumberLabel.Caption
   Print #FFILE, "      Number of legs: " & NumberOfLegsLabel.Caption
   Print #FFILE, "  Length of traverse: " & TravLengthLabel.Caption
   Print #FFILE, " Northing misclosure: " & NorthMisclosureLabel.Caption
   Print #FFILE, "  Easting misclosure: " & EastingMiscloseLabel.Caption
   Print #FFILE, " Misclosure distance: " & MiscloseDistanceLabel.Caption
   Print #FFILE, "Misclosure direction: " & MiscloseDirectionLabel.Caption
   Print #FFILE, "           Precision: " & TraversePrecLabel.Caption
End Sub



Private Function GetReportFilename(ByRef ReportName As String) As Boolean
'MAKE THIS ROUTINE GENERIC LATER
'RETURNS TRUE IF SUCCESSFUL
   GetReportFilename = False

'CREATE DEFAULT FILENAME
   Dim DefaultFilename As String
   DefaultFilename = "C:\report" & FILE_EXTENSION_REPORT

'GET CURRENT LOT FILE NAME
   Dim fullFilename As String
   fullFilename = Me.CurrentFile

'GET SUGGESTED FILENAME FOR REPORT FILE
   Dim xSplit2 As Variant
   xSplit2 = Split(fullFilename, "\")
   Dim TheCompassRuleFilename As String
   TheCompassRuleFilename = xSplit2(UBound(xSplit2))
   Dim PeriodPosition As Long
   PeriodPosition = InStrRev(TheCompassRuleFilename, ".")
   Dim SuggestedFilename As String
   If PeriodPosition > 0 Then
      TheCompassRuleFilename = Left(TheCompassRuleFilename, PeriodPosition - 1)
   End If
   SuggestedFilename = TheCompassRuleFilename & FILE_EXTENSION_REPORT

'GET SUGGESTED PATH FOR REPORT FILE
   xSplit2(UBound(xSplit2)) = ""
   Dim NewTextFilePath As String
   NewTextFilePath = Join(xSplit2, "\")

'CREATE FILTER STRING
   Dim FilterString As String
   FilterString = "*" & FILE_EXTENSION_REPORT

'CALL COMMON DIALOG FOR CREATING FILE
   Dim retVal As Long
   Dim lngfhandle As Long
   Dim lngrid As Long
   Dim strFName As String
   strFName = space(255)
   retVal = mdlDialog_fileCreate(strFName, lngfhandle, lngrid, SuggestedFilename, FilterString, NewTextFilePath, "Create Report File")
   Select Case retVal
      Case 0 'Open
'RETURN NEW REPORT FILENAME
         strFName = Left(strFName, InStr(1, strFName, Chr(0)) - 1)
         ReportName = strFName
         GetReportFilename = True
      Case 1 'Cancel
           'MsgBox "No File Selected."
           'User hit the Cancel Button
   End Select
End Function



'++++++++++++++EXPORT COORDINATES++++++++++++++
Private Sub ExportCoords(TheFullFilename As String)
   Dim IncludeSides As Boolean
   IncludeSides = ExportSidesCheckBox.value

'CALC THE RAW
   Dim ThePointsArray As Variant
   ThePointsArray = CalcRaw(False, Nothing)

'APPLY APPROPRIATE ADJUSTMENTS
'COMPASS RULE
   CompassRulePointsArray ThePointsArray

'COORDINATE TRANSFORMATION IF ANY
   TransformPointsArray ThePointsArray

'OPEN FILE FOR WRITE
   Dim FFILE As Long
   FFILE = FreeFile
   Open TheFullFilename For Output As #FFILE

'LOOP THROUGH LISTBOX
   Dim lastIndex As Long
   lastIndex = RawEntriesListBox.ListCount - 1
   Dim rawIndex As Long
   For rawIndex = 0 To lastIndex
'READ ONE LINE OF RAW ENTRIES
      Dim shotType As String
      Dim pointName As String
      Dim bSString As String
      Dim fSString As String
      Dim hDString As String
      Dim descriptionString As String
      Dim showDrop As Boolean
      Dim elevationString As String
      GetRawListLine rawIndex, shotType, pointName, bSString, fSString, hDString, descriptionString, showDrop, elevationString
      If (shotType = KEY_COMPASS_RULE_SIDE_SHOT) And IncludeSides Then
         Dim thePoint As Point3d
         thePoint = ThePointsArray(rawIndex)
         Print #FFILE, CreatePointString(pointName, descriptionString, thePoint)
      End If
      If shotType = KEY_COMPASS_RULE_TRAV Then
         thePoint = ThePointsArray(rawIndex)
         thePoint.z = CDbl(Mid(elevationString, 2))
         Print #FFILE, CreatePointString(pointName, descriptionString, thePoint)
      End If
   Next rawIndex

'TAKE CARE OF LAST FORESIGHT CONDITION
   If LastForesightOption.value And LastForesightOption.enabled Then
         thePoint = ThePointsArray(UBound(ThePointsArray))
         If ToBeginningOption.value Then
            GetRawListLine 0, shotType, pointName, bSString, fSString, hDString, descriptionString, showDrop, elevationString
            thePoint.z = CDbl(Mid(elevationString, 2))
            Print #FFILE, CreatePointString(pointName, descriptionString, thePoint)
         Else
            thePoint.z = CDbl(ElevationTextBox.text)
            Print #FFILE, CreatePointString(CloseNameTextBox.text, CloseDescTextBox.text, thePoint)
         End If
   End If
   
'CLOSE OUTPUT FILE
   Close #FFILE
End Sub



Private Function CreatePointString(pointName As String, descriptionString As String, thePoint As Point3d) As String
   Dim NEprecision As Long
   NEprecision = START_COORD_PREC
   Dim ElevationPrecision As Long
   ElevationPrecision = MAX_PRECISION_ELEV
   Dim NewPointName As String
   NewPointName = Replace(pointName, ",", ";")
   CreatePointString = NewPointName & _
                       "," & _
                       FormatNumber(Round(thePoint.Y, NEprecision), NEprecision, vbTrue, vbFalse, vbFalse) & _
                       "," & _
                       FormatNumber(Round(thePoint.X, NEprecision), NEprecision, vbTrue, vbFalse, vbFalse) & _
                       "," & _
                       FormatNumber(Round(thePoint.z, ElevationPrecision), ElevationPrecision, vbTrue, vbFalse, vbFalse) & _
                       "," & _
                       descriptionString
End Function



'**************************************************************************************
'///////////////////////////////////PROCESSING\\\\\\\\\\\\\\\\\\\\\\\\\\\\\\\\\\\\\\\\\
'**************************************************************************************
'++++++++++++++PROCESS THE CIRCUIT++++++++++++++
Private Function CalcRaw(ByVal SaveAzStrings As Boolean, AzStringArray As Variant) As Variant
'RETURN ARRAY OF POINT VALUES CORRESPONDING TO ENTRY ARRAY.  LAST ELEMENT CORRESPONDS TO LAST
'FORESIGHT OF THE LAST TRAVERSE SETUP POINT IF SETUP EXISTS.
   Dim rawCalcPointArray() As Point3d
   ReDim rawCalcPointArray(0 To RawEntriesListBox.ListCount)

'CHECK IF NEED TO FILL STRING ARRAY
   If SaveAzStrings Then
      ReDim AzStringArray(0 To (TraversesListBox.ListCount - 1))
      Dim TravIndex As Long
      TravIndex = 0
   End If

'GET STARTING POINT OF TRAVERSE
   Dim SetupPoint As Point3d
   SetupPoint = GetStartingPoint()
   Dim nextSetup As Point3d
   nextSetup = SetupPoint

'GET BACK SIGHT AZIMUTH STRING
   Dim newBSAzString As String
   newBSAzString = FirstBSAzTextBox.text

'CALC INITIAL ANGLE PRECISION
   Dim anglePrecison As Long
   anglePrecison = AngleStringPrecision(newBSAzString)

'START RAW INDEX
   Dim rawIndex As Long
   rawIndex = 0
   
'CALCULATE ENDING INDEX
   Dim EndIndex As Long
   EndIndex = RawEntriesListBox.ListCount - 1

'INITIALIZE COUNTERS
   Dim NumberOfSetups As Long
   NumberOfSetups = 0
   Dim NumberOfSideshots As Long
   NumberOfSideshots = 0
   Dim LengthOfTraverse As Double
   LengthOfTraverse = 0

'LOOP THROUGH RAW ENTRIES
   Do While rawIndex <= EndIndex
'READ ONE LINE OF RAW ENTRIES
      Dim shotType As String
      Dim pointName As String
      Dim bSString As String
      Dim fSString As String
      Dim hDString As String
      Dim descriptionString As String
      Dim showDrop As Boolean
      Dim elevationString As String
      GetRawListLine rawIndex, shotType, pointName, bSString, fSString, hDString, descriptionString, showDrop, elevationString
      If shotType = KEY_COMPASS_RULE_SIDE_SHOT Then
'CALCULATE SIDE SHOT POINT
         Dim BSAzimuthString As String
         Dim ForwardSAz As Double
         rawCalcPointArray(rawIndex) = forwardPoint(SetupPoint, BSAzimuthString, bSString, fSString, hDString, ForwardSAz)
         NumberOfSideshots = NumberOfSideshots + 1
      End If

'TRAVERSE
      If shotType = KEY_COMPASS_RULE_TRAV Then
         If rawIndex > 0 Then
            SetupPoint = nextSetup
         End If
         BSAzimuthString = newBSAzString
         rawCalcPointArray(rawIndex) = SetupPoint
         nextSetup = forwardPoint(SetupPoint, BSAzimuthString, bSString, fSString, hDString, ForwardSAz)
         Dim PreviousSetup As Point3d
         PreviousSetup = SetupPoint
         NumberOfSetups = NumberOfSetups + 1
         Dim FSHDdouble As Double
         FSHDdouble = CDbl(hDString)
         LengthOfTraverse = LengthOfTraverse + FSHDdouble
         anglePrecison = Max(AngleStringPrecision(bSString), anglePrecison)
         anglePrecison = Max(AngleStringPrecision(fSString), anglePrecison)
         Dim ForwardAzimString As String
         ForwardAzimString = SAzToAzimuthStr(ForwardSAz, anglePrecison, GetAngleStyle())
         If SaveAzStrings Then
            AzStringArray(TravIndex) = ForwardAzimString
            TravIndex = TravIndex + 1
         End If
         newBSAzString = ForwardAzimString
         If Not ReverseDirText(newBSAzString) Then
'SHOULD NEVER GET HERE, CREATE ERROR IF IT DOES
            Err.Raise ERROR_NUM_530
         End If
      End If
'INCREMENT LOOP
      rawIndex = rawIndex + 1
   Loop

'DEDUCT LAST FORESIGHT IF CLOSING POINT IS THE LAST TRAVERSE
   If LastTraverseOption.value = True Then
      LengthOfTraverse = LengthOfTraverse - FSHDdouble
   End If

'ADD LAST FORESIGHT
   rawCalcPointArray(rawIndex) = nextSetup

'UPDATE STATISTICS
   Dim NumOfLegs As Long
   NumOfLegs = NumberOfSetups
   If LastTraverseOption.value = True Then
      NumOfLegs = Max(NumOfLegs - 1, 0)
   End If
   If LastTraverseOption.value = True Then
      Dim ClosingObsPoint As Point2d
      ClosingObsPoint.Y = SetupPoint.Y
      ClosingObsPoint.X = SetupPoint.X
   Else
      ClosingObsPoint.Y = nextSetup.Y
      ClosingObsPoint.X = nextSetup.X
   End If
   UpdateStatistics NumberOfSetups, NumberOfSideshots, NumOfLegs, LengthOfTraverse, ClosingObsPoint

'RETURN VALUES
   CalcRaw = rawCalcPointArray
End Function



Private Function PrecisionString(miscloseDistance As String, travLength As String) As String
   Dim misDistDouble As Double
   misDistDouble = CDbl(miscloseDistance)
   Dim travLenDouble As Double
   travLenDouble = CDbl(travLength)
   Dim divisor As Double
   divisor = (misDistDouble / travLenDouble)
   If travLenDouble = 0 Then
      PrecisionString = NOT_APPLICABLE_STRING
   ElseIf misDistDouble = 0 Then
      PrecisionString = PERFECT_STRING
   ElseIf divisor = 0 Then
         PrecisionString = PERFECT_STRING
   Else
      If divisor = 0 Then
      End If
      Dim denominator As Double
      denominator = 1 / divisor
      If denominator >= 1 Then
         PrecisionString = "1/" & FormatNumber(denominator, 0, vbTrue, vbFalse, vbTrue)
      Else
        PrecisionString = POOR_STRING
      End If
   End If
End Function



Private Sub CalcDropAverage(PointsArray As Variant)
'START RAW INDEX AT SECOND ELEMENT
   Dim rawIndex As Long
   rawIndex = 0

'CALCULATE ENDING INDEX
   Dim EndIndex As Long
   EndIndex = RawEntriesListBox.ListCount - 1

'GET DIAGRAM REFERENCE AZIMUTH
   Dim origPrec As Long
   Dim dirType As Integer
   Dim quad As Integer
   Dim DiagSAzDegrees As Double
   If Not DirStringToSAz(DropAzimuthTextBox.text, DiagSAzDegrees, origPrec, dirType, quad) Then
      DiagSAzDegrees = 270#  'DIAGRAM READ FROM LEFT TO RIGHT
   End If

'COUNT THE DROPS INCLUDED
   Dim DropCount As Long
   DropCount = 0
   
'ACUUMULATORS
   Dim TotalX As Double
   TotalX = 0
   Dim TotalY As Double
   TotalY = 0

'LOOP THROUGH RAW ENTRIES
   Do While rawIndex <= EndIndex
'READ ONE LINE OF RAW ENTRIES
      Dim shotType As String
      Dim pointName As String
      Dim bSString As String
      Dim fSString As String
      Dim hDString As String
      Dim descriptionString As String
      Dim showDrop As Boolean
      Dim elevationString As String
      GetRawListLine rawIndex, shotType, pointName, bSString, fSString, hDString, descriptionString, showDrop, elevationString

      If shotType = KEY_COMPASS_RULE_SIDE_SHOT And showDrop Then
         Dim RecordNorth As String
         Dim RecordEast As String
         Dim DiagramNorth As String
         Dim DiagramEast As String
         GetDropsListLine rawIndex, RecordNorth, RecordEast, DiagramNorth, DiagramEast
         If IsNumeric(RecordNorth) And IsNumeric(RecordEast) And IsNumeric(DiagramNorth) And IsNumeric(DiagramEast) Then
            Dim sideShotPoint As Point3d
            sideShotPoint = PointsArray(rawIndex)
            Dim recordPoint As Point3d
            recordPoint.Y = CDbl(RecordNorth)
            recordPoint.X = CDbl(RecordEast)
            recordPoint.z = sideShotPoint.z
                  
            Dim DropXString As String
            Dim DropYString As String
            DropQuadAndText quad, DropXString, DropYString, recordPoint, sideShotPoint, DiagSAzDegrees
            If IsNumeric(DropXString) And IsNumeric(DropYString) Then
               DropCount = DropCount + 1
               Dim XVal As Double
               XVal = CDbl(DropXString)
               Dim YVal As Double
               YVal = CDbl(DropYString)
               If quad = QUAD_SOUTH_EAST Then
                  YVal = -YVal
               ElseIf quad = QUAD_SOUTH_WEST Then
                  YVal = -YVal
                  XVal = -XVal
               ElseIf quad = QUAD_NORTH_WEST Then
                  XVal = -XVal
               End If
               TotalX = TotalX + XVal
               TotalY = TotalY + YVal
            End If
         End If
      End If
'INCREMENT LOOP
      rawIndex = rawIndex + 1
   Loop
   ClearAverageDrop
   If DropCount > 0 Then
      AverageXLabel.Caption = FormatNumber(TotalX / DropCount, 2, vbTrue, vbFalse, vbFalse)
      AverageYLabel.Caption = FormatNumber(TotalY / DropCount, 2, vbTrue, vbFalse, vbFalse)
   End If
   NumberOfDropsLabel.Caption = FormatNumber(DropCount, vbFalse, vbFalse, vbFalse)
End Sub



Private Sub DrawTheCircuit(TraversePointsArray As Variant, PreAdjArray As Variant, ByVal isFinal As Boolean)
'GET PLOT SCALE
   Dim charSize As Double
   charSize = GetCharSize()
   
'GET ACTIVE VIEW IF ANY
   Dim mySelectedView As view
   Set mySelectedView = GetSelectedView()

'MAKE TEMPLATES FOR DIFFERENT OBJECTS
   Dim travSymTemplate As Element
   Set travSymTemplate = CreateTraverseSymbolTemplate()
   Dim travLineTemplate As Element
   Set travLineTemplate = CreateTraverseLineTemplate()
   Dim sideLineTemplate As Element
   Set sideLineTemplate = CreateSideShotLineTemplate()
   Dim sideSymTemplate As Element
   Set sideSymTemplate = CreateSideShotSymbolTemplate()
   Dim traverseTextTemplate As TextElement
   Set traverseTextTemplate = CreateTraverseTextTextTemplate()
   Dim sideShotTextTemplate As TextElement
   Set sideShotTextTemplate = CreateSideShotTextTextTemplate()
   Dim miniCellTextTemplate As TextElement
   Set miniCellTextTemplate = CreateMiniCellTextTemplate()
   Dim preDropDiagramTemplate As TextElement
   Set preDropDiagramTemplate = CreatePreDropDiagramTextTemplate()
   Dim finDropDiagramTemplate As TextElement
   Set finDropDiagramTemplate = CreateFinDropDiagramTextTemplate()
   Dim dropLeaderTemplate As LineElement
   Set dropLeaderTemplate = CreateDropLeaderTemplate()
   
'DON'T ROTATE IF NO VIEW OPEN
   If mySelectedView Is Nothing Then
      Dim rotateViewAboutZAngle As Double
      rotateViewAboutZAngle = 0
   Else
'CALCULATE HOW MUCH TO ROTATE ELEMENTS TO MATCH VIEW
      Dim ViewAngle As Double
      If Matrix3dIsXYRotation(mySelectedView.rotation, ViewAngle) Then
         rotateViewAboutZAngle = -ViewAngle
      Else
         rotateViewAboutZAngle = 0
      End If
   End If

'START RAW INDEX AT SECOND ELEMENT
   Dim rawIndex As Long
   rawIndex = 0

'INITIALIZE SETUP POINT
   Dim SetupPoint As Point3d
   SetupPoint = TraversePointsArray(rawIndex)
'CALCULATE ENDING INDEX
   Dim EndIndex As Long
   EndIndex = RawEntriesListBox.ListCount - 1

'GET DIAGRAM REFERENCE AZIMUTH
   Dim origPrec As Long
   Dim dirType As Integer
   Dim quad As Integer
   Dim DiagSAzDegrees As Double
   If Not DirStringToSAz(DropAzimuthTextBox.text, DiagSAzDegrees, origPrec, dirType, quad) Then
'SHOULD NEVER GET HERE, CREATE ERROR IF IT DOES
      Err.Raise ERROR_NUM_531
   End If
   Dim AzimuthString As String
   AzimuthString = SAzToAzimuthStr(DiagSAzDegrees, 4, STYLE_ANGLE_LEAD + STYLE_ANGLE_NO_00_MIN + STYLE_ANGLE_CARET)

'LOOP THROUGH RAW ENTRIES
   Do While rawIndex <= EndIndex
'READ ONE LINE OF RAW ENTRIES
      Dim shotType As String
      Dim pointName As String
      Dim bSString As String
      Dim fSString As String
      Dim hDString As String
      Dim descriptionString As String
      Dim showDrop As Boolean
      Dim elevationString As String
      GetRawListLine rawIndex, shotType, pointName, bSString, fSString, hDString, descriptionString, showDrop, elevationString

'SIDE SHOT
      If shotType = KEY_COMPASS_RULE_SIDE_SHOT And SidesOffCheckBox.value = False Then
'DRAW THE LINE FROM SETUP POINT TO SIDE SHOT POINT
         Dim sideShotPoint As Point3d
         sideShotPoint = TraversePointsArray(rawIndex)
         DrawTravSideLine sideLineTemplate, SetupPoint, sideShotPoint
'DRAW SIDE SHOT SYMBOL AND TEXT HERE
         Dim SideSym As CellElement
         Set SideSym = CreateSymbol2Cell(sideSymTemplate, sideShotPoint, charSize, rotateViewAboutZAngle)
         AddCompassRuleElement SideSym
         DrawTheSideShotText sideShotPoint, rotateViewAboutZAngle, sideShotTextTemplate, pointName, descriptionString
'DRAW MINI CELL HERE
         DrawTheMiniCell sideShotPoint, rotateViewAboutZAngle, miniCellTextTemplate, pointName, descriptionString
'DRAW THE DROP DIAGRAM HERE
         If showDrop Then
            Dim preSideShotPoint As Point3d
            preSideShotPoint = PreAdjArray(rawIndex)
            DrawDropDiagram rawIndex, _
                            pointName, _
                            descriptionString, _
                            sideShotPoint, _
                            preSideShotPoint, _
                            AzimuthString, _
                            DiagSAzDegrees, _
                            preDropDiagramTemplate, _
                            finDropDiagramTemplate, _
                            dropLeaderTemplate, _
                            isFinal
         End If
      End If

'TRAVERSE
      If shotType = KEY_COMPASS_RULE_TRAV Then
         If rawIndex > 0 Then
'MOVE OLD SETUP POINT TO BACKSIGHT
            Dim BackSightPoint As Point3d
            BackSightPoint = SetupPoint
'MOVE UP TO NEW SETUP POINT
            SetupPoint = TraversePointsArray(rawIndex)
'DRAW THE LINE FROM BACKSIGHT TO NEW SETUP POINT
            DrawTravSideLine travLineTemplate, BackSightPoint, SetupPoint
         End If
'DRAW SETUP SYMBOL AND TEXT HERE
         If rawIndex <> 0 Or DrawStartCheckBox.value Then
         DrawTravSym travSymTemplate, SetupPoint, charSize, rotateViewAboutZAngle
         DrawTheTraverseText SetupPoint, rotateViewAboutZAngle, traverseTextTemplate, pointName, descriptionString, elevationString
         End If
      End If
'INCREMENT LOOP
      rawIndex = rawIndex + 1
   Loop
   
'DRAW LAST FORESIGHT IF APPROPRIATE
   Dim LastForesightPoint As Point3d
   LastForesightPoint = TraversePointsArray(rawIndex)
   If LastForesightOption.value And LastForesightOption.enabled And RawEntriesListBox.ListCount >= 0 Then
      DrawTravSideLine travLineTemplate, SetupPoint, LastForesightPoint
      If (NameAndDescCheckBox.value = True) And (NameAndDescCheckBox.enabled = True) Then
         DrawTravSym travSymTemplate, LastForesightPoint, charSize, rotateViewAboutZAngle
         Dim elevString As String
         If IncludeElCheckBox.value Then
            elevString = PLOT_EL_TRUE & ElevationTextBox.text
         Else
            elevString = PLOT_EL_FALSE & ElevationTextBox.text
         End If
         DrawTheTraverseText LastForesightPoint, _
                             rotateViewAboutZAngle, _
                             traverseTextTemplate, _
                             CloseNameTextBox.text, _
                             CloseDescTextBox.text, _
                             elevString
      End If
   End If
End Sub



Private Sub DrawDropDiagram(ByVal rawIndex As Long, _
                            ByVal nameString As String, _
                            ByVal DescString As String, _
                            sideShotPoint As Point3d, _
                            preSideShotPoint As Point3d, _
                            ByVal AzimuthString As String, _
                            ByVal diagAzDegrees As Double, _
                            preTemplate As Element, _
                            finTemplate As Element, _
                            leaderTemplate As Element, _
                            ByVal isFinal As Boolean)
   If DiagramOffCheckBox.value Then
      Exit Sub
   End If
'NOTE: WHEN PRELIMINARY ONLY (IsFinal IS FALSE), SIDESHOTPOINT AND PRESIDESHOTPOINT SHOULD BE SAME POINT
   Dim CorRecNorthString As String
   Dim CorRecEastString As String
   Dim DiaPlaceNorthString As String
   Dim DiaPlaceEastString As String
   GetDropsListLine rawIndex, CorRecNorthString, CorRecEastString, DiaPlaceNorthString, DiaPlaceEastString
   Dim PlaceDiagramPoint As Point3d
   Dim origPrec As Long
   PlaceDiagramPoint.z = sideShotPoint.z
   If Not IsNorthingString(DiaPlaceNorthString, PlaceDiagramPoint.Y, origPrec) Then
      Exit Sub
   End If
   If Not IsEastingString(DiaPlaceEastString, PlaceDiagramPoint.X, origPrec) Then
      Exit Sub
   End If

'ADD THE CROSS
   Dim rotAngleRad As Double  ' in radians
   Dim legLength As Double
   Dim extLineLength As Double
   Dim halfExtLineLength As Double
   Dim markerRadius As Double
   Dim fontSize As Double
   Dim LineSpacing As Double
   CalcDropMetrics diagAzDegrees, _
                   fontSize, _
                   legLength, _
                   extLineLength, _
                   halfExtLineLength, _
                   LineSpacing, _
                   rotAngleRad, _
                   markerRadius
   
   Dim CellElementArray() As Element
   ReDim CellElementArray(3)
   
'IF THERE IS A RECORD COORDINATE, DRAW THE DROPS AND AZIMUTH
   AddDropCrossToCell CellElementArray, preTemplate, PlaceDiagramPoint, legLength

'IF NO RECORD COORDINATE, DEFAULT TO DRAW THE AZIMUTH IN QUADRANT FOUR
   Dim AzQuad As Long
   AzQuad = QUAD_NORTH_WEST
   
'DRAW THE DROP LINES
   Dim RecordCoord As Point3d
   RecordCoord.z = sideShotPoint.z
   If Not IsNorthingString(CorRecNorthString, RecordCoord.Y, origPrec) Then
      Exit Sub
   End If
   If Not IsEastingString(CorRecEastString, RecordCoord.X, origPrec) Then
      Exit Sub
   End If

'DRAW THE PRELIMINARY PART
   Dim PreQuad As Integer
   Dim PreDropXString As String
   Dim PreDropYString As String
   DropQuadAndText PreQuad, PreDropXString, PreDropYString, RecordCoord, preSideShotPoint, diagAzDegrees
   Dim ExtLine1 As LineElement
   Dim ExtLine2 As LineElement
   Dim MarkerCircle As EllipseElement
   CreateExtLinesAndMarker ExtLine1, ExtLine2, MarkerCircle, PreQuad, PlaceDiagramPoint, extLineLength, markerRadius, preTemplate
   AddItToArray CellElementArray, ExtLine1
   AddItToArray CellElementArray, ExtLine2
   AddItToArray CellElementArray, MarkerCircle
      
   Dim PreXTextElement As TextElement
   Dim PreYTextElement As TextElement
   Dim PreNameElement As TextElement
   Dim PreDescElement As TextElement
   CreateTheDropText PreDropXString, _
                     PreDropYString, _
                     nameString, _
                     DescString, _
                     PreQuad, _
                     PlaceDiagramPoint, _
                     preTemplate, _
                     LineSpacing, _
                     extLineLength, _
                     fontSize, _
                     PreXTextElement, _
                     PreYTextElement, _
                     PreNameElement, _
                     PreDescElement
                        
   AddItToArray CellElementArray, PreXTextElement
   AddItToArray CellElementArray, PreYTextElement
   AddItToArray CellElementArray, PreNameElement
   AddItToArray CellElementArray, PreDescElement
   AzQuad = CalcAzQuad(PreQuad, PreQuad)

   If isFinal Then
'DRAW THE FINAL PART
      Dim FinQuad As Integer
      Dim FinDropXString As String
      Dim FinDropYString As String
      DropQuadAndText FinQuad, FinDropXString, FinDropYString, RecordCoord, sideShotPoint, diagAzDegrees
      Dim ZeroString As String
      ZeroString = DropValString(0)
      If FinDropXString = ZeroString And FinDropYString = ZeroString Then
         FinQuad = PreQuad
      End If
      If PreQuad = FinQuad Then
'SINGLE QUADRANT
'CROSS OUT OLD VALUES, PLACE NEW ONES
         If (PreDropXString = FinDropXString) And (PreDropYString = FinDropYString) Then
            Dim NoChangeElement As TextElement
            Set NoChangeElement = CreateTextElement1(finTemplate, "No Change", PlaceDiagramPoint, Matrix3dIdentity)
            Dim NoChangePosition As Point3d
            NoChangePosition = PlaceDiagramPoint
            NoChangePosition.Y = NoChangePosition.Y - (legLength + fontSize)
            Dim NoChangeSize As Point2d
            NoChangeElement.GetTotalTextSize NoChangeSize.X, NoChangeSize.Y
            NoChangePosition.X = NoChangePosition.X - (NoChangeSize.X / 2)
            NoChangeElement.origin = NoChangePosition
            AddItToArray CellElementArray, NoChangeElement
         End If
            
         If PreDropXString <> FinDropXString Then
            CrossOutXText PreXTextElement, CellElementArray, finTemplate
            Dim FinDropXElement As TextElement
            Set FinDropXElement = CreateTextElement1(finTemplate, FinDropXString, PlaceDiagramPoint, Matrix3dIdentity)
            Dim TextSize As Point2d
            FinDropXElement.GetTotalTextSize TextSize.X, TextSize.Y
            FinDropXElement.origin = NewXTextPosition(TextSize.X, FinQuad, PlaceDiagramPoint, LineSpacing, extLineLength, fontSize)
            AddItToArray CellElementArray, FinDropXElement
         End If

         If PreDropYString <> FinDropYString Then
            CrossOutYText PreYTextElement, CellElementArray, finTemplate
            Dim finDropYElement As TextElement
            Set finDropYElement = CreateTextElement1(finTemplate, FinDropYString, PreYTextElement.origin, Matrix3dIdentity)
            finDropYElement.GetTotalTextSize TextSize.X, TextSize.Y
            finDropYElement.origin = NewYTextPosition(TextSize.X, FinQuad, PlaceDiagramPoint, LineSpacing, extLineLength, fontSize)
            finDropYElement.RotateAboutZ finDropYElement.origin, Pi / 2
            AddItToArray CellElementArray, finDropYElement
         End If
      Else
'TWO QUADRANTS
         CreateExtLinesAndMarker ExtLine1, ExtLine2, MarkerCircle, FinQuad, PlaceDiagramPoint, extLineLength, markerRadius, finTemplate
         AddItToArray CellElementArray, ExtLine1
         AddItToArray CellElementArray, ExtLine2
         AddItToArray CellElementArray, MarkerCircle
         
         Dim FinXTextElement As TextElement
         Dim FinYTextElement As TextElement
         Dim FinNameElement As TextElement
         Dim FinDescElement As TextElement
         CreateTheDropText FinDropXString, _
                           FinDropYString, _
                           nameString, _
                           DescString, _
                           FinQuad, _
                           PlaceDiagramPoint, _
                           finTemplate, _
                           LineSpacing, _
                           extLineLength, _
                           fontSize, _
                           FinXTextElement, _
                           FinYTextElement, _
                           FinNameElement, _
                           FinDescElement
                             
         AddItToArray CellElementArray, FinXTextElement
         AddItToArray CellElementArray, FinYTextElement
         AddItToArray CellElementArray, FinNameElement
         AddItToArray CellElementArray, FinDescElement
            
         CrossOutXText PreXTextElement, CellElementArray, finTemplate
         CrossOutYText PreYTextElement, CellElementArray, finTemplate
         CrossOutNameDesc PreNameElement, PreQuad, CellElementArray, finTemplate
         CrossOutNameDesc PreDescElement, PreQuad, CellElementArray, finTemplate
         AzQuad = CalcAzQuad(PreQuad, FinQuad)
      End If
   End If
   
'DRAW THE AZIMUTH IN APPROPRIATE QUADRANT
   Dim AzTextEl As TextElement
   Dim ArrowCell As CellElement
   CreateRefAzElements AzQuad, _
                       AzTextEl, _
                       ArrowCell, _
                       DropAzimuthTextBox.text, _
                       preTemplate, _
                       PlaceDiagramPoint, _
                       LineSpacing, _
                       fontSize, _
                       legLength, _
                       extLineLength
   AddItToArray CellElementArray, AzTextEl
   AddItToArray CellElementArray, ArrowCell
   
'DRAW LEADER IF NEEDED
   If LeaderLineCheckBox.value Then
      Dim tetherDist As Double
      Dim tetherAz As Double
      Inverse sideShotPoint, PlaceDiagramPoint, tetherAz, tetherDist
      If tetherDist > ((MIN_DROP_LEADER + TRIM_DROP_LEADER) * fontSize) Then
         Dim endOfLeader As Point3d
         Dim LeaderLength As Double
         LeaderLength = tetherDist - (TRIM_DROP_LEADER * fontSize)
         endOfLeader = CoordFwdSAz(sideShotPoint, tetherAz, LeaderLength)
         Dim linePoints(0 To 2) As Point3d
         linePoints(0) = sideShotPoint
         linePoints(1) = endOfLeader
         linePoints(2) = RecordCoord
         Dim Leader As LineElement
         Set Leader = CreateLineElement1(leaderTemplate, linePoints)
         AddCompassRuleElement Leader
      End If
   End If

'ADD DROP DIAGRAM TO DRAWING
   Dim DropCell As CellElement
   Set DropCell = CreateCellElement1(vbNullString, CellElementArray, PlaceDiagramPoint)
   DropCell.RotateAboutZ PlaceDiagramPoint, rotAngleRad
   AddCompassRuleElement DropCell
End Sub



Private Function NewXTextPosition(ByVal XTextLen As Double, _
                                  ByVal DropQuad As Long, _
                                  originPoint As Point3d, _
                                  ByVal LineSpacing As Double, _
                                  ByVal extLineLength As Double, _
                                  ByVal fontSize As Double) As Point3d

'POSITION TEXT ACCORDING TO QUADRANT
   Dim lineOffset As Double
   lineOffset = LineSpacing + fontSize
   
   Dim TextXaxisInsertPoint As Point3d
   TextXaxisInsertPoint = originPoint

   Dim XTextOffsets As Point2d
   XTextOffsets = XTextOffset(XTextLen, DropQuad, LineSpacing, extLineLength, fontSize)

   TextXaxisInsertPoint.X = TextXaxisInsertPoint.X + XTextOffsets.X
   TextXaxisInsertPoint.Y = TextXaxisInsertPoint.Y + XTextOffsets.Y

   Select Case DropQuad 'the quadrant of the deviation
      Case QUAD_NORTH_EAST
          TextXaxisInsertPoint.Y = TextXaxisInsertPoint.Y + lineOffset
      Case QUAD_SOUTH_EAST
          TextXaxisInsertPoint.Y = TextXaxisInsertPoint.Y - lineOffset
      Case QUAD_SOUTH_WEST
          TextXaxisInsertPoint.Y = TextXaxisInsertPoint.Y - lineOffset
      Case QUAD_NORTH_WEST
          TextXaxisInsertPoint.Y = TextXaxisInsertPoint.Y + lineOffset
    End Select
    NewXTextPosition = TextXaxisInsertPoint
End Function



Private Function NewYTextPosition(ByVal YTextLen As Double, _
                                  ByVal DropQuad As Long, _
                                  originPoint As Point3d, _
                                  ByVal LineSpacing As Double, _
                                  ByVal extLineLength As Double, _
                                  ByVal fontSize As Double) As Point3d

'POSITION TEXT ACCORDING TO QUADRANT
   Dim lineOffset As Double
   lineOffset = LineSpacing + fontSize
   
   Dim TextYaxisInsertPoint As Point3d
   TextYaxisInsertPoint = originPoint

   Dim YTextOffsets As Point2d
   YTextOffsets = YTextOffset(YTextLen, DropQuad, LineSpacing, extLineLength, fontSize)

   TextYaxisInsertPoint.X = TextYaxisInsertPoint.X + YTextOffsets.X
   TextYaxisInsertPoint.Y = TextYaxisInsertPoint.Y + YTextOffsets.Y

   Select Case DropQuad
      Case QUAD_NORTH_EAST
          TextYaxisInsertPoint.X = TextYaxisInsertPoint.X + lineOffset
      Case QUAD_SOUTH_EAST
          TextYaxisInsertPoint.X = TextYaxisInsertPoint.X + lineOffset
      Case QUAD_SOUTH_WEST
          TextYaxisInsertPoint.X = TextYaxisInsertPoint.X - lineOffset
      Case QUAD_NORTH_WEST
          TextYaxisInsertPoint.X = TextYaxisInsertPoint.X - lineOffset
    End Select
    NewYTextPosition = TextYaxisInsertPoint
End Function



Private Sub CrossOutNameDesc(ByRef TheTextElement As TextElement, _
                             ByVal quadrant As Long, _
                             ByRef CellElementArray() As Element, _
                             ByRef template As Element)
'CHECK IF ANYTHING TO CROSS OUT
   Dim LabelString As String
   LabelString = TheTextElement.text
   LabelString = Trim(LabelString)

   If LabelString <> "" Then
'DETERMINE WHERE TO DRAW THE CROSS-OUT LINE
      Dim LineStartPoint As Point3d
      LineStartPoint = TheTextElement.origin
      Dim LineEndPoint As Point3d
      LineEndPoint = LineStartPoint
      Dim LabelLen As Point2d
      TheTextElement.GetTotalTextSize LabelLen.X, LabelLen.Y
      Select Case quadrant
         Case QUAD_NORTH_EAST
            LineEndPoint.X = LineEndPoint.X + LabelLen.X
         Case QUAD_SOUTH_EAST
            LineEndPoint.X = LineEndPoint.X + LabelLen.X
         Case QUAD_SOUTH_WEST
            LineEndPoint.X = LineEndPoint.X - LabelLen.X
         Case QUAD_NORTH_WEST
            LineEndPoint.X = LineEndPoint.X - LabelLen.X
      End Select
      
'CREATE THE CROSS-OUT LINE
      Dim lineOut As LineElement
      Set lineOut = CreateLineElement2(template, LineStartPoint, LineEndPoint)
      
'ADD IT TO THE CELL
      AddItToArray CellElementArray, lineOut
   End If
End Sub



Private Sub CrossOutXText(XTextElement As TextElement, CellElementArray() As Element, template As Element)
'CROSS OUT X-VALUE
   Dim XTextLen As Point2d
   XTextElement.GetTotalTextSize XTextLen.X, XTextLen.Y
   Dim LineOutStart As Point3d
   LineOutStart = XTextElement.origin
   Dim LineOutEnd As Point3d
   LineOutEnd = LineOutStart
   LineOutEnd.X = LineOutEnd.X + XTextLen.X
   Dim LineOutXElement As LineElement
   Set LineOutXElement = CreateLineElement2(template, LineOutStart, LineOutEnd)
   AddItToArray CellElementArray, LineOutXElement
End Sub



Private Sub CrossOutYText(YTextElement As TextElement, CellElementArray() As Element, template As Element)
'CROSS OUT Y-VALUE
   Dim YTextLen As Point2d
   YTextElement.GetTotalTextSize YTextLen.X, YTextLen.Y
   Dim LineOutStart As Point3d
   LineOutStart = YTextElement.origin
   Dim LineOutEnd As Point3d
   LineOutEnd = LineOutStart
   LineOutEnd.Y = LineOutEnd.Y + YTextLen.X
   Dim LineOutYElement As LineElement
   Set LineOutYElement = CreateLineElement2(template, LineOutStart, LineOutEnd)
   AddItToArray CellElementArray, LineOutYElement
End Sub



Private Sub CreateTheDropText(ByVal XText As String, _
                              ByVal YText As String, _
                              ByVal nameString As String, _
                              ByVal DescString As String, _
                              ByVal DropQuad As Long, _
                              originPoint As Point3d, _
                              ByVal textTemplate As TextElement, _
                              ByVal LineSpacing As Double, _
                              ByVal extLineLength As Double, _
                              ByVal fontSize As Double, _
                              ByRef DimXEl As TextElement, _
                              ByRef DimYEl As TextElement, _
                              ByRef NameTextEl As TextElement, _
                              ByRef DescTextEl As TextElement)
   If DropNameCheckBox.value Then
      Dim NameStr As String
      NameStr = nameString
   Else
      NameStr = STRING_SPACE
   End If
   
   If DropDescCheckBox.value Then
      Dim DescStr As String
      DescStr = DescString
   Else
      DescStr = STRING_SPACE
   End If
   
   CreateDimAndNameText XText, _
                        YText, _
                        NameStr, _
                        DescStr, _
                        DropQuad, _
                        originPoint, _
                        textTemplate, _
                        LineSpacing, _
                        extLineLength, _
                        fontSize, _
                        DimXEl, _
                        DimYEl, _
                        NameTextEl, _
                        DescTextEl
End Sub



Private Sub DrawTravSym(template As Element, originPoint As Point3d, charSize As Double, rotateViewAboutZAngle As Double)
   If OptionSetupSym1.value = True Then
      Dim TravSym As Element
      Set TravSym = CreateSymbol1Cell(template, originPoint, charSize, rotateViewAboutZAngle)
   ElseIf OptionSetupSym2.value = True Then
      Set TravSym = CreateSymbol2Cell(template, originPoint, charSize, rotateViewAboutZAngle)
   ElseIf OptionSetupSym3.value = True Then
      Set TravSym = CreateSymbol3Cell(template, originPoint, charSize, rotateViewAboutZAngle)
   ElseIf OptionSetupSym4.value = True Then
      Set TravSym = CreateSymbol4Cell(template, originPoint, charSize, rotateViewAboutZAngle)
   ElseIf OptionSetupSym5.value = True Then
      Set TravSym = CreateSymbol5Cell(template, originPoint, charSize, rotateViewAboutZAngle)
   ElseIf OptionSetupSym6.value = True Then
      Set TravSym = CreateSymbol6Cell(template, originPoint, charSize, rotateViewAboutZAngle)
   Else
      Exit Sub
   End If
   AddCompassRuleElement TravSym
End Sub



Private Sub DrawTheMiniCell(InsertionPoint As Point3d, _
                            ByVal rotateViewAboutZAngle As Double, _
                            template As TextElement, _
                            PointNameString As String, _
                            descriptionString As String)
   Dim markerRadius As Double
   markerRadius = 0.05
   Dim position As Point3d
   position = InsertionPoint
   If UseMiniCellCheckBox.value = True Then
      Dim charSize As Double
      charSize = template.TextStyle.Height
      Dim MiniCellArray(0 To 6) As Element
'CREATE THE CENTER CIRCLE ABOUT THE SIZE OF A 3/4" PIPE
      Set MiniCellArray(0) = CreateEllipseElement2(template, position, markerRadius, markerRadius, Matrix3dIdentity)

'CREATE THE POINT NAME TEXT ELEMENT
      Dim NamePosition As Point3d
      NamePosition.X = position.X + (charSize * CDbl(MiniCellLRNameTextBox.text))
      NamePosition.Y = position.Y + (charSize * CDbl(MiniCellNameUDTextBox.text))
      NamePosition.z = position.z
      Set MiniCellArray(1) = CreateTextElement1(template, PointNameString, NamePosition, Matrix3dIdentity)
      
'CREATE THE DESCRIPTION TEXT ELEMENT
      Dim DescPosition As Point3d
      DescPosition.X = position.X + (charSize * CDbl(MinicellLRDescTextBox.text))
      DescPosition.Y = position.Y + (charSize * CDbl(MiniCellUDDescTextBox.text))
      DescPosition.z = position.z
      Set MiniCellArray(2) = CreateTextElement1(template, descriptionString, DescPosition, Matrix3dIdentity)

'CREATE THE CENTER CROSS
      Dim CrossEnd As Point3d
      CrossEnd = position
      CrossEnd.Y = CrossEnd.Y + markerRadius
      Set MiniCellArray(3) = CreateLineElement2(template, position, CrossEnd)
      CrossEnd = position
      CrossEnd.Y = CrossEnd.Y - markerRadius
      Set MiniCellArray(4) = CreateLineElement2(template, position, CrossEnd)
      CrossEnd = position
      CrossEnd.X = CrossEnd.X + markerRadius
      Set MiniCellArray(5) = CreateLineElement2(template, position, CrossEnd)
      CrossEnd = position
      CrossEnd.X = CrossEnd.X - markerRadius
      Set MiniCellArray(6) = CreateLineElement2(template, position, CrossEnd)

'CREATE THE CELL ELEMENT
      Dim MiniCell As CellElement
      Set MiniCell = CreateCellElement1(vbNullString, MiniCellArray, position)

'ROTATE IT TO THE APPROPRIATE ANGLE
      MiniCell.RotateAboutZ position, rotateViewAboutZAngle

'ADD IT TO THE DRAWING AS A COMPASS RULE ELEMENT
      AddCompassRuleElement MiniCell
   End If
End Sub



Private Sub DrawTheSideShotText(position As Point3d, _
                                ByVal rotateViewAboutZAngle As Double, _
                                template As TextElement, _
                                PointNameString As String, _
                                descriptionString As String)
   If SideShotTextPointNameCheckBox.value = True Then
      DrawTheText position, CDbl(SideNameUDOffsetTextBox.text), CDbl(SideNameLROffsetTextBox.text), rotateViewAboutZAngle, template, PointNameString
   End If
   If SideShotTextDescriptionCheckBox.value = True Then
      DrawTheText position, CDbl(SideDescUDOffsetTextBox.text), CDbl(SideDescLROffsetTextBox.text), rotateViewAboutZAngle, template, descriptionString
   End If
End Sub



Private Sub DrawTheTraverseText(position As Point3d, _
                                ByVal rotateViewAboutZAngle As Double, _
                                template As TextElement, _
                                PointNameString As String, _
                                descriptionString As String, _
                                travElString As String)
   If TraversePointNameCheckBox.value Then
      DrawTheText position, CDbl(TravNameUDOffsetTextBox.text), CDbl(TravNameLROffsetTextBox.text), rotateViewAboutZAngle, template, PointNameString
   End If
   If TraverseDescriptionCheckBox.value Then
      DrawTheText position, CDbl(TravDescUDOffsetTextBox.text), CDbl(TravDescLROffsetTextBox.text), rotateViewAboutZAngle, template, descriptionString
   End If
   If ElevCheckBox.value Then
      Dim plotElev As Boolean
      Dim elevString As String
      ParseTravElString travElString, plotElev, elevString
      If plotElev Then
         DrawTheText position, CDbl(elUDOSTextBox.text), CDbl(elLRLOSTextBox.text), rotateViewAboutZAngle, template, "El. = " & elevString
      End If
   End If
End Sub



Private Sub DrawTheText(position As Point3d, _
                        ByVal UpDownOffset As Double, _
                        ByVal LeftRightOffset As Double, _
                        ByVal rotateViewAboutZAngle As Double, _
                        template As TextElement, _
                        theText As String)
   Dim charSize As Double
   charSize = template.TextStyle.Height
   Dim UpDownOffsetFeet As Double
   UpDownOffsetFeet = UpDownOffset * charSize
   Dim LeftRightOffsetFeet As Double
   LeftRightOffsetFeet = LeftRightOffset * charSize
   Dim InsertionPoint As Point3d
   InsertionPoint.X = position.X + LeftRightOffsetFeet
   InsertionPoint.Y = position.Y + UpDownOffsetFeet
   InsertionPoint.z = position.z
   Dim PointNameElement As TextElement
   Set PointNameElement = CreateTextElement1(template, theText, InsertionPoint, Matrix3dIdentity)
   PointNameElement.RotateAboutZ position, rotateViewAboutZAngle
   AddCompassRuleElement PointNameElement
End Sub



Private Function GetStartingPoint() As Point3d
   GetStartingPoint.X = GetEasting(TextEasting)
   GetStartingPoint.Y = GetNorthing(TextNorthing)
   GetStartingPoint.z = CDbl(TextElevation.text)
End Function



Private Function forwardPoint(startPoint As Point3d, _
                              BSAzimuthString As String, _
                              BSAngleString As String, _
                              FSAngleString As String, _
                              hDString As String, _
                              ByRef ForwardSAz As Double) As Point3d
'DEFAULT VALUE
   forwardPoint = startPoint

'CONVERT BACK SIGHT AZIMUTH TO DEGREES DOUBLE
   Dim BSAzimuthDegreesDouble As Double
   Dim origPrec As Long
   Dim dirType As Integer
   Dim quad As Integer
   If Not DirStringToSAz(BSAzimuthString, BSAzimuthDegreesDouble, origPrec, dirType, quad) Then
'SHOULD NEVER GET HERE, CREATE ERROR IF IT DOES
      Err.Raise ERROR_NUM_534
   End If

'CONVERT BACK SIGHT ANGLE TO DEGREES DOUBLE
   Dim BSAngleDegreesDouble As Double
   If Not AngleStringToDegree(BSAngleString, BSAngleDegreesDouble) Then
'SHOULD NEVER GET HERE, CREATE ERROR IF IT DOES
      Err.Raise ERROR_NUM_532
   End If

'CONVERT FORE SIGHT ANGLE TO DEGREES DOUBLE
   Dim FSAngleDegreesDouble As Double
   If Not AngleStringToDegree(FSAngleString, FSAngleDegreesDouble) Then
      Exit Function
   End If

'CALCULATE FORWARD AZIMUTH IN DEGREES
   ForwardSAz = (FSAngleDegreesDouble - BSAngleDegreesDouble) + BSAzimuthDegreesDouble
   MakeSure360 ForwardSAz

'CALCULATE FORWARD POINT
   forwardPoint = CoordFwdSAz(startPoint, ForwardSAz, CDbl(hDString))
End Function



Private Sub AddCompassRuleElement(theElement As Element)
'ADD IT TO THE FILE
   ActiveModelReference.AddElement theElement

'ADD THE TAGS TO IS FOR AUTO DELETING
   AddTraverseAutoDeleteTags theElement, Me.IDstring
   
'MAKE SURE YOU CAN SEE IT
   theElement.Redraw
End Sub



Private Sub DrawTravSideLine(template As Element, startPoint As Point3d, endPoint As Point3d)
'CREATE THE LINE ELEMENT
   Dim newLine As LineElement
   Set newLine = CreateLineElement2(template, startPoint, endPoint)
   AddCompassRuleElement newLine
End Sub



Public Sub AddTraverseAutoDeleteTags(theElement As Element, ByVal TraverseFileIDString As String)
'GET ELEMENT ID TO USE FOR TAG
   Dim ID As DLong
   Dim IDstring As String
   If Not GetTheElementID(theElement, ID, IDstring) Then
   'SOMETHING WRONG, EXIT
      Exit Sub
   End If
'TAG ELEMENT WITH ITS ID STRING SO WE KNOW THIS PROGRAM CREATED IT, AND IT'S NOT JUST A COPY
   TagMyElement theElement, TAG_NAME_MY_ID, IDstring
'TAG THE ELEMENT WITH THE TRAVERSE FILE ID SO WE KNOW IT RELATES ONLY TO THIS FILE
   TagMyElement theElement, TAG_NAME_COMPASS_RULE_2D_ID, TraverseFileIDString
End Sub



Private Sub RewriteRedrawCompassRuleFile()
'WRITE TO FILE
   RewriteCompassRuleFile

'DRAW THE FILE
   RedrawCompassRuleFile
End Sub



Private Sub RewriteCompassRuleFile()
'GET RID OF OLD INFO
   ClearAverageDrop

'DO NOTHING IF FILE IS NOT LOADED
   If Not Me.FileLoaded Then
      Exit Sub
   End If

'REWRITE THE FILE
   If Not WriteCompassRuleFile(GetCompassRuleFullFilename(), Me) Then
      Exit Sub
   End If
End Sub



Private Sub RedrawCompassRuleFile()
'DO NOTHING IF FILE IS NOT LOADED
   If Not Me.FileLoaded Then
      Exit Sub
   End If

'DELETE PREVIOUSLY DRAWN ELEMENTS
   DeletePreviousElements Me.IDstring

'REDRAW THE FILE
   If ActiveModelReference.IsReadOnly Then
      Exit Sub
   End If

'CALC THE RAW
   Dim PreAdjPointsArray As Variant
   PreAdjPointsArray = CalcRaw(False, Nothing)
   Dim TheAdjPointsArray As Variant
   TheAdjPointsArray = PreAdjPointsArray

'APPLY APPROPRIATE ADJUSTMENTS
'COMPASS RULE
   CompassRulePointsArray TheAdjPointsArray

'COORDINATE TRANSFORMATION IF ANY
   TransformPointsArray TheAdjPointsArray
   
'DRAW THE TRAVERSE CIRCUIT
   If FinalOption.value Then
      StoFinalTab
      RclPrelimTab
      ApplyStates
      CompassRulePointsArray PreAdjPointsArray
      TransformPointsArray PreAdjPointsArray
      DrawTheCircuit TheAdjPointsArray, PreAdjPointsArray, True
      RclFinalTab
      ApplyStates
   Else
      DrawTheCircuit TheAdjPointsArray, TheAdjPointsArray, False
   End If
   CommandState.CommandName = COMMAND_NAME_COMPASS_RULE_2D
   CommandState.StartDefaultCommand
End Sub



Private Sub ReviseTheSideshots(TraverseAdjustedArray As Variant)
'GET STARTING POINT OF TRAVERSE
   Dim SetupPoint As Point3d
   SetupPoint = GetStartingPoint()

'INITIALIZE BACK SIGHT AZIMUTH
   Dim origPrec As Long
   Dim dirType As Integer
   Dim quad As Integer
   Dim BSAzDegrees As Double
   If Not DirStringToSAz(FirstBSAzTextBox.text, BSAzDegrees, origPrec, dirType, quad) Then
      MsgBox "problem revising sideshots"
      Exit Sub
   End If

'CALCULATE ENDING INDEX
   Dim EndIndex As Long
   EndIndex = RawEntriesListBox.ListCount - 1

'LOOP THROUGH RAW ENTRIES
   Dim rawIndex As Long
   For rawIndex = 0 To EndIndex
'READ ONE LINE OF RAW ENTRIES
      Dim shotType As String
      Dim pointName As String
      Dim bSString As String
      Dim fSString As String
      Dim hDString As String
      Dim descriptionString As String
      Dim showDrop As Boolean
      Dim elevationString As String
      GetRawListLine rawIndex, shotType, pointName, bSString, fSString, hDString, descriptionString, showDrop, elevationString
      If shotType = KEY_COMPASS_RULE_SIDE_SHOT Then
'CALCULATE SIDE SHOT POINT, DOES NOT WORK WHEN MADE INTO A FUNCTION
         Dim BSAngleDegrees As Double
         If Not AngleStringToDegree(bSString, BSAngleDegrees) Then
            Exit Sub
         End If

         Dim FSAngleDegrees As Double
         If Not AngleStringToDegree(fSString, FSAngleDegrees) Then
            Exit Sub
         End If
         Dim FSAzimDegrees As Double
         FSAzimDegrees = FSAngleDegrees - BSAngleDegrees + BSAzDegrees
         TraverseAdjustedArray(rawIndex) = CoordFwdSAz(SetupPoint, FSAzimDegrees, CDbl(hDString))
      End If
'TRAVERSE
      If shotType = KEY_COMPASS_RULE_TRAV Then
         If rawIndex > 0 Then
            Dim PreviousSetup As Point3d
            PreviousSetup = SetupPoint
            SetupPoint = TraverseAdjustedArray(rawIndex)
            BSAzDegrees = InverseAzimuth(SetupPoint, PreviousSetup)
         End If
      End If
   Next rawIndex
End Sub



Private Sub CompassRulePointsArray(ThePointsArray As Variant)
'CLEAR OUT MISCLOSURE FIELDS FOR RERUNS
   ClearRerunStats

   If ApplyAdjustmentCheckBox.value = False Or ApplyAdjustmentCheckBox.enabled = False Then
      CompassRuleStatusLabel.Caption = NOT_APPLICABLE_STRING
      Exit Sub
   End If

   If LastForesightOption.value = True And TraversesListBox.ListCount < 2 Then
      CompassRuleStatusLabel.Caption = NOT_APPLICABLE_STRING
      Exit Sub
   End If

   If LastTraverseOption.value = True And TraversesListBox.ListCount < 3 Then
      CompassRuleStatusLabel.Caption = NOT_APPLICABLE_STRING
      Exit Sub
   End If

   If TraversePrecLabel.Caption = POOR_STRING Then
      CompassRuleStatusLabel.Caption = "Poor precision, not applied"
      Exit Sub
   End If

   If TwoPointAdjustmentOption.value = True And ChooseTwoPtObsComboBox.listIndex < 0 Then
      CompassRuleStatusLabel.Caption = NOT_APPLICABLE_STRING
      Exit Sub
   End If

   Dim LastTravRawIndex As Long
   LastTravRawIndex = TraversesListBox.List(TraversesListBox.ListCount - 1, TRAV_COLUMN_REF_NUM)
   Dim ObsRawIndex As Long
   ObsRawIndex = TwoPtObsComboRefNum()
   If (TwoPointAdjustmentOption.value = True) And _
      (LastTraverseOption.value = True) And _
      (ObsRawIndex = LastTravRawIndex) Then
      CompassRuleStatusLabel.Caption = "Not doable"
      Exit Sub
   End If

   If (TwoPointAdjustmentOption.value = True) And _
      (ObsRawIndex = RawEntriesListBox.ListCount - 1) Then
      CompassRuleStatusLabel.Caption = "Not doable"
      Exit Sub
   End If


'PRORATE ANGULAR ERROR
   AngularAdjustPointsArray ThePointsArray

'COMPASS RULE COURSES
   CompassRuleThePointsArray ThePointsArray

'RERUN AT PRECISION
   RerunAtPrecPointsArray ThePointsArray

'REVISE THE SIDE SHOTS
   ReviseTheSideshots ThePointsArray

'UPDATE THE 2 POINT MISCLOSURE FIELDS IF APPLIES
   Update2PointMisclosureFields ThePointsArray

'UPDATE THE STATUS FIELD
   CompassRuleStatusLabel.Caption = COMPASS_RULE_APPLIED
End Sub



Private Sub Update2PointMisclosureFields(ThePointsArray As Variant)
   If TwoPointAdjustmentOption.value = False Then
      Exit Sub
   End If
   If TwoPointAdjustmentOption.enabled = False Then
      Exit Sub
   End If
   If InverseCourseOption.value = True Then
      Exit Sub
   End If
   Dim twoPointObsIndex As Long
   twoPointObsIndex = TwoPtObsComboRefNum()
   Dim intCloseOBSPoint As Point3d
   intCloseOBSPoint = ThePointsArray(twoPointObsIndex)
   Dim dY As Double
   dY = intCloseOBSPoint.Y - GetNorthing(TwoPtNorthTextBox)
   RerunIntNorthMisLabel.Caption = FormatNumber(dY, 4, vbTrue, vbFalse, vbFalse)
   Dim dX As Double
   dX = intCloseOBSPoint.X - GetEasting(TwoPtEastTextBox)
   RerunIntEastMisLabel.Caption = FormatNumber(dX, 4, vbTrue, vbFalse, vbFalse)
   RerunIntDistMisLabel.Caption = FormatNumber(InverseDistance(dY, dX), 3, vbTrue, vbFalse, vbFalse)
End Sub



Private Sub RerunAtPrecPointsArray(ThePointsArray As Variant)
   If HoldingCoursesOption.value = False Then
      Exit Sub
   End If

'GET PRECISION
   Dim precision As Long
   If SecondOption.value = True Then
      precision = 4
   ElseIf TenthSecondOption.value = True Then
      precision = 5
   Else
      Exit Sub
   End If

   Dim distPrec As Long
   If HundredthOption.value = True Then
      distPrec = 2
   ElseIf ThousandthOption.value = True Then
      distPrec = 3
   Else
      Exit Sub
   End If

'LOOP THROUGH THE TRAVERSES
   Dim PreviousSetupPoint As Point3d
   PreviousSetupPoint = ThePointsArray(0)
   Dim UpdatedPoint As Point3d
   UpdatedPoint = PreviousSetupPoint
   Dim refNum As Long
   Dim PreviousRefNum As Long
   Dim pointName As String
   Dim bSString As String
   Dim fSString As String
   Dim hDString As String
   Dim descriptionString As String
   GetTravListLine 0, refNum, pointName, bSString, fSString, hDString, descriptionString
   Dim itsASideShot As Boolean
   itsASideShot = True
   Dim TravIndex As Long
   For TravIndex = 1 To (TraversesListBox.ListCount - 1)
      GetTravListLine TravIndex, refNum, pointName, bSString, fSString, hDString, descriptionString
      Dim SetupPoint As Point3d
      SetupPoint = ThePointsArray(refNum)

      Dim InversedDistance As Double
      Dim InversedAzimDegrees As Double
      Inverse PreviousSetupPoint, SetupPoint, InversedAzimDegrees, InversedDistance

      Dim InversedAzimString As String
      InversedAzimString = SAzToAzimuthStr(InversedAzimDegrees, precision, GetAngleStyle())
      Dim TheRoundedDegrees As Double
      Dim origPrec As Long
      Dim dirType As Integer
      Dim quad As Integer
      If Not DirStringToSAz(InversedAzimString, TheRoundedDegrees, origPrec, dirType, quad) Then
         Exit Sub
      End If

      UpdatedPoint = CoordFwdSAz(UpdatedPoint, TheRoundedDegrees, Round(InversedDistance, distPrec))
      ThePointsArray(refNum) = UpdatedPoint
      PreviousSetupPoint = SetupPoint
   Next TravIndex

'IF CLOSING TO LAST FORESIGHT, APPLY TO LAST ELEMENT IN ARRAY
   If LastForesightOption.value = True Then
      SetupPoint = ThePointsArray(UBound(ThePointsArray))
      Inverse PreviousSetupPoint, SetupPoint, InversedAzimDegrees, InversedDistance

      InversedAzimString = SAzToAzimuthStr(InversedAzimDegrees, precision, GetAngleStyle())
      If Not DirStringToSAz(InversedAzimString, TheRoundedDegrees, origPrec, dirType, quad) Then
         Exit Sub
      End If
      Dim ClosingObsPoint As Point3d
      ClosingObsPoint = CoordFwdSAz(UpdatedPoint, TheRoundedDegrees, Round(InversedDistance, distPrec))
      ThePointsArray(UBound(ThePointsArray)) = ClosingObsPoint
   Else
      ClosingObsPoint = UpdatedPoint
   End If

'UPDATE MISCLOSURE FIELDS
'GET CLOSE TO POINT
   If ToBeginningOption.value = True Then
      Dim ClosingPoint As Point3d
      ClosingPoint.Y = GetNorthing(TextNorthing)
      ClosingPoint.X = GetEasting(TextEasting)
      ClosingPoint.z = CDbl(TextElevation.text)
   ElseIf ToPointOption.value = True Then
      ClosingPoint.Y = GetNorthing(CloseNorthTextBox)
      ClosingPoint.X = GetEasting(CloseEastTextBox)
      ClosingPoint.z = CDbl(TextElevation.text)
   Else
      Exit Sub
   End If
   Dim dY As Double
   dY = ClosingObsPoint.Y - ClosingPoint.Y
   RerunMisNorthLabel.Caption = FormatNumber(dY, 4, vbTrue, vbFalse, vbFalse)
   Dim dX As Double
   dX = ClosingObsPoint.X - ClosingPoint.X
   RerunMisEastLabel.Caption = FormatNumber(dX, 4, vbTrue, vbFalse, vbFalse)
   RerunMisDisLabel.Caption = FormatNumber(InverseDistance(dY, dX), 3, vbTrue, vbFalse, vbFalse)
End Sub



Private Sub CompassRuleThePointsArray(ThePointsArray As Variant)
   If SingleCompassRuleOption.value And SingleCompassRuleOption.enabled Then
      SingleCompassruleTheArray ThePointsArray
      Exit Sub
   End If
   
   If TwoPointAdjustmentOption.value And TwoPointAdjustmentOption.enabled Then
      TwoPointCompassruleTheArray ThePointsArray
   End If
End Sub

Private Sub TwoPointCompassruleTheArray(ThePointsArray As Variant)
'GET INTERMEDIATE CLOSING POINT OBS INDEX NUMBER
   Dim IntClosePointIndex As Long
   IntClosePointIndex = TwoPtObsComboRefNum()

'GET ANGLE PRECISION
   Dim AngPrec As Long
   If HoldingCoursesOption.value = True Then
      If SecondOption.value = True Then
          AngPrec = 4
      Else
          AngPrec = 5
      End If
   Else
      If Inv1secOption.value = True Then
          AngPrec = 4
      Else
          AngPrec = 5
      End If
   End If

'GET INTERMEDIATE POINT VALUE
   Dim IntermediatePoint As Point2d
   IntermediatePoint.X = GetEasting(TwoPtEastTextBox)
   IntermediatePoint.Y = GetNorthing(TwoPtNorthTextBox)
   
'IF FIRST TRAVERSE IS THE CLOSING POINT, THEN MAKE IT THE MOVE TO COORDINATE
   If IntClosePointIndex = 0 Then
      changeXYPointsArray ThePointsArray, 0, IntermediatePoint.X, IntermediatePoint.Y
'ADJUST PART 2
      AdjSecondPartOfArray ThePointsArray, 0, FirstBSAzTextBox.text
      Exit Sub
   End If
   
   Dim refNum As Long
   Dim PreviousRefNum As Long
   Dim pointName As String
   Dim bSString As String
   Dim fSString As String
   Dim hDString As String
   Dim descriptionString As String
   GetTravListLine 1, refNum, pointName, bSString, fSString, hDString, descriptionString

'IF SIDESHOT OF FIRST TRAVERSE IS THE CLOSING POINT, THEN BACK IT UP TO THE TRAVERSE
   If IntClosePointIndex < refNum Then
      Dim ClosingSideShot As Point3d
      ClosingSideShot = ThePointsArray(IntClosePointIndex)
      Dim SetupPoint As Point3d
      SetupPoint = ThePointsArray(0)
      Dim NewSetupPoint As Point3d
      NewSetupPoint.X = SetupPoint.X - ClosingSideShot.X + IntermediatePoint.X
      NewSetupPoint.Y = SetupPoint.Y - ClosingSideShot.Y + IntermediatePoint.Y
      changeXYPointsArray ThePointsArray, 0, NewSetupPoint.X, NewSetupPoint.Y
      changeXYPointsArray ThePointsArray, IntClosePointIndex, IntermediatePoint.X, IntermediatePoint.Y
'ADJUST PART 2
      AdjSecondPartOfArray ThePointsArray, 0, FirstBSAzTextBox.text
      Exit Sub
   End If

'IF THE SECOND TRAVERSE IS THE CLOSING POINT, THEN JUST MOVE THE SECOND TRAVERSE
   If IntClosePointIndex = refNum Then
      changeXYPointsArray ThePointsArray, refNum, IntermediatePoint.X, IntermediatePoint.Y
'ADJUST PART 2
      SetupPoint = ThePointsArray(refNum)
      Dim BackSightPoint As Point3d
      BackSightPoint = ThePointsArray(0)
      Dim BacksightSADegrees As Double
      BacksightSADegrees = InverseAzimuth(SetupPoint, BackSightPoint)
      Dim BSAzString As String
      BSAzString = SAzToAzimuthStr(BacksightSADegrees, AngPrec, GetAngleStyle())
      AdjSecondPartOfArray ThePointsArray, 1, BSAzString
      Exit Sub
   End If

'PROCESS FOR NORMAL CASE
   Dim TravIndex As Long
   TravIndex = 0
   Dim highestTravIndex As Long
   highestTravIndex = TraversesListBox.ListCount - 1
   Dim FullLengthOfTrav As Double
   FullLengthOfTrav = 0
   refNum = 0
   Dim lastHD As Double
   lastHD = 0
'CALCULATE THE TRAVERSE LENGTH TO THE INTERMEDIATE POINT AND THE TRAVERSE TO IT
   Do While refNum <= IntClosePointIndex
      GetTravListLine TravIndex, refNum, pointName, bSString, fSString, hDString, descriptionString
      If refNum <= IntClosePointIndex Then
         FullLengthOfTrav = FullLengthOfTrav + lastHD
         lastHD = CDbl(hDString)
      End If
      If refNum > IntClosePointIndex Then
         TravIndex = TravIndex - 1
         Exit Do
      End If
      If refNum = IntClosePointIndex Then
         Exit Do
      End If
      If TravIndex = highestTravIndex Then
         Exit Do
      End If
      TravIndex = TravIndex + 1
   Loop

'ACCOUNT FOR WHEN IT'S A SIDE SHOT
   If refNum > IntClosePointIndex Then
      Dim shotType As String
      Dim showDrop As Boolean
      Dim elevationString As String
      GetRawListLine IntClosePointIndex, shotType, pointName, bSString, fSString, hDString, descriptionString, showDrop, elevationString
      FullLengthOfTrav = FullLengthOfTrav + CDbl(hDString)
   End If

'IF LENGTH OF TRAVERSE IS ZERO, NOTHING TO DO
   If FullLengthOfTrav = 0 Then
      Exit Sub
   End If

'GET THE MISCLOSURE ERROR
   Dim ClosingPointObs As Point3d
   ClosingPointObs = ThePointsArray(IntClosePointIndex)
   Dim Xerror As Double
   Xerror = ClosingPointObs.X - IntermediatePoint.X
   Dim Yerror As Double
   Yerror = ClosingPointObs.Y - IntermediatePoint.Y
'APPLY THE PRORATED ERROR TO EACH TRAVERSE
   Dim SubLengthOfTrav As Double
   SubLengthOfTrav = 0
   Dim FinTravIndex As Long
   FinTravIndex = TravIndex
   For TravIndex = 0 To FinTravIndex
      Dim BacksightPointRawIndex As Long
      BacksightPointRawIndex = refNum
      GetTravListLine TravIndex, refNum, pointName, bSString, fSString, hDString, descriptionString
      Dim SetupPointRawIndex As Long
      SetupPointRawIndex = refNum
      Dim ObsPoint As Point3d
      ObsPoint = ThePointsArray(refNum)
      Dim proration As Double
      proration = SubLengthOfTrav / FullLengthOfTrav
      Dim newX As Double
      newX = ObsPoint.X - (Xerror * proration)
      Dim newY As Double
      newY = ObsPoint.Y - (Yerror * proration)
      changeXYPointsArray ThePointsArray, refNum, newX, newY
      SubLengthOfTrav = SubLengthOfTrav + CDbl(hDString)
   Next TravIndex

'COMPASS RULE THE SECOND PART
   SetupPoint = ThePointsArray(SetupPointRawIndex)
   BackSightPoint = ThePointsArray(BacksightPointRawIndex)
   BacksightSADegrees = InverseAzimuth(SetupPoint, BackSightPoint)
   BSAzString = SAzToAzimuthStr(BacksightSADegrees, AngPrec, GetAngleStyle())
   AdjSecondPartOfArray ThePointsArray, FinTravIndex, BSAzString
End Sub



Private Sub AdjSecondPartOfArray(ThePointsArray As Variant, ByVal StartTravIndex As Long, BackAzDegrees As String)
'GET THE CLOSING POINT
   If ToPointOption.value = True Then
      Dim ClosingPoint As Point3d
      ClosingPoint.X = GetEasting(CloseEastTextBox)
      ClosingPoint.Y = GetNorthing(CloseNorthTextBox)
   End If
   If ToBeginningOption.value Then
      ClosingPoint = ThePointsArray(0)
   End If

'GET CLOSING OBSERVATION TYPE
   Dim UseLastForeSightOBS As Boolean
   UseLastForeSightOBS = LastForesightOption.value

'FIND LAST TRAVERSE INDEX
   Dim LastTravIndex As Long
   LastTravIndex = TraversesListBox.ListCount - 1

'HANDLE SPECIAL CASES
   If (StartTravIndex = LastTravIndex) And UseLastForeSightOBS Then
      changeXYPointsArray ThePointsArray, UBound(ThePointsArray), ClosingPoint.X, ClosingPoint.Y
      Exit Sub
   End If

   If (StartTravIndex = LastTravIndex - 1) And (Not UseLastForeSightOBS) Then
      Dim refNum As Long
      Dim pointName As String
      Dim bSString As String
      Dim fSString As String
      Dim hDString As String
      Dim descriptionString As String
      GetTravListLine LastTravIndex, refNum, pointName, bSString, fSString, hDString, descriptionString
      changeXYPointsArray ThePointsArray, refNum, ClosingPoint.X, ClosingPoint.Y
      Exit Sub
   End If

'GET INITIAL SETUP POINT
   GetTravListLine StartTravIndex, refNum, pointName, bSString, fSString, hDString, descriptionString
   Dim foresightPoint As Point3d
   foresightPoint = ThePointsArray(refNum)

'RERUN TRAVERSE POINTS BASED ON NEW AZIMUTH
   Dim BSSAzDegrees As Double
   Dim origPrec As Long
   Dim dirType As Integer
   Dim quad As Integer
   If Not DirStringToSAz(BackAzDegrees, BSSAzDegrees, origPrec, dirType, quad) Then
'SHOULD NEVER GET HERE, CREATE ERROR IF IT DOES
      Err.Raise ERROR_NUM_538
   End If
   Dim TravLen As Double
   TravLen = 0
   Dim TravIndex As Long
   For TravIndex = StartTravIndex To LastTravIndex
      Dim SetupPoint As Point3d
      SetupPoint = foresightPoint
      GetTravListLine TravIndex, refNum, pointName, bSString, fSString, hDString, descriptionString
      Dim HD As Double
      HD = CDbl(hDString)
      TravLen = TravLen + HD
      foresightPoint = calcPointFwd(SetupPoint, BSSAzDegrees, bSString, fSString, HD)
      BSSAzDegrees = InverseAzimuth(foresightPoint, SetupPoint)
      ThePointsArray(refNum) = SetupPoint
   Next TravIndex
   ThePointsArray(UBound(ThePointsArray)) = foresightPoint
   If UseLastForeSightOBS Then
      Dim CloseObsPoint As Point3d
      CloseObsPoint = foresightPoint
   Else
      CloseObsPoint = SetupPoint
      TravLen = TravLen - HD
   End If

'CALC NEW MISCLOSURE
   Dim dY As Double
   dY = CloseObsPoint.Y - ClosingPoint.Y
   Dim dX As Double
   dX = CloseObsPoint.X - ClosingPoint.X

'APPLY THE ADJUSTMENT
   If TravLen = 0 Then
      Exit Sub
   End If
   Dim TravSubLen As Double
   TravSubLen = 0
   For TravIndex = StartTravIndex To LastTravIndex
      Dim proration As Double
      proration = TravSubLen / TravLen
      GetTravListLine TravIndex, refNum, pointName, bSString, fSString, hDString, descriptionString
      SetupPoint = ThePointsArray(refNum)
      SetupPoint.X = SetupPoint.X - (proration * dX)
      SetupPoint.Y = SetupPoint.Y - (proration * dY)
      ThePointsArray(refNum) = SetupPoint
      HD = CDbl(hDString)
      TravSubLen = TravSubLen + HD
   Next TravIndex
   If UseLastForeSightOBS Then
      SetupPoint = ThePointsArray(UBound(ThePointsArray))
      proration = TravSubLen / TravLen
      SetupPoint.X = SetupPoint.X - (proration * dX)
      SetupPoint.Y = SetupPoint.Y - (proration * dY)
      ThePointsArray(UBound(ThePointsArray)) = SetupPoint
   End If
End Sub



Private Function calcPointFwd(SetupPoint As Point3d, BSSAzDegrees As Double, bSString As String, fSString As String, HD As Double) As Point3d
   Dim BS As Double
   If Not AngleStringToDegree(bSString, BS) Then
      BS = 0#
   End If
   Dim FS As Double
   If Not AngleStringToDegree(fSString, FS) Then
      FS = 0#
   End If
   Dim az As Double
   az = FS - BS + BSSAzDegrees
   calcPointFwd = CoordFwdSAz(SetupPoint, az, HD)
End Function



Private Sub changeXYPointsArray(ThePointsArray As Variant, ArrayIndex As Long, X As Double, Y As Double)
   Dim tempPoint As Point3d
   tempPoint = ThePointsArray(ArrayIndex)
   tempPoint.X = X
   tempPoint.Y = Y
   ThePointsArray(ArrayIndex) = tempPoint
End Sub



Private Sub SingleCompassruleTheArray(ThePointsArray As Variant)
'GET LENGTH OF TRAVERSE
   Dim TraverseLength As Double
   TraverseLength = CDbl(TravLengthLabel)
   If TraverseLength <= 0 Then
      Exit Sub
   End If

'GET CLOSE TO POINT
   If ToBeginningOption.value = True Then
      Dim ClosingPoint As Point3d
      ClosingPoint.Y = GetNorthing(TextNorthing)
      ClosingPoint.X = GetEasting(TextEasting)
      ClosingPoint.z = CDbl(TextElevation.text)
   ElseIf ToPointOption.value = True Then
      ClosingPoint.Y = GetNorthing(CloseNorthTextBox)
      ClosingPoint.X = GetEasting(CloseEastTextBox)
      ClosingPoint.z = CDbl(TextElevation.text)
   Else
      Exit Sub
   End If
   
'DETERMINE CLOSING OBSERVATION REF#
   If LastForesightOption.value = True Then
      Dim lastForesight As Boolean
      lastForesight = True
      Dim ClosingObsPoint As Point3d
      ClosingObsPoint = ThePointsArray(UBound(ThePointsArray))
   Else
      lastForesight = False
      Dim refNum As Long
      Dim pointName As String
      Dim bSString As String
      Dim fSString As String
      Dim hDString As String
      Dim descriptionString As String
      GetTravListLine TraversesListBox.ListCount - 1, refNum, pointName, bSString, fSString, hDString, descriptionString
      ClosingObsPoint = ThePointsArray(refNum)
   End If

'CALCULATE THE CHANGE IN X AND Y
   Dim dY As Double
   Dim dX As Double
   dY = ClosingObsPoint.Y - ClosingPoint.Y
   dX = ClosingObsPoint.X - ClosingPoint.X

'LOOP THOUGH TRAVERSES, APPLY ADJUSTMENT
   Dim LengthAlongTrav As Double
   LengthAlongTrav = 0
   Dim TravIndex As Long
   For TravIndex = 0 To (TraversesListBox.ListCount - 1)
      Dim proration As Double
      If TraverseLength <> 0 Then
         proration = LengthAlongTrav / TraverseLength
      Else
         proration = 0
      End If
      GetTravListLine TravIndex, refNum, pointName, bSString, fSString, hDString, descriptionString
      Dim SetupPoint As Point3d
      SetupPoint = ThePointsArray(refNum)
      SetupPoint.Y = SetupPoint.Y + (proration * -dY)
      SetupPoint.X = SetupPoint.X + (proration * -dX)
      ThePointsArray(refNum) = SetupPoint
      LengthAlongTrav = LengthAlongTrav + CDbl(hDString)
   Next TravIndex

'IF CLOSING TO LAST FORESIGHT, APPLY TO LAST ELEMENT IN ARRAY
   If lastForesight Then
      If TraverseLength <> 0 Then
         proration = LengthAlongTrav / TraverseLength
      Else
         proration = 0
      End If
      Dim foresightPoint As Point3d
      foresightPoint = ThePointsArray(UBound(ThePointsArray))
      foresightPoint.Y = foresightPoint.Y + (proration * -dY)
      foresightPoint.X = foresightPoint.X + (proration * -dX)
      ThePointsArray(UBound(ThePointsArray)) = foresightPoint
   End If
End Sub



Private Sub AngularAdjustPointsArray(NonangularAdjustedArray As Variant)
'ADJUST TRAVERSE LEGS ONLY, NOT SIDESHOTS
'CHECK IF OPTION REQUESTED
   If Not (AngularAdjustmentCheckBox.value And AngularAdjustmentCheckBox.enabled) Then
      Exit Sub
   End If

'CHECK IF THERE IS ANYTHING TO ADJUST
   Dim NumberOfLegs As Long
   NumberOfLegs = CLng(NumberOfLegsLabel)
   If NumberOfLegs < 1 Then
      Exit Sub
   End If

'GET ANGLE TO ADJUST BY
   Dim AggregateAngleDegrees As Double
   If Not AngleStringToDegree(AngularAdjustmentTextBox.text, AggregateAngleDegrees) Then
      Exit Sub
   End If

'CALCULATE THE PRORATION
   Dim prorata As Double
   prorata = AggregateAngleDegrees / NumberOfLegs
   
'GET THE BACKSIGHT AZIMUTH
   Dim origPrec As Long
   Dim dirType As Integer
   Dim quad As Integer
   Dim BacksightDegrees As Double
   If Not DirStringToSAz(FirstBSAzTextBox.text, BacksightDegrees, origPrec, dirType, quad) Then
      Exit Sub
   End If

'APPLY THE PRORATION
   Dim NextSetupPoint As Point3d
   NextSetupPoint = NonangularAdjustedArray(0)
   Dim TravIndex As Long
   For TravIndex = 0 To (TraversesListBox.ListCount - 1)
      Dim SetupPoint As Point3d
      SetupPoint = NextSetupPoint
      Dim refNum As Long
      Dim pointName As String
      Dim bSString As String
      Dim fSString As String
      Dim hDString As String
      Dim descriptionString As String
      GetTravListLine TravIndex, refNum, pointName, bSString, fSString, hDString, descriptionString
      NonangularAdjustedArray(refNum) = SetupPoint
      Dim BSDegrees As Double
      If Not AngleStringToDegree(bSString, BSDegrees) Then
         BSDegrees = 0#
      End If
      Dim FSDegrees As Double
      If Not AngleStringToDegree(fSString, FSDegrees) Then
         FSDegrees = 0#
      End If
      Dim azFwdDegrees As Double
      azFwdDegrees = FSDegrees - BSDegrees + BacksightDegrees + prorata
      NextSetupPoint = CoordFwdSAz(SetupPoint, azFwdDegrees, CDbl(hDString))
      BacksightDegrees = azFwdDegrees + 180
   Next TravIndex
   NonangularAdjustedArray(UBound(NonangularAdjustedArray)) = NextSetupPoint
End Sub



Private Sub TranslatePointsArray(UntranslatedPointsArray As Variant)
'TRANSLATE ARRAY OF POINTS BY REFERENCE, ALTERS ORIGINAL
'ONLY APPLY IF CHECKED AND ENABLED
   If Not (TranslationCheckBox.enabled And TranslationCheckBox.value) Then
      Exit Sub
   End If

'MAKE SURE THERE IS SOMETHING A TRANSLATE
   If RawEntriesListBox.ListCount <= 0 Then
      Exit Sub
   End If

'MAKE SURE THE "FROM" POINT IS SELECTED
   If ChooseMoveObsComboBox.listIndex < 0 Then
      Exit Sub
   End If

'GET "FROM" POINT
   Dim MoveFromPoint As Point3d
   MoveFromPoint = UntranslatedPointsArray(ChooseMoveObsComboBox.listIndex)
   
'CALCULATE CHANGE
   Dim ChangeInNorth As Double
   ChangeInNorth = GetNorthing(MoveToNorthTextBox) - MoveFromPoint.Y
   Dim ChangeInEast As Double
   ChangeInEast = GetEasting(MoveToEastTextBox) - MoveFromPoint.X

'ADD CHANGE TO WHOLE ARRAY
   Dim loopIndex As Long
   For loopIndex = LBound(UntranslatedPointsArray) To UBound(UntranslatedPointsArray)
      Dim OldPoint As Point3d
      OldPoint = UntranslatedPointsArray(loopIndex)
      Dim NewPoint As Point3d
      NewPoint.Y = OldPoint.Y + ChangeInNorth
      NewPoint.X = OldPoint.X + ChangeInEast
      UntranslatedPointsArray(loopIndex) = NewPoint
   Next loopIndex
End Sub



Private Sub RotateThePointsArray(ThePointsArray As Variant)
   If Not (RotationCheckBox.value And TranslationCheckBox.value) Then
      Exit Sub
   End If

'GET ROTATION ANGLE
   Dim RotationInDegrees As Double
   If Not AngleStringToDegree(RotationTextBox.text, RotationInDegrees) Then
      Exit Sub
   End If
   
'ROTATED ABOUT THE FIRST POINT IN THE ARRAY
   Dim ArrayIndex As Long
   Dim lowerBound As Long
   lowerBound = LBound(ThePointsArray)
   For ArrayIndex = lowerBound To UBound(ThePointsArray)
      If ArrayIndex = lowerBound Then
         Dim FirstSetup As Point3d
         FirstSetup = ThePointsArray(ArrayIndex)
      Else
         Dim OriginalSide As Point3d
         OriginalSide = ThePointsArray(ArrayIndex)
         Dim OrigAzInDegrees As Double
         Dim OrigDist As Double
         Inverse FirstSetup, OriginalSide, OrigAzInDegrees, OrigDist
         Dim NewAzimuth As Double
         NewAzimuth = OrigAzInDegrees + RotationInDegrees
         ThePointsArray(ArrayIndex) = CoordFwdSAz(FirstSetup, NewAzimuth, OrigDist)
      End If
   Next ArrayIndex
End Sub



Private Sub TransformPointsArray(UntransformedPointsArray As Variant)
   RotateThePointsArray UntransformedPointsArray
   TranslatePointsArray UntransformedPointsArray
End Sub



'++++++++++++++REMOVING PREVIOUS GRAPHIC ELEMENTS++++++++++++++
Private Sub DeletePreviousElements(ByVal TraverseIDString As String)
'REMOVE PREVIOUS STATION TEXT ELEMENT FOR THIS STATION AND ELEMENT
'SCAN FILE FOR TEXT ELEMENTS
   Dim myFilter As New ElementScanCriteria
   myFilter.ExcludeAllTypes
   myFilter.IncludeType msdElementTypeLine
   myFilter.IncludeType msdElementTypeLineString
   myFilter.IncludeType msdElementTypeCellHeader
   myFilter.IncludeType msdElementTypeText
   myFilter.IncludeType msdElementTypeEllipse
   Dim myElemEnum As ElementEnumerator
   Set myElemEnum = Application.ActiveModelReference.Scan(myFilter)
   
'CYCLE THROUGH FOUND ELEMENTS, EXAMINE ONE WITH TAGS
   While myElemEnum.MoveNext
      Dim TheElem As Element
      Set TheElem = myElemEnum.Current
      If TheElem.HasAnyTags Then
         DeleteIfPreviousElement TheElem, TraverseIDString
      End If
   Wend
End Sub



Private Sub DeleteIfPreviousElement(ByVal TheElem As Element, TraverseIDString As String)
'CHECK FOR THE CORRECT TRAVERSE FILE ID TAG
   Dim TheTagVal As String
   If Not CheckForSurveyorToolsTagAndVal(TheElem, TAG_NAME_COMPASS_RULE_2D_ID, TheTagVal) Then
      Exit Sub
   End If
   If TraverseIDString <> TheTagVal Then
      Exit Sub
   End If

'CHECK FOR THE CORRECT ELEMENT ID TAG
   If Not CheckForSurveyorToolsTagAndVal(TheElem, TAG_NAME_MY_ID, TheTagVal) Then
      Exit Sub
   End If
   Dim CurrentElementIdString As String
   CurrentElementIdString = DLongToString(TheElem.ID)
   If CurrentElementIdString <> TheTagVal Then
      Exit Sub
   End If

'IT'S CORRECT, REMOVE PREVIOUS ELEMENT
   ActiveModelReference.RemoveElement TheElem
End Sub



'++++++++++++++INITIALIZING FOR NEW FILE++++++++++++++
Public Sub InitNewCRForm()
'INITIALIZE FLAG
   Me.FileLoaded = False

'INITIALIZE STARTING POINT
   TextNorthing.text = INITIAL_COORD_VAL
   TextNorthingUpdate
   TextEasting.text = INITIAL_COORD_VAL
   TextEastingUpdate
   TextElevation.text = INITIAL_COORD_VAL
   TextElevationUpdate

'INITALIZE MOVE TO POINT
   MoveToNorthTextBox.text = INITIAL_COORD_VAL
   MoveToNorthTextBoxSub
   MoveToEastTextBox.text = INITIAL_COORD_VAL
   MoveToEastTextBoxSub

'INITALIZE TWO POINT POINT
   TwoPtNorthTextBox.text = INITIAL_COORD_VAL
   TwoPtNorthTextBoxSub
   TwoPtEastTextBox.text = INITIAL_COORD_VAL
   TwoPtEastTextBoxSub

'INITALIZE BACK SIGHT AZIMUTH TEXTBOX
   FirstBSAzTextBox.text = DefaultAzString()
   FirstBSAzTextBoxSub

'SET LAST FORESIGHT OPTION
   LastForesightOption.value = True

'UNCHECK NAME AND DESCRIPTION
   NameAndDescCheckBox.value = False
   
'CLEAR OUT NAME AND DESCRIPTION FIELDS
   CloseNameTextBox.text = "Trav-1"
   CloseDescTextBox.text = ""

'INITIALIZE CLOSING POINT
   CloseNorthTextBox.text = INITIAL_COORD_VAL
   CloseNorthTextBoxSub
   CloseEastTextBox.text = INITIAL_COORD_VAL
   CloseEastTextBoxSub

'INITIALIZE COMPASS RULE STATUS
   CompassRuleStatusLabel.Caption = NOT_APPLICABLE_STRING

'SET CLOSURE TYPE TO NONE
   Me.NoneYetOption.value = True

'UNCHECK APPLY COMPASS RULE ADJUSTMENT
   ApplyAdjustmentCheckBox.value = False

'UNCHECK APPLY COMPASS RULE ADJUSTMENT
   ApplyAdjustmentCheckBox.value = False

'UNCHECK ANGULAR ADJUSTMENT BOX
   AngularAdjustmentCheckBox.value = False

'INITIALIZE ANGULAR ADJUSTMENT TEXT BOX
   AngularAdjustmentTextBox.text = DefaultAzString()

'INITIALIZE DROP DIAGRAM AZIMUTH TEXT BOX
   DropAzimuthTextBox.text = DefaultAzString()
   DropAzimuthTextBoxSub

'START OFF AS PRELIMINARY
   PreliminaryOption.value = True
   PhaseColor

'UNCHECK ROTATION CHECK BOX
   RotationCheckBox.value = False

'INITIALIZE ROTATION
   RotationTextBox.text = DefaultAzString()
   RotationTextBoxSub

'CHOOSE SINGLE POINT ADJUSTMENT OPTION
   SingleCompassRuleOption.value = True

'UNCHECK MOVE ALL BOX
   TranslationCheckBox.value = False

'SET SOLUTION RULES TO RERUN COURSES AT PRECISION
   HoldingCoursesOption.value = True

'SET PRECISION TO 1 SECOND AND 0.01'
   SecondOption.value = True
   HundredthOption.value = True

'CLEAR OUT FIELDS
   DateTextBox.text = ""
   ProjectTextBox.text = ""
   OriginTextBox.text = ""
   AzimuthTextBox.text = ""
   FieldBookTextBox.text = ""
   NotesTextBox.text = ""

'STO TAB DATA
   StoAdjTab PreliminaryAdj
   StoAdjTab FinalAdj

'FLAG THAT ON PRELIMINARY ADJUSTMENT
   WasPreliminary = True
End Sub



'**************************************************************************************
'////////////////////////////INTERFACE WITH EXTERNAL USERFORMS\\\\\\\\\\\\\\\\\\\\\\\\\
'**************************************************************************************
Public Sub AtSetupPoint(ByRef SetupPoint As Point3d, ByRef BSSAzDegrees As Double, ByRef SetupName As String)
   If TraversesListBox.ListCount > 0 Then
'RECALL THE SELECTED TRAVERSE POINT
      Dim refNum As Long
      Dim PreviousRefNum As Long
      Dim pointName As String
      Dim bSString As String
      Dim fSString As String
      Dim hDString As String
      Dim descriptionString As String
      GetTravListLine TraversesListBox.listIndex, refNum, pointName, bSString, fSString, hDString, descriptionString
      SetupName = pointName

'CALC THE RAW
      Dim ThePointsArray As Variant
      ThePointsArray = CalcRaw(False, Nothing)

'APPLY APPROPRIATE ADJUSTMENTS
'COMPASS RULE
      CompassRulePointsArray ThePointsArray

'COORDINATE TRANSFORMATION IF NY
      TransformPointsArray ThePointsArray
      Dim AtPoint As Point3d
      AtPoint = ThePointsArray(refNum)
'CALCULATE THE BACKSIGHT AZIMUTH IN DEGREES
      If TraversesListBox.listIndex > 0 Then
         GetTravListLine (TraversesListBox.listIndex - 1), refNum, pointName, bSString, fSString, hDString, descriptionString
         Dim BackAzDegrees As Double
         Dim distance As Double
         Dim BackPoint As Point3d
         BackPoint = ThePointsArray(refNum)
         Inverse AtPoint, BackPoint, BackAzDegrees, distance
      Else
         Dim origPrec As Long
         Dim dirType As Integer
         Dim quad As Integer
         If DirStringToSAz(FirstBSAzTextBox.text, BackAzDegrees, origPrec, dirType, quad) Then
            If RotationCheckBox.value Then
               Dim rotationDegrees As Double
               If Not AngleStringToDegree(RotationTextBox.text, rotationDegrees) Then
                  rotationDegrees = 0#
               End If
               BackAzDegrees = BackAzDegrees + rotationDegrees
            End If
         Else
            BackAzDegrees = 0#
         End If
      End If
   Else
      AtPoint.X = 0    'DEFAULT
      AtPoint.Y = 0    'DEFAULT
      AtPoint.z = 0    'DEFAULT
      BSSAzDegrees = 0  'DEFAULT
   End If
   SetupPoint = AtPoint
   BSSAzDegrees = BackAzDegrees
End Sub






Private Function MakeTravElString(plotElev As Boolean, elevString As String) As String
   If plotElev Then
      MakeTravElString = PLOT_EL_TRUE & elevString
   Else
      MakeTravElString = PLOT_EL_FALSE & elevString
   End If
End Function



Public Sub InsertTraverse(ByVal pointName As String, _
                          ByVal description As String, _
                          ByVal BSAngle As String, _
                          ByVal FSAngle As String, _
                          ByVal HD As String, _
                          ByVal elevationString As String, _
                          ByVal plotElev As Boolean)
'CALL THIS SUBROUTINE FROM FrmEnterTrav

'CHECK THERE ARE ANY ENTRIES IN THE INDEX
   If TraversesListBox.ListCount <= 0 Then
'FIRST ENTRY, START REF# OFF AT ZERO
      Dim refNum As Long
      refNum = 0
   Else
'NOT FIRST ENTRY, GET SELECTED ENTRY REF#
      Dim selectedRefNum As Long
      selectedRefNum = TraversesListBox.List(TraversesListBox.listIndex, TRAV_COLUMN_REF_NUM)
'SCAN FOR NEXT TRAVERSE RAW LIST INSERTION PLACE
      refNum = GetNextTraverseRawIndex(selectedRefNum + 1)
   End If

'GET INDEX FROM CHOOSE COMBO BOXES
   Dim twoPointIndex As Long
   twoPointIndex = ChooseTwoPtObsComboBox.listIndex
   Dim twoPointRefNum As Long
   twoPointRefNum = TwoPtObsComboRefNum()
   Dim moveToIndex As Long
   moveToIndex = ChooseMoveObsComboBox.listIndex

   Dim hiddenTab As AdjTabData
   hiddenTab = GetHiddenTabData()
   
   Dim twoPointRefNum2 As Long
   twoPointRefNum2 = GetTwoPtObsComboRefNum(hiddenTab.TwoPathObsIndex)

'CREATE NEW ROW
   Dim selectedIndex As Long
   selectedIndex = TraversesListBox.listIndex + 1
   NewTravListRow selectedIndex

'FILL IN THE NEW ROW
   FillTravListIndex selectedIndex, refNum, pointName, BSAngle, FSAngle, HD, description

'MOVE SELECTOR TO NEW ROW
   TraversesListBox.listIndex = selectedIndex

'CREATE NEW ROW IN RAW ENTRIES
   NewRawListRow refNum

'ADD IT TO THE RAW ENTRIES LIST BOX
   FillRawListIndex refNum, _
                    KEY_COMPASS_RULE_TRAV, _
                    pointName, _
                    BSAngle, _
                    FSAngle, _
                    HD, _
                    description, _
                    False, _
                    MakeTravElString(plotElev, elevationString)

'UPDATE REF# FOR REST OF TRAVERSES LIST BOX
   UpdateTraversesRefNums selectedIndex + 1, 1

'UPDATE SIDE SHOTS WINDOW
   InitSideShotListbox

'UPDATE CHOOSE COMBO BOXES
   fillMoveAllObsCombo
   If moveToIndex >= refNum Then
      ChooseMoveObsComboBox.listIndex = moveToIndex + 1
   Else
      ChooseMoveObsComboBox.listIndex = moveToIndex
   End If
   fillTwoPtObsCombo
   If twoPointRefNum >= refNum Then
      ChooseTwoPtObsComboBox.listIndex = twoPointIndex + 1
   Else
      ChooseTwoPtObsComboBox.listIndex = twoPointIndex
   End If

   If hiddenTab.TranslationIndex >= refNum Then
      hiddenTab.TranslationIndex = hiddenTab.TranslationIndex + 1
   End If

   If twoPointRefNum2 >= refNum Then
      hiddenTab.TwoPathObsIndex = twoPointIndex + 1
   End If

   SetHiddenTabData hiddenTab

'UPDATE BUTTON STATES
   TravEditDeleteStates
   ApplyStates

'REWRITE, REDRAW
   RewriteRedrawCompassRuleFile
End Sub



Public Sub EditTraverse(ByVal pointName As String, _
                        ByVal description As String, _
                        ByVal BSAngle As String, _
                        ByVal FSAngle As String, _
                        ByVal HD As String, _
                        ByVal elevationString As String, _
                        ByVal plotElev As Boolean)
'CALL THIS SUBROUTINE FROM FrmEnterTrav

'GET THE CURRENT REF#
   Dim refNum As Long
   refNum = TraversesListBox.List(TraversesListBox.listIndex, TRAV_COLUMN_REF_NUM)

'REVISE THE TRAVERSES LIST BOX
   FillTravListIndex TraversesListBox.listIndex, refNum, pointName, BSAngle, FSAngle, HD, description

'REVISE THE RAW ENTRIES LIST BOX
   FillRawListIndex refNum, _
                    KEY_COMPASS_RULE_TRAV, _
                    pointName, _
                    BSAngle, _
                    FSAngle, _
                    HD, _
                    description, _
                    False, _
                    MakeTravElString(plotElev, elevationString)

'REWRITE, REDRAW
   RewriteRedrawCompassRuleFile

'UPDATE CHOOSE COMBO BOXES
   ReLoadChooseboxes
End Sub



Public Sub InsertSideShot(ByVal pointName As String, _
                          ByVal description As String, _
                          ByVal BSAngle As String, _
                          ByVal FSAngle As String, _
                          ByVal HD As String, _
                          ByVal showDrop As Boolean, _
                          ByVal RecordNorth As String, _
                          ByVal RecordEast As String, _
                          ByVal DiagramNorth As String, _
                          ByVal DiagramEast As String)
'CALL THIS SUBROUTINE FROM FrmEnterSide

'SUBROUTING FOR BATCH PROCESSING
   insertSideSub pointName, _
                 description, _
                 BSAngle, _
                 FSAngle, _
                 HD, _
                 showDrop, _
                 RecordNorth, _
                 RecordEast, _
                 DiagramNorth, _
                 DiagramEast
'UPDATE THINGS
   insertSideUpdateSub
End Sub



Public Sub insertSideUpdateSub()
'UPDATE BUTTON STATES
   SideEditDeleteStates
   
'REWRITE, REDRAW
   RewriteRedrawCompassRuleFile
End Sub



Public Sub insertSideSub(ByVal pointName As String, _
                         ByVal description As String, _
                         ByVal BSAngle As String, _
                         ByVal FSAngle As String, _
                         ByVal HD As String, _
                         ByVal showDrop As Boolean, _
                         ByVal RecordNorth As String, _
                         ByVal RecordEast As String, _
                         ByVal DiagramNorth As String, _
                         ByVal DiagramEast As String)
'CHECK IF SETUP EXISTS
   If TraversesListBox.ListCount < 1 Then
      Exit Sub
   End If

'GET INDEX FROM CHOOSE COMBO BOXES
   Dim twoPointIndex As Long
   twoPointIndex = ChooseTwoPtObsComboBox.listIndex
   Dim twoPointRefNum As Long
   twoPointRefNum = TwoPtObsComboRefNum()
   Dim moveToIndex As Long
   moveToIndex = ChooseMoveObsComboBox.listIndex
   
   Dim hiddenTab As AdjTabData
   hiddenTab = GetHiddenTabData()
   
   Dim twoPointRefNum2 As Long
   twoPointRefNum2 = GetTwoPtObsComboRefNum(hiddenTab.TwoPathObsIndex)

'IF NOTHING IN SIDE SHOT LIST BOX
   If SideshotsListBox.listIndex < 0 Then
'FIRST ENTRY, START SIDE SHOT INDEX OFF AT ZERO
      Dim SideIndex As Long
      SideIndex = 0
'GET REF# FROM TRAVERSE, INCREMENT IT
      Dim refNum As Long
      refNum = TraversesListBox.List(TraversesListBox.listIndex, TRAV_COLUMN_REF_NUM) + 1
   Else
'NOT FIRST SIDE SHOT, USE NEXT AFTER SELECTED
      SideIndex = SideshotsListBox.listIndex + 1
'GET REF# FROM SELECTED SIDE SHOT, INCREMENT IT
      refNum = SideshotsListBox.List(SideshotsListBox.listIndex, SIDE_COLUMN_REF_NUM) + 1
   End If

'CREATE NEW ROW
   NewSideShotListRow SideIndex

'FILL IN THE NEW ROW
   FillSideShotListIndex SideIndex, refNum, pointName, BSAngle, FSAngle, HD, description, showDrop

'MOVE SELECTOR TO NEW ROW
   SideshotsListBox.listIndex = SideIndex

'CREATE NEW ROW IN RAW ENTRIES
   NewRawListRow refNum

'ADD IT TO THE RAW ENTRIES LIST BOX
   FillRawListIndex refNum, KEY_COMPASS_RULE_SIDE_SHOT, pointName, BSAngle, FSAngle, HD, description, showDrop, ""
   FillDropsListIndex refNum, RecordNorth, RecordEast, DiagramNorth, DiagramEast

'UPDATE REF# FOR REST OF TRAVERSES LIST BOX
   UpdateTraversesRefNums TraversesListBox.listIndex + 1, 1

'UPDATE REF# FOR REST OF SIDE SHOTS LIST BOX
   UpdateSideShotRefNums SideIndex + 1, 1

'UPDATE CHOOSE COMBOBOXES
   fillMoveAllObsCombo
   If moveToIndex >= refNum Then
      ChooseMoveObsComboBox.listIndex = moveToIndex + 1
   Else
      ChooseMoveObsComboBox.listIndex = moveToIndex
   End If
   fillTwoPtObsCombo
   
   Dim TwoPointComboBeginIndex As Long
   TwoPointComboBeginIndex = GetTwoPtObsComboRefNum(0)
   If (twoPointRefNum >= refNum) And (TwoPointComboBeginIndex < refNum) Then
      ChooseTwoPtObsComboBox.listIndex = twoPointIndex + 1
   Else
      ChooseTwoPtObsComboBox.listIndex = twoPointIndex
   End If

   If hiddenTab.TranslationIndex >= refNum Then
      hiddenTab.TranslationIndex = hiddenTab.TranslationIndex + 1
   End If
   
   If (twoPointRefNum2 >= refNum) And (TwoPointComboBeginIndex < refNum) Then
      hiddenTab.TwoPathObsIndex = hiddenTab.TwoPathObsIndex + 1
   End If
   
   SetHiddenTabData hiddenTab
End Sub



Public Sub EditSideShot(ByVal pointName As String, _
                        ByVal description As String, _
                        ByVal BSAngle As String, _
                        ByVal FSAngle As String, _
                        ByVal HD As String, _
                        ByVal showDrop As Boolean, _
                        ByVal RecordNorth As String, _
                        ByVal RecordEast As String, _
                        ByVal DiagramNorth As String, _
                        ByVal DiagramEast As String)
'CALL THIS SUBROUTINE FROM FrmEnterSide

'GET THE CURRENT REF#
   Dim refNum As Long
   refNum = SideshotsListBox.List(SideshotsListBox.listIndex, SIDE_COLUMN_REF_NUM)

'REVISE THE TRAVERSES LIST BOX
   FillSideShotListIndex SideshotsListBox.listIndex, refNum, pointName, BSAngle, FSAngle, HD, description, showDrop

'REVISE THE RAW ENTRIES LIST BOX
   FillRawListIndex refNum, KEY_COMPASS_RULE_SIDE_SHOT, pointName, BSAngle, FSAngle, HD, description, showDrop, ""
   FillDropsListIndex refNum, RecordNorth, RecordEast, DiagramNorth, DiagramEast

'REWRITE, REDRAW
   RewriteRedrawCompassRuleFile

'UPDATE CHOOSE COMBO BOXES
   ReLoadChooseboxes
End Sub






'**************************************************************************************
'/////////////////////////////////////ENTRY TAB\\\\\\\\\\\\\\\\\\\\\\\\\\\\\\\\\\\\\\\\
'**************************************************************************************
'---BEGIN FILE FRAME---
'NEW BUTTON
Private Sub NewButton_Click()
'CREATE NEW COMPASS RULE FILE
'MAKE MODAL
   Me.enabled = False

'CREATE NEW FILE
   Dim TheNewFileName As String
   If NewCompassRuleFile(TheNewFileName, Me) Then
'SAVE FILENAME FOR WRITING TO
      Me.CurrentFile = TheNewFileName

'INITIALIZE FIELDS
      InitNewCRForm

'IF NEW FILE IS CREATED, LOAD IT
      Me.FileLoaded = LoadCompassRuleFile(TheNewFileName, Me)
      If Not Me.FileLoaded Then
         MsgBox "Problem with file"
      End If
      
'INITIALIZE THE TRAVERSE WINDOW
      InitTravListbox

'WRITE THE FILE
      RewriteRedrawCompassRuleFile
   End If

'UPDATE STATES
   AllButtonStates

'UPDATE THE CAPTION
   UpdateCaption

'MAKE UNMODAL
   Me.enabled = True
End Sub



'OPEN BUTTON
Private Sub OpenButton_Click()
'OPEN COMPASS RULE FILE
'MAKE MODAL
   Me.enabled = False

'OPEN FILE
   Dim TheNewFileName As String
   If OpenCompassRuleFile(TheNewFileName) Then
'SAVE FILENAME FOR WRITING TO
      Me.CurrentFile = TheNewFileName

'MARK FILE AS NOT LOADED
      Me.FileLoaded = False

'IF FILE CHOSEN, LOAD IT
      Me.FileLoaded = LoadCompassRuleFile(TheNewFileName, Me)
      If Not Me.FileLoaded Then
         MsgBox "Problem with file"
      End If

'INITIALIZE THE SIDE SHOT WINDOW
      InitSideShotListbox

'UPDATE STATES
      AllButtonStates

'UPDATE THE CAPTION
      UpdateCaption
      
'UPDATE STATISTICS PANE
      UpdateStats

'GET RID OF OLD INFO
      ClearAverageDrop
   End If

'MAKE UNMODAL
   Me.enabled = True
End Sub



'COPY TO NEW BUTTON
Private Sub CopyNewButton_Click()
'MAKE MODAL
   Me.enabled = False

'DO THE COPY THING
   CopyToCompassRuleFile Me

'MAKE UNMODAL
   Me.enabled = True
End Sub

'---END FILE FRAME---



'REDRAW BUTTON
Private Sub RedrawButton_Click()
   RedrawCompassRuleFile
End Sub

'STARTING POINT FRAME
'DRAW SYMBOL AND LABEL CHECKBOX
Private Sub DrawStartCheckBox_Click()
   RewriteRedrawCompassRuleFile
End Sub


'==============RAW ENTRIES TEXT BOX==============
Public Sub GetRawListLine(ByVal index As Long, _
                          ByRef shotType As String, _
                          ByRef pointName As String, _
                          ByRef bSString As String, _
                          ByRef fSString As String, _
                          ByRef hDString As String, _
                          ByRef descriptionString As String, _
                          ByRef showDrop As Boolean, _
                          ByRef elevationString As String)
   shotType = RawEntriesListBox.List(index, RAW_COLUMN_ENTRY_TYPE) 'GET THE TYPE OF SHOT
   pointName = RawEntriesListBox.List(index, RAW_COLUMN_POINT_NAME) 'GET THE POINT NAME
   bSString = RawEntriesListBox.List(index, RAW_COLUMN_BACK_SIGHT) 'GET THE BACKSIGHT ANGLE STRING
   fSString = RawEntriesListBox.List(index, RAW_COLUMN_FORE_SIGHT) 'GET THE FORESIGHT ANGLE STRING
   hDString = RawEntriesListBox.List(index, RAW_COLUMN_HD) 'GET THE HORIZONTAL DISTANCE STRING
   descriptionString = RawEntriesListBox.List(index, RAW_COLUMN_DESCRIPTION) 'GET THE DESCRIPTION

'ELEVATION FIELD IF IT'S A TRAVERSE
   If shotType = KEY_COMPASS_RULE_TRAV Then
      elevationString = RawEntriesListBox.List(index, RAW_COLUMN_ELEVATION)
   End If

'SHOW DROP FIELD IF IT'S A SIDE SHOT
   If shotType = KEY_COMPASS_RULE_SIDE_SHOT Then
      Dim ShowDropIndicator As String
      ShowDropIndicator = RawEntriesListBox.List(index, RAW_COLUMN_SHOW_DROP)
      If ShowDropIndicator = SHOW_DROP_INDICATOR Then
         showDrop = True
      Else
         showDrop = False
      End If
   End If
End Sub



Public Sub GetDropsListLine(ByVal index As Long, _
                            ByRef RecordNorth As String, _
                            ByRef RecordEast As String, _
                            ByRef DiagramNorth As String, _
                            ByRef DiagramEast As String)

   RecordNorth = DropsListBox.List(index, DROPS_COLUMN_RECORD_NORTH)
   RecordEast = DropsListBox.List(index, DROPS_COLUMN_RECORD_EAST)
   DiagramNorth = DropsListBox.List(index, DROPS_COLUMN_DIAGRAM_NORTH)
   DiagramEast = DropsListBox.List(index, DROPS_COLUMN_DIAGRAM_EAST)
End Sub
                            
                            
                            
Public Function RawListTopIndex() As Long
'USE THIS TO FIND TOP INDEX BECAUSE .TOP DOES NOT ALWAYS WORK
   RawListTopIndex = RawEntriesListBox.ListCount - 1
End Function



Public Sub NewRawListRow(TheIndex As Long)
'ADD THE ROW
   RawEntriesListBox.AddItem "", TheIndex
   DropsListBox.AddItem "", TheIndex
End Sub



Public Sub FillRawListIndex(ByVal TheIndex As Long, _
                            ByVal shotType As String, _
                            ByVal pointName As String, _
                            ByVal BSAngleString As String, _
                            ByVal FSAngleString As String, _
                            ByVal hDString As String, _
                            ByVal description As String, _
                            Optional ByVal showDrop As Boolean = True, _
                            Optional ByVal elevation As String = "0.00")
   RawEntriesListBox.List(TheIndex, RAW_COLUMN_ENTRY_TYPE) = shotType
   RawEntriesListBox.List(TheIndex, RAW_COLUMN_POINT_NAME) = pointName
   RawEntriesListBox.List(TheIndex, RAW_COLUMN_BACK_SIGHT) = BSAngleString
   RawEntriesListBox.List(TheIndex, RAW_COLUMN_FORE_SIGHT) = FSAngleString
   RawEntriesListBox.List(TheIndex, RAW_COLUMN_HD) = hDString
   RawEntriesListBox.List(TheIndex, RAW_COLUMN_DESCRIPTION) = description
   If shotType = KEY_COMPASS_RULE_TRAV Then
      RawEntriesListBox.List(TheIndex, RAW_COLUMN_ELEVATION) = elevation
   Else
      Dim Indicator As String
      If showDrop Then
         Indicator = SHOW_DROP_INDICATOR
      Else
         Indicator = STRING_SPACE
      End If
      RawEntriesListBox.List(TheIndex, RAW_COLUMN_SHOW_DROP) = Indicator
   End If
End Sub



Public Sub FillDropsListIndex(ByVal TheIndex As Long, _
                              ByVal RecordNorth As String, _
                              ByVal RecordEast As String, _
                              ByVal DiagramNorth As String, _
                              ByVal DiagramEast As String)
   DropsListBox.List(TheIndex, DROPS_COLUMN_RECORD_NORTH) = RecordNorth
   DropsListBox.List(TheIndex, DROPS_COLUMN_RECORD_EAST) = RecordEast
   DropsListBox.List(TheIndex, DROPS_COLUMN_DIAGRAM_NORTH) = DiagramNorth
   DropsListBox.List(TheIndex, DROPS_COLUMN_DIAGRAM_EAST) = DiagramEast
End Sub



Private Function GetNextTraverseRawIndex(ByVal fromIndex As Long) As Long
   Dim index As Long
   index = fromIndex
   Dim EndIndex As Long
   EndIndex = RawEntriesListBox.ListCount - 1
   
   If index > EndIndex Then
      GetNextTraverseRawIndex = index
      Exit Function
   End If

   Do While index <= EndIndex
      Dim shotType As String
      shotType = RawEntriesListBox.List(index, RAW_COLUMN_ENTRY_TYPE)
      If shotType = KEY_COMPASS_RULE_TRAV Then
         GetNextTraverseRawIndex = index
         Exit Function
      End If
      index = index + 1
   Loop
   GetNextTraverseRawIndex = index
End Function



'==============TRAVERSES LISTBOX==============
Private Sub TraversesListBox_Click()
   InitSideShotListbox
   SideEditDeleteStates
End Sub

Private Sub TraversesListBox_DblClick(ByVal Cancel As MSForms.ReturnBoolean)
   TraversesEditButton_Click
End Sub

Private Sub InitTravListboxSub()
'EMPTY THE TRAVERSES LIST BOX
   TraversesListBox.Clear
   
'GET TRAVERSE ENTRIES FROM RAW ENTRIES
'NEXT INDEX TO USE IN TRAVERSE LISTBOX
   Dim TravIndex As Long
   TravIndex = TravListTopIndex() + 1

'INITIALIZE INDEX FOR RAW ENTRIES LISTBOX
   Dim rawIndex As Long
   rawIndex = 0

'GET END FOR LOOP
   Dim TopRawIndex As Long
   TopRawIndex = RawListTopIndex()

'LOOP THROUGH RAW ENTRIES INDEX
   Do While rawIndex <= TopRawIndex
'GET LINE OF RAW ENTRY
      Dim shotType As String
      Dim pointName As String
      Dim bSString As String
      Dim fSString As String
      Dim hDString As String
      Dim descriptionString As String
      Dim showDrop As Boolean
      Dim elevationString As String
      GetRawListLine rawIndex, shotType, pointName, bSString, fSString, hDString, descriptionString, showDrop, elevationString

'CHECK IF ENTRY IS A TRAVERSE ENTRY
      If shotType = KEY_COMPASS_RULE_TRAV Then
         NewTravListRow TravIndex 'CREATE ROW FOR ENTRY, FILL IT IN
         FillTravListIndex TravIndex, rawIndex, pointName, bSString, fSString, hDString, descriptionString
         TravIndex = TravIndex + 1 'INCREMENT INDEX FOR NEXT ENTRY
      End If

'INCREMENT FOR NEXT LINE IN THE RAW ENTRIES
      rawIndex = rawIndex + 1
   Loop

'SET HIGHLIGHT TO FIRST LINE IF CAN
   If (TraversesListBox.listIndex < 0) And (TraversesListBox.ListCount > 0) Then
      TraversesListBox.listIndex = 0
      TraversesListBox.Selected(TraversesListBox.listIndex) = True
   End If
End Sub

Private Sub InitTravListbox()
'END HERE IF NO FILE LOADED
   If Not Me.FileLoaded Then
      Exit Sub
   End If
   
   InitTravListboxSub
End Sub

Private Sub FillTravListIndex(TheIndex As Long, _
                              LineNum As Long, _
                              pointName As String, _
                              BSAngleString As String, _
                              FSAngleString As String, _
                              hDString As String, _
                              description As String)
   TraversesListBox.List(TheIndex, TRAV_COLUMN_REF_NUM) = LineNum
   TraversesListBox.List(TheIndex, TRAV_COLUMN_POINT_NAME) = pointName
   TraversesListBox.List(TheIndex, TRAV_COLUMN_BACK_SIGHT) = BSAngleString
   TraversesListBox.List(TheIndex, TRAV_COLUMN_FORE_SIGHT) = FSAngleString
   TraversesListBox.List(TheIndex, TRAV_COLUMN_HD) = hDString
   TraversesListBox.List(TheIndex, TRAV_COLUMN_DESCRIPTION) = description
End Sub

Private Sub GetTravListLine(ByVal TheIndex As Long, _
                            ByRef refNum As Long, _
                            ByRef pointName As String, _
                            ByRef bSString As String, _
                            ByRef fSString As String, _
                            ByRef hDString As String, _
                            ByRef descriptionString As String)
   refNum = TraversesListBox.List(TheIndex, TRAV_COLUMN_REF_NUM)
   pointName = TraversesListBox.List(TheIndex, TRAV_COLUMN_POINT_NAME)
   bSString = TraversesListBox.List(TheIndex, TRAV_COLUMN_BACK_SIGHT)
   fSString = TraversesListBox.List(TheIndex, TRAV_COLUMN_FORE_SIGHT)
   hDString = TraversesListBox.List(TheIndex, TRAV_COLUMN_HD)
   descriptionString = TraversesListBox.List(TheIndex, TRAV_COLUMN_DESCRIPTION)
End Sub

Private Function TravListTopIndex() As Long
'USE THIS TO FIND TOP INDEX BECAUSE .TOP DOES NOT ALWAYS WORK
   TravListTopIndex = TraversesListBox.ListCount - 1
End Function


Private Sub NewTravListRow(TheIndex As Long)
'ADD THE ROW
   TraversesListBox.AddItem "", TheIndex
End Sub

Private Sub UpdateTraversesRefNums(ByVal StartingIndex As Long, ByVal ValueToAdd As Long)
'INITALIZE START AND END INDEX
   Dim index As Long
   index = StartingIndex
   Dim EndIndex As Long
   EndIndex = TraversesListBox.ListCount - 1

'LOOP UNTIL END OF LIST
   Do While index <= EndIndex
'ADD TO THE REF#
      TraversesListBox.List(index, TRAV_COLUMN_REF_NUM) = TraversesListBox.List(index, TRAV_COLUMN_REF_NUM) + ValueToAdd
'INCREMENT INDEX
      index = index + 1
   Loop
End Sub



'---BEGIN STARTING POINT FRAME---
'FIRST BS AZIMUTH TEXTBOX
Private Sub FirstBSAzTextBox_AfterUpdate()
   FirstBSAzTextBoxSub
   RewriteRedrawCompassRuleFile
End Sub

Public Sub FirstBSAzTextBoxSub()
   BackupAzTextBox FirstBSAzTextBox, OldStartAzimuth
End Sub

Private Sub BackupAzTextBox(theTextbox As TextBox, theVariable As String)
   Dim origPrec As Long
   Dim degPart As Long
   Dim minPart As Long
   Dim secPart As Double
   If IsDeltaString(theTextbox.text, origPrec, degPart, minPart, secPart) Then
      theTextbox.text = DirString(degPart, minPart, secPart, origPrec, DIR_TYPE_AZIMUTH, GetAngleStyle())
      theVariable = theTextbox.text
   Else
      theTextbox.text = theVariable
      Beep
   End If
End Sub

Private Sub FirstBSAzTextBox_Enter()
   SelectAllText FirstBSAzTextBox
End Sub



'Z TEXTBOX
Private Sub TextElevation_AfterUpdate()
   TextElevationUpdate
   RewriteRedrawCompassRuleFile
End Sub

Public Sub TextElevationUpdate()
   SaveElevationEntry TextElevation, SECTION_COMPASS_RULE_2D, KEY_START_POINT_Z, START_COORD_PREC
End Sub

Private Sub TextElevation_Enter()
   SelectAllText TextElevation
End Sub



'PICK Z BUTTON
Private Sub PickZButton_Click()
   FrmCompassRule.Hide
   Dim ThePickedPoint As Point3d
   If PickSub(COMMAND_NAME_COMPASS_RULE_2D, "Pick first traverse coordinate.", ThePickedPoint) Then
      TextElevation.text = FormatNumber(ThePickedPoint.z, START_COORD_PREC, vbTrue, vbFalse, vbFalse)
      TextElevation_AfterUpdate
   End If
   FrmCompassRule.Show
End Sub



'NORTHING TEXTBOX
Private Sub TextNorthing_AfterUpdate()
   TextNorthingUpdate
   RewriteRedrawCompassRuleFile
End Sub

Public Sub TextNorthingUpdate()
   NorthingFieldSub TextNorthing, OldStartingNorthing
End Sub

Private Function GetNorthing(theTextbox As TextBox) As Double
   Dim origPrec As Long
   If Not IsNorthingString(theTextbox.text, GetNorthing, origPrec) Then
'SHOULD NEVER GET HERE, CREATE ERROR IF IT DOES
      Err.Raise ERROR_NUM_533
   End If
End Function

Private Sub TextNorthing_Enter()
   SelectAllText TextNorthing
End Sub



'EASTING TEXTBOX
Private Sub TextEasting_AfterUpdate()
   TextEastingUpdate
   RewriteRedrawCompassRuleFile
End Sub

Public Sub TextEastingUpdate()
   EastingFieldSub TextEasting, OldStartingEasting
End Sub

Private Function GetEasting(theTextbox As TextBox) As Double
   Dim origPrec As Long
   If Not IsEastingString(theTextbox.text, GetEasting, origPrec) Then
'SHOULD NEVER GET HERE, CREATE ERROR IF IT DOES
      Err.Raise ERROR_NUM_535
   End If
End Function

Private Sub TextEasting_Enter()
   SelectAllText TextEasting
End Sub



'NORTHING EASTING PICK BUTTON
Private Sub ButtonPick_Click()
'PICK START POINT
   FrmCompassRule.Hide
   Dim ThePickedPoint As Point3d
   If PickSub(COMMAND_NAME_COMPASS_RULE_2D, "Pick first traverse coordinate.", ThePickedPoint) Then
      TextNorthing.text = FormatNumber(ThePickedPoint.Y, START_COORD_PREC, vbTrue, vbFalse, vbFalse)
      TextNorthingUpdate
      TextEasting.text = FormatNumber(ThePickedPoint.X, START_COORD_PREC, vbTrue, vbFalse, vbFalse)
      TextEastingUpdate
      RewriteRedrawCompassRuleFile
   End If
   FrmCompassRule.Show
End Sub

'---END STARTING POINT FRAME---


'---BEGIN TRAVERSES FRAME---
'TRAVERSES DELETE BUTTON
Private Sub TraversesDeleteButton_Click()
'END HERE IF NO FILE LOADED
   If Not Me.FileLoaded Then
      Exit Sub
   End If

'CHECK IF THERE IS SOMETHING SELECTED
   If TraversesListBox.listIndex >= 0 Then
      DeleteTraverse
   End If
End Sub

Private Sub DeleteTraverse()
'GET CURRENT INDEX
   Dim currentIndex As Long
   currentIndex = TraversesListBox.listIndex
   
'GET REF#
   Dim refNum As Long
   refNum = TraversesListBox.List(currentIndex, TRAV_COLUMN_REF_NUM)
   
   Dim hiddenTab As AdjTabData
   hiddenTab = GetHiddenTabData()
   
   Dim twoPointRefNum2 As Long
   twoPointRefNum2 = GetTwoPtObsComboRefNum(hiddenTab.TwoPathObsIndex)
   
   Dim MoveToIndexHidden As Long
   MoveToIndexHidden = GetTwoPtObsComboRefNum(hiddenTab.TranslationIndex)

'GET INDICES OF CHOOSE COMBO BOXES NOT HIDDEN
   Dim twoPointIndex As Long
   twoPointIndex = ChooseTwoPtObsComboBox.listIndex
   Dim twoPointRefNum As Long
   twoPointRefNum = TwoPtObsComboRefNum()
   Dim moveToIndex As Long
   moveToIndex = ChooseMoveObsComboBox.listIndex
   
'CALCULATE NEW REFNUM FOR CHOOSE COMBO BOXES
   NewRefNumSub moveToIndex, currentIndex, refNum, moveToIndex
   Dim NewHiddenMoveToIndex   As Long
   NewRefNumSub MoveToIndexHidden, currentIndex, refNum, MoveToIndexHidden
   NewRefNumSub twoPointRefNum, currentIndex, refNum, twoPointIndex
   Dim New2PtRefnum As Long
   NewRefNumSub twoPointRefNum2, currentIndex, refNum, New2PtRefnum

'DELETE SELECTED ENTRY FROM TRAVERSES LISTBOX
   TraversesListBox.RemoveItem currentIndex

'DELETE SETUP FROM RAW ENTRIES LISTBOX
   Dim NegDeletedLines As Long
   NegDeletedLines = DeleteSetupFromRaw(refNum)

'UPDATE REF#
   UpdateTraversesRefNums currentIndex, NegDeletedLines

'UPDATE SIDE SHOTS WINDOW
   InitSideShotListbox

'UPDATE CHOOSE COMBO BOXES
   fillMoveAllObsCombo
   ChooseMoveObsComboBox.listIndex = moveToIndex
   
   
   
   fillTwoPtObsCombo
   If ChooseTwoPtObsComboBox.ListCount > 0 Then
      Dim beginIndex As Long
      beginIndex = GetTwoPtObsComboRefNum(0)
      Dim EndIndex As Long
      EndIndex = beginIndex + ChooseTwoPtObsComboBox.ListCount - 1
      If (twoPointIndex < beginIndex) Or (twoPointIndex > EndIndex) Then
         ChooseTwoPtObsComboBox.listIndex = -1
      Else
         ChooseTwoPtObsComboBox.listIndex = twoPointIndex - beginIndex
      End If
   End If

   If hiddenTab.TranslationIndex > refNum Then
      hiddenTab.TranslationIndex = hiddenTab.TranslationIndex - 1
   ElseIf hiddenTab.TranslationIndex = refNum Then
      hiddenTab.TranslationIndex = -1
   End If
   
   If (beginIndex <= New2PtRefnum) Then
      hiddenTab.TwoPathObsIndex = New2PtRefnum - beginIndex
   Else
      hiddenTab.TwoPathObsIndex = -1
   End If
   SetHiddenTabData hiddenTab

'UPDATE BUTTON STATES
   TravEditDeleteStates
   ApplyStates

'REWRITE, REDRAW
   RewriteRedrawCompassRuleFile
End Sub

Private Sub NewRefNumSub(OldRefNum As Long, _
                      CurrentTravIndex As Long, _
                      RefnumOfTrav As Long, _
                      ByRef TheNewRefNum As Long)

   If OldRefNum = RefnumOfTrav Then
'DELETING THE CHOSEN ONE, SET INDEX TO NOTHING
      TheNewRefNum = -1
   ElseIf OldRefNum > RefnumOfTrav Then
'DELETING BEFORE CHOSEN ONE
      If (TraversesListBox.ListCount - 1) > CurrentTravIndex Then
'LOOK FOR NEXT
         Dim refNum As Long
         refNum = TraversesListBox.List(CurrentTravIndex + 1, TRAV_COLUMN_REF_NUM)
         TheNewRefNum = CLng(Max(-1, OldRefNum - (refNum - RefnumOfTrav)))
      Else
'NO OTHER TRAVERSE AFTER ONE TO DELETE
         TheNewRefNum = -1
      End If
   Else
'NO CHANGE IN REF NUM
      TheNewRefNum = OldRefNum
   End If
End Sub

Private Function DeleteSetupFromRaw(ByVal refNum As Long) As Long
'RETURNS NEGATIVE NUMBER OF LINES DELETED FROM THE RAW ENTRIES LISTBOX
'DELETE LINE AT REF# INDEX
   RawEntriesListBox.RemoveItem refNum
   DropsListBox.RemoveItem refNum

'INITIALIZE COUNTER
   Dim DeletedLineCount As Long
   DeletedLineCount = 1

'LOOP UNTIL NO MORE LINES OR MEET NEXT TRAVERSE
   Do While ((RawEntriesListBox.ListCount - 1) >= refNum)
      If RawEntriesListBox.List(refNum, RAW_COLUMN_ENTRY_TYPE) = KEY_COMPASS_RULE_TRAV Then
         Exit Do
      End If
      RawEntriesListBox.RemoveItem refNum
      DropsListBox.RemoveItem refNum
      DeletedLineCount = DeletedLineCount + 1
   Loop

'RETURN NEGATIVE NUMBER OF LINES DELETED
   DeleteSetupFromRaw = -DeletedLineCount
End Function



'TRAVERSES EDIT BUTTON
Private Sub TraversesEditButton_Click()
'END HERE IF NO FILE LOADED
   If Not Me.FileLoaded Then
      Exit Sub
   End If

'FLAG THAT WE ARE EDITING AN EXISTING TRAVERSE
   InsertMode = False

'PREFILL THE BOXES FOR FrmEnterTrav
   Dim refNum As Long
   Dim pointName As String
   Dim bSString As String
   Dim fSString As String
   Dim hDString As String
   Dim descriptionString As String
   GetTravListLine TraversesListBox.listIndex, refNum, pointName, bSString, fSString, hDString, descriptionString
   SaveSetting APP_NAME, SECTION_COMPASS_RULE_2D_ENTER_TRAV, KEY_POINTNAME, pointName
   SaveSetting APP_NAME, SECTION_COMPASS_RULE_2D_ENTER_TRAV, KEY_BACK_SIGHT_ANGLE, bSString
   SaveSetting APP_NAME, SECTION_COMPASS_RULE_2D_ENTER_TRAV, KEY_FORE_SIGHT_ANGLE, fSString
   SaveSetting APP_NAME, SECTION_COMPASS_RULE_2D_ENTER_TRAV, KEY_HORIZONTAL_DISTANCE, hDString
   SaveSetting APP_NAME, SECTION_COMPASS_RULE_2D_ENTER_TRAV, KEY_POINT_DESC, descriptionString

'GET ELEVATION
   Dim shotType As String
   Dim showDrop As Boolean
   Dim elevationString As String
   GetRawListLine refNum, shotType, pointName, bSString, fSString, hDString, descriptionString, showDrop, elevationString
   SaveSetting APP_NAME, SECTION_COMPASS_RULE_2D_ENTER_TRAV, KEY_ELEVATION, elevationString

'MAKE MODAL
   Me.enabled = False

'LAUNCH THE FORM
   FrmEnterTrav.Show
End Sub



'TRAVERSES INSERT BUTTON
Private Sub TraversesAddButton_Click()
'END HERE IF NO FILE LOADED
   If Not Me.FileLoaded Then
      Exit Sub
   End If

'FLAG THAT WE ARE INSERTING A NEW TRAVERSE
   InsertMode = True

'PREFILL THE BACK SIGHT TEXT BOX IF POSSIBLE
   If TraversesListBox.listIndex >= 0 Then
'GET CURRENT FS STRING
      Dim fSString As String
      fSString = TraversesListBox.List(TraversesListBox.listIndex, TRAV_COLUMN_FORE_SIGHT)

'MAKE INTO NEW BACK SIGHT STRING
      Dim NewBSString As String
      NewBSString = fSString
      If Not ReverseDirText(NewBSString) Then
'SHOULD NEVER GET HERE, CREATE ERROR IF IT DOES
         Err.Raise ERROR_NUM_536
      End If

'STORE IT FOR FrmEnterTrav
      SaveSetting APP_NAME, SECTION_COMPASS_RULE_2D_ENTER_TRAV, KEY_BACK_SIGHT_ANGLE, NewBSString
   Else
'STORE IT FOR FrmEnterTrav
      SaveSetting APP_NAME, SECTION_COMPASS_RULE_2D_ENTER_TRAV, KEY_BACK_SIGHT_ANGLE, FirstBSAzTextBox.text
   End If

'LOCK FORM
   Me.enabled = False

'LAUNCH THE FORM
   FrmEnterTrav.Show
End Sub

'---END TRAVERSES FRAME---


'---BEGIN SIDE SHOTS FRAME---
'==============SIDE SHOTS LISTBOX==============
Private Sub SideshotsListBox_DblClick(ByVal Cancel As MSForms.ReturnBoolean)
   SideShotsEditButton_Click
End Sub

Private Sub InitSideShotListbox()
'EMPTY THE SIDE SHOTS LIST BOX
   SideshotsListBox.Clear
   
'END HERE IF NO FILE LOADED
   If Not Me.FileLoaded Then
      TravEditDeleteStates
      SideInsertStates
      Exit Sub
   End If

'END HERE IF NO TRAVERSE IS SELECTED
   If TraversesListBox.listIndex < 0 Then
      TravEditDeleteStates
      SideInsertStates
      Exit Sub
   End If

'GET REF# FROM TRAVERSE LISTBOX
   Dim TravRefNum As Long
   TravRefNum = TraversesListBox.List(TraversesListBox.listIndex, TRAV_COLUMN_REF_NUM)

'START LOOKING AT THE NEXT INDEX
   Dim rawIndex As Long
   rawIndex = TravRefNum + 1

'GET TOP INDEX FOR RAW ENTRIES LISTBOX
   Dim TopRawIndex As Long
   TopRawIndex = RawListTopIndex()

'INITIALIZE SIDE SHOTS LISTBOX INDEX
   Dim SideShotsIndex As Long
   SideShotsIndex = 0
   
'LOOP THROUGH RAW ENTRIES INDEX
   Do While rawIndex <= TopRawIndex
      'GET LINE OF RAW ENTRY
      Dim shotType As String
      Dim pointName As String
      Dim bSString As String
      Dim fSString As String
      Dim hDString As String
      Dim descriptionString As String
      Dim showDrop As Boolean
      Dim elevationString As String
'READ ONE ROW OF RAW ENTRIES LIST BOX
      GetRawListLine rawIndex, shotType, pointName, bSString, fSString, hDString, descriptionString, showDrop, elevationString
'CHECK IF ENTRY IS A SIDE SHOT ENTRY
      If shotType <> KEY_COMPASS_RULE_SIDE_SHOT Then
'END LOOP IF NOT
         Exit Do
      End If
'ADD IT TO SIDE SHOT LISTBOX
      NewSideShotListRow SideShotsIndex
      FillSideShotListIndex SideShotsIndex, rawIndex, pointName, bSString, fSString, hDString, descriptionString, showDrop

'INCREMENT INDICES
      SideShotsIndex = SideShotsIndex + 1
      rawIndex = rawIndex + 1
   Loop

'SET HIGHLIGHT TO FIRST LINE IF CAN
   If (SideshotsListBox.listIndex < 0) And (SideshotsListBox.ListCount > 0) Then
      SideshotsListBox.listIndex = 0
      SideshotsListBox.Selected(SideshotsListBox.listIndex) = True
   End If
         
'SET BUTTON STATES
   TravEditDeleteStates
   SideInsertStates
End Sub

Private Sub FillSideShotListIndex(ByVal TheIndex As Long, _
                                  ByVal LineNum As Long, _
                                  ByVal pointName As String, _
                                  ByVal BSAngleString As String, _
                                  ByVal FSAngleString As String, _
                                  ByVal hDString As String, _
                                  ByVal description As String, _
                                  ByVal showDrop As Boolean)
   SideshotsListBox.List(TheIndex, SIDE_COLUMN_REF_NUM) = LineNum
   SideshotsListBox.List(TheIndex, SIDE_COLUMN_POINT_NAME) = pointName
   SideshotsListBox.List(TheIndex, SIDE_COLUMN_BACK_SIGHT) = BSAngleString
   SideshotsListBox.List(TheIndex, SIDE_COLUMN_FORE_SIGHT) = FSAngleString
   SideshotsListBox.List(TheIndex, SIDE_COLUMN_HD) = hDString
   SideshotsListBox.List(TheIndex, SIDE_COLUMN_DESCRIPTION) = description
   SideshotsListBox.List(TheIndex, SIDE_COLUMN_SHOW_DROP) = ShowDropIndicator(showDrop)
End Sub

Private Function ShowDropIndicator(ByVal showDrop As Boolean) As String
   If showDrop Then
      ShowDropIndicator = SHOW_DROP_INDICATOR
   Else
      ShowDropIndicator = STRING_SPACE
   End If
End Function

Private Function ShowDropIndicatorToBoolean(ByVal IndicatorString As String) As Boolean
   If IndicatorString = SHOW_DROP_INDICATOR Then
      ShowDropIndicatorToBoolean = True
   Else
      ShowDropIndicatorToBoolean = False
   End If
End Function



Private Sub GetSideShotListLine(ByVal TheIndex As Long, _
                                ByRef refNum As Long, _
                                ByRef pointName As String, _
                                ByRef bSString As String, _
                                ByRef fSString As String, _
                                ByRef hDString As String, _
                                ByRef descriptionString As String, _
                                ByRef showDrop As Boolean)
   refNum = SideshotsListBox.List(TheIndex, SIDE_COLUMN_REF_NUM)
   pointName = SideshotsListBox.List(TheIndex, SIDE_COLUMN_POINT_NAME)
   bSString = SideshotsListBox.List(TheIndex, SIDE_COLUMN_BACK_SIGHT)
   fSString = SideshotsListBox.List(TheIndex, SIDE_COLUMN_FORE_SIGHT)
   hDString = SideshotsListBox.List(TheIndex, SIDE_COLUMN_HD)
   descriptionString = SideshotsListBox.List(TheIndex, SIDE_COLUMN_DESCRIPTION)
   showDrop = ShowDropIndicatorToBoolean(SideshotsListBox.List(TheIndex, SIDE_COLUMN_SHOW_DROP))
End Sub

Private Function SideShotListTopIndex() As Long
'USE THIS TO FIND TOP INDEX BECAUSE .TOP DOES NOT ALWAYS WORK
   SideShotListTopIndex = SideshotsListBox.ListCount - 1
End Function


Private Sub NewSideShotListRow(TheIndex As Long)
'ADD THE ROW
   SideshotsListBox.AddItem "", TheIndex
End Sub

Private Sub UpdateSideShotRefNums(ByVal StartingIndex As Long, ByVal ValueToAdd As Long)
'INITALIZE START AND END INDEX
   Dim index As Long
   index = StartingIndex
   Dim EndIndex As Long
   EndIndex = SideshotsListBox.ListCount - 1

'LOOP UNTIL END OF LIST
   Do While index <= EndIndex
'ADD TO THE REF#
      SideshotsListBox.List(index, SIDE_COLUMN_REF_NUM) = SideshotsListBox.List(index, SIDE_COLUMN_REF_NUM) + ValueToAdd
'INCREMENT INDEX
      index = index + 1
   Loop
End Sub





'DROP DIAGRAM AZIMUTH TEXTBOX
Private Sub DropAzimuthTextBox_AfterUpdate()
   DropAzimuthTextBoxSub
   RewriteRedrawCompassRuleFile
End Sub

Public Sub DropAzimuthTextBoxSub()
   BackupAzTextBox DropAzimuthTextBox, OldDiagramAzimuth
End Sub

Private Sub DropAzimuthTextBox_Enter()
   SelectAllText DropAzimuthTextBox
End Sub



'PLUS 180 BUTTON
Private Sub Plus180Button_Click()
   Plus180 DropAzimuthTextBox
   DropAzimuthTextBox_AfterUpdate
End Sub



'DROP DIAGRAM MARK ALL BUTTON
Private Sub MarkAllDropsButton_Click()
   AllDropMarks True
End Sub



'DROP DIAGRAM CLEAR ALL BUTTON
Private Sub UnmarkAllDropsButton_Click()
   AllDropMarks False
End Sub

Private Sub AllDropMarks(ByVal MakeMarked As Boolean)
'SAVE SIDESHOT CURRENT INDEX
   Dim SideIndex As Long
   SideIndex = SideshotsListBox.listIndex

'START RAW INDEX AT SECOND ELEMENT
   Dim rawIndex As Long
   rawIndex = 0

'CALCULATE ENDING INDEX
   Dim EndIndex As Long
   EndIndex = RawEntriesListBox.ListCount - 1

'LOOP THROUGH RAW ENTRIES
   Do While rawIndex <= EndIndex
'READ ONE LINE OF RAW ENTRIES
      Dim shotType As String
      Dim pointName As String
      Dim bSString As String
      Dim fSString As String
      Dim hDString As String
      Dim descriptionString As String
      Dim showDrop As Boolean
      Dim elevationString As String
      GetRawListLine rawIndex, shotType, pointName, bSString, fSString, hDString, descriptionString, showDrop, elevationString

      If shotType = KEY_COMPASS_RULE_SIDE_SHOT Then
         FillRawListIndex rawIndex, shotType, pointName, bSString, fSString, hDString, descriptionString, MakeMarked, ""
      End If
'INCREMENT LOOP
      rawIndex = rawIndex + 1
   Loop
   InitSideShotListbox
   If SideIndex < SideshotsListBox.ListCount Then
      SideshotsListBox.listIndex = SideIndex
   End If
   RewriteRedrawCompassRuleFile
End Sub



'SIDE SHOTS DELETE BUTTON
Private Sub SideShotsDeleteButton_Click()
'END HERE IF NO FILE LOADED
   If Not Me.FileLoaded Then
      Exit Sub
   End If

'CHECK IF THERE IS SOMETHING SELECTED
   If SideshotsListBox.listIndex >= 0 Then
      DeleteSideShot
   End If
End Sub

Private Sub DeleteSideShot()
'GET CURRENT SIDE SHOTS INDEX
   Dim currentIndex As Long
   currentIndex = SideshotsListBox.listIndex

'GET INDEX FROM CHOOSE COMBO BOXES
   Dim twoPointIndex As Long
   twoPointIndex = ChooseTwoPtObsComboBox.listIndex
   Dim twoPointRefNum As Long
   twoPointRefNum = TwoPtObsComboRefNum()
   Dim moveToIndex As Long
   moveToIndex = ChooseMoveObsComboBox.listIndex
   
'GET REF#
   Dim refNum As Long
   refNum = CLng(SideshotsListBox.List(currentIndex, SIDE_COLUMN_REF_NUM))

   Dim hiddenTab As AdjTabData
   hiddenTab = GetHiddenTabData()
   
   Dim twoPointRefNum2 As Long
   twoPointRefNum2 = GetTwoPtObsComboRefNum(hiddenTab.TwoPathObsIndex)

'DELETE SELECTED ENTRY FROM SIDE SHOTS LISTBOX
   SideshotsListBox.RemoveItem currentIndex

'DELETE SETUP FROM RAW ENTRIES LISTBOX
   RawEntriesListBox.RemoveItem refNum
   DropsListBox.RemoveItem refNum

'UPDATE REF#
   UpdateSideShotRefNums currentIndex, -1
   UpdateTraversesRefNums TraversesListBox.listIndex + 1, -1

'UPDATE CHOOSE COMBO BOXES
   fillMoveAllObsCombo
   If moveToIndex > refNum Then
      ChooseMoveObsComboBox.listIndex = moveToIndex - 1
   ElseIf moveToIndex = refNum Then
      ChooseMoveObsComboBox.listIndex = -1
   Else
      ChooseMoveObsComboBox.listIndex = moveToIndex
   End If
   
   fillTwoPtObsCombo
   Dim TwoPointComboBeginIndex As Long
   TwoPointComboBeginIndex = GetTwoPtObsComboRefNum(0)
   If (twoPointRefNum > refNum) And (TwoPointComboBeginIndex < refNum) Then
      ChooseTwoPtObsComboBox.listIndex = twoPointIndex - 1
   ElseIf twoPointRefNum = refNum Then
      ChooseTwoPtObsComboBox.listIndex = -1
   Else
      ChooseTwoPtObsComboBox.listIndex = twoPointIndex
   End If
      
   If hiddenTab.TranslationIndex > refNum Then
      hiddenTab.TranslationIndex = hiddenTab.TranslationIndex - 1
   ElseIf hiddenTab.TranslationIndex = refNum Then
      hiddenTab.TranslationIndex = -1
   End If
   If (twoPointRefNum2 > refNum) And (TwoPointComboBeginIndex < refNum) Then
      hiddenTab.TwoPathObsIndex = hiddenTab.TwoPathObsIndex - 1
   ElseIf twoPointRefNum2 = refNum Then
      hiddenTab.TwoPathObsIndex = -1
   End If

   SetHiddenTabData hiddenTab

'UPDATE BUTTON STATES
   SideEditDeleteStates

'REWRITE, REDRAW
   RewriteRedrawCompassRuleFile
End Sub



'SIDE SHOTS EDIT BUTTON
Private Sub SideShotsEditButton_Click()
'END HERE IF NO FILE LOADED
   If Not Me.FileLoaded Then
      Exit Sub
   End If

'FLAG THAT WE ARE EDITING AN EXISTING TRAVERSE
   InsertMode = False

'PREFILL THE BOXES FOR FrmEnterTrav
   Dim refNum As Long
   Dim pointName As String
   Dim bSString As String
   Dim fSString As String
   Dim hDString As String
   Dim descriptionString As String
   Dim showDrop As Boolean
   GetSideShotListLine SideshotsListBox.listIndex, refNum, pointName, bSString, fSString, hDString, descriptionString, showDrop
   SaveSetting APP_NAME, SECTION_COMPASS_RULE_2D_ENTER_SIDE, KEY_POINTNAME, pointName
   SaveSetting APP_NAME, SECTION_COMPASS_RULE_2D_ENTER_SIDE, KEY_BACK_SIGHT_ANGLE, bSString
   SaveSetting APP_NAME, SECTION_COMPASS_RULE_2D_ENTER_SIDE, KEY_FORE_SIGHT_ANGLE, fSString
   SaveSetting APP_NAME, SECTION_COMPASS_RULE_2D_ENTER_SIDE, KEY_HORIZONTAL_DISTANCE, hDString
   SaveSetting APP_NAME, SECTION_COMPASS_RULE_2D_ENTER_SIDE, KEY_POINT_DESC, descriptionString
   SaveSetting APP_NAME, SECTION_COMPASS_RULE_2D_ENTER_SIDE, KEY_SHOW_DROP, TrueFalseString(showDrop)
   Dim RecordNorth As String
   Dim RecordEast As String
   Dim DiagramNorth As String
   Dim DiagramEast As String
   GetDropsListLine refNum, RecordNorth, RecordEast, DiagramNorth, DiagramEast
   SaveSetting APP_NAME, SECTION_COMPASS_RULE_2D_ENTER_SIDE, KEY_REC_NORTH, RecordNorth
   SaveSetting APP_NAME, SECTION_COMPASS_RULE_2D_ENTER_SIDE, KEY_REC_EAST, RecordEast
   SaveSetting APP_NAME, SECTION_COMPASS_RULE_2D_ENTER_SIDE, KEY_DIAGRAM_NORTH, DiagramNorth
   SaveSetting APP_NAME, SECTION_COMPASS_RULE_2D_ENTER_SIDE, KEY_DIAGRAM_EAST, DiagramEast

'LAUNCH THE FORM
   Me.enabled = False
   FrmEnterSide.Show
End Sub



'SIDE SHOTS INSERT BUTTON
Private Sub SideShotsAddButton_Click()
'END HERE IF NO FILE LOADED
   If Not Me.FileLoaded Then
      Exit Sub
   End If

'FLAG THAT WE ARE INSERTING A NEW SIDE SHOT
   InsertMode = True

'STORE THE BACKSIGHT ANGLE
   StoBS
   
'LAUNCH THE FORM
   Me.enabled = False
   FrmEnterSide.Show
End Sub

Private Sub StoBS()
'PREFILL THE BACK SIGHT TEXT BOX
   If SideshotsListBox.listIndex > 0 Then
'NOT FIRST SIDE SHOT IN LIST BOX, BACK SIGHT FROM PREVIOUS SIDE SHOT
      Dim bSString As String
      bSString = SideshotsListBox.List(SideshotsListBox.listIndex, SIDE_COLUMN_BACK_SIGHT)
   Else
'FIRST SIDE SHOT FOR SETUP, GET BACK SIGHT FROM TRAVERSE
      bSString = TraversesListBox.List(TraversesListBox.listIndex, TRAV_COLUMN_BACK_SIGHT)
   End If
   
'STORE IT FOR FrmEnterSide
   SaveSetting APP_NAME, SECTION_COMPASS_RULE_2D_ENTER_SIDE, KEY_BACK_SIGHT_ANGLE, bSString
End Sub



'SIDE SHOTS INSERT BY FILE BUTTON
Private Sub FileInsertButton_Click()
   If Not Me.FileLoaded Then
      Exit Sub
   End If

   StoBS
'   Me.enabled = False
   FrmInsByCoord.Show
End Sub

'---END SIDE SHOTS FRAME---



'**************************************************************************************
'///////////////////////////////////CLOSURE TAB\\\\\\\\\\\\\\\\\\\\\\\\\\\\\\\\\\\\\\\\
'**************************************************************************************
'---BEGIN CLOSURE TYPE FRAME---
'FLOATING RADIO BUTTON
Private Sub NoneYetOption_Click()
   ApplyStates
   ClosureTypeSub
End Sub



'TO BEGINNING RADIO BUTTON
Private Sub ToBeginningOption_Click()
   AdjustmentsOnOff True
   ClosureTypeSub
End Sub



'TO POINT RADIO BUTTON
Private Sub ToPointOption_Click()
   AdjustmentsOnOff True
   ClosureTypeSub
End Sub



'CLOSE TO POINT NORTHING TEXTBOX
Private Sub CloseNorthTextBox_AfterUpdate()
   CloseNorthTextBoxSub
   RewriteRedrawCompassRuleFile
End Sub

Public Sub CloseNorthTextBoxSub()
   NorthingFieldSub CloseNorthTextBox, OldClosingNorthing
End Sub

Private Sub CloseNorthTextBox_Enter()
   SelectAllText CloseNorthTextBox
End Sub



'CLOSE TO POINT EASTING TEXTBOX
Private Sub CloseEastTextBox_AfterUpdate()
   CloseEastTextBoxSub
   RewriteRedrawCompassRuleFile
End Sub

Public Sub CloseEastTextBoxSub()
   EastingFieldSub CloseEastTextBox, OldClosingEasting
End Sub

Private Sub CloseEastTextBox_Enter()
   SelectAllText CloseEastTextBox
End Sub



'CLOSE TO POINT PICK BUTTON
Private Sub ClosePointPickButton_Click()
'PICK CLOSING POINT
   FrmCompassRule.Hide

   Dim ThePickedPoint As Point3d
   If PickSub(COMMAND_NAME_COMPASS_RULE_2D, "Pick Closing Point.", ThePickedPoint) Then
      SetClosingPoint ThePickedPoint
   End If

   FrmCompassRule.Show
End Sub



Private Sub SetClosingPoint(ClosingPoint As Point3d)
   CloseNorthTextBox.text = CoordinateString4Places(ClosingPoint.Y)
   CloseNorthTextBoxSub
   CloseEastTextBox.text = CoordinateString4Places(ClosingPoint.X)
   CloseEastTextBoxSub
   RewriteRedrawCompassRuleFile
End Sub



Private Sub ClosureTypeSub()
'UPDATE BUTTON STATES
   ClosureTypeStates
   ClosingPointObsStates

'UPDATE CHOOSE DROP DOWN BOXES
   Dim moveToIndex As Long
   moveToIndex = ChooseMoveObsComboBox.listIndex
   fillMoveAllObsCombo
   If ChooseMoveObsComboBox.ListCount > moveToIndex Then
      ChooseMoveObsComboBox.listIndex = moveToIndex
   Else
      ChooseMoveObsComboBox.listIndex = -1
   End If
   Dim twoPointIndex As Long
   twoPointIndex = TwoPtObsComboRefNum()
   fillTwoPtObsCombo
   If ChooseTwoPtObsComboBox.ListCount > 0 Then
      Dim beginIndex As Long
      beginIndex = GetTwoPtObsComboRefNum(0)
      Dim EndIndex As Long
      EndIndex = beginIndex + ChooseTwoPtObsComboBox.ListCount - 1
      If (twoPointIndex < beginIndex) Or (twoPointIndex > EndIndex) Then
         ChooseTwoPtObsComboBox.listIndex = -1
      Else
         ChooseTwoPtObsComboBox.listIndex = twoPointIndex - beginIndex
      End If
   End If

'REWRITE, REDRAW
   RewriteRedrawCompassRuleFile
End Sub

'---END CLOSURE TYPE FRAME---


'---BEGIN CLOSING POINT OBSERVATION FRAME---
'THE FORESIGHT FROM LAST TRAVERSE RADIO BUTTON
Private Sub LastForesightOption_Click()
   ChangeLastObsSub
   ClosingPointObSub
End Sub



'NAME TEXTBOX
Private Sub CloseNameTextBox_AfterUpdate()
   SavePointNameEntry CloseNameTextBox, SECTION_COMPASS_RULE_2D, KEY_POINTNAME
   RewriteRedrawCompassRuleFile
   ReLoadChooseboxes
End Sub

Private Sub CloseNameTextBox_Enter()
   SelectAllText CloseNameTextBox
End Sub



'DESC TEXTBOX
Private Sub CloseDescTextBox_AfterUpdate()
   RewriteRedrawCompassRuleFile
   ReLoadChooseboxes
End Sub

Private Sub CloseDescTextBox_Enter()
   SelectAllText CloseDescTextBox
End Sub



'DRAW NAME, DESCRIPTION, SYMBOL CHECKBOX
Private Sub NameAndDescCheckBox_Click()
   ClosingPointObSub
End Sub



'ELV. TEXTBOX
Private Sub ElevationTextBox_AfterUpdate()
   Dim origPrec As Long
   Dim value As Double
   If IsElevationString(ElevationTextBox.text, value, origPrec) Then
      ElevationTextBox.text = FormatNumber(value, origPrec, vbTrue, vbFalse, vbTrue)
   Else
      ElevationTextBox.text = DEFAULT_ELEVATION_STRING
   End If
End Sub



'INCLUDE ELEVATION CHECK BOX
Private Sub IncludeElCheckBox_Click()
   ClosingPointObSub
End Sub



'THE LAST TRAVERSE(SETUP) CHECKBOX
Private Sub LastTraverseOption_Click()
   ChangeLastObsSub
   ClosingPointObSub
End Sub



Private Sub ChangeLastObsSub()
   Dim MoveIndex As Long
   MoveIndex = ChooseMoveObsComboBox.listIndex
   fillMoveAllObsCombo
   If (ChooseMoveObsComboBox.ListCount - 1) < MoveIndex Then
      ChooseMoveObsComboBox.listIndex = -1
   Else
      ChooseMoveObsComboBox.listIndex = MoveIndex
   End If
   Dim IntPointIndex As Long
   IntPointIndex = ChooseTwoPtObsComboBox.listIndex
   fillTwoPtObsCombo
   If (ChooseTwoPtObsComboBox.ListCount - 1) < IntPointIndex Then
      ChooseTwoPtObsComboBox.listIndex = -1
   Else
      ChooseTwoPtObsComboBox.listIndex = IntPointIndex
   End If
End Sub



Private Sub ClosingPointObSub()
   CPNameAndDescStates
   ApplyStates
   RewriteRedrawCompassRuleFile
End Sub



Private Sub ReLoadChooseboxes()
   Dim MoveIndex As Long
   MoveIndex = ChooseMoveObsComboBox.listIndex
   fillMoveAllObsCombo
   ChooseMoveObsComboBox.listIndex = MoveIndex
   Dim TwoPathIndex As Long
   TwoPathIndex = ChooseTwoPtObsComboBox.listIndex
   fillTwoPtObsCombo
   ChooseTwoPtObsComboBox.listIndex = TwoPathIndex
End Sub

'---END CLOSING POINT OBSERVATION FRAME---



'**************************************************************************************
'////////////////////////////////ADJUSTMENT TAB\\\\\\\\\\\\\\\\\\\\\\\\\\\\\\\\\\\\\\\\
'**************************************************************************************
'==============ADJUSTMENT PHASE RADIO BUTTONS==============
'PRIMARY RADIO BUTTON
Private Sub PreliminaryOption_Click()
   If WasPreliminary Then
      Exit Sub
   End If
   StoFinalTab
   RclPrelimTab
   PhaseColor
   ApplyStates
   RewriteRedrawCompassRuleFile
   WasPreliminary = True
End Sub



'FINAL RADIO BUTTON
Private Sub FinalOption_Click()
   If Not WasPreliminary Then
      Exit Sub
   End If
   StoPrelimTab
   RclFinalTab
   PhaseColor
   ApplyStates
   RewriteRedrawCompassRuleFile
   WasPreliminary = False
End Sub



Private Sub PhaseColor()
   If PreliminaryOption.value Then
      PreliminaryOption.ForeColor = TEXT_COLOR_RED
      FinalOption.ForeColor = TEXT_COLOR_BLACK
   Else
      PreliminaryOption.ForeColor = TEXT_COLOR_BLACK
      FinalOption.ForeColor = TEXT_COLOR_RED
   End If
End Sub



'APPLY COMPASS RULE ADJUSTMENT CHECKBOX
Private Sub ApplyAdjustmentCheckBox_Click()
   CompassRuleStates
   RewriteRedrawCompassRuleFile
End Sub



'ANGULAR ADJUSTMENT CHECKBOX
Private Sub AngularAdjustmentCheckBox_Click()
   AngluarErrorAngleStates
   RewriteRedrawCompassRuleFile
End Sub



'ANGULAR ADJUSTMENT TEXT BOX
Private Sub AngularAdjustmentTextBox_AfterUpdate()
'ENTERED AS NUMBER
   PlusMinusAngleEntry AngularAdjustmentTextBox, OldAngularError, ANGLUAR_ADJ_LIMIT
   RewriteRedrawCompassRuleFile
End Sub

Private Sub AngularAdjustmentTextBox_Enter()
   SelectAllText AngularAdjustmentTextBox
End Sub


Private Sub PlusMinusAngleEntry(theTextbox As TextBox, backupVariable As String, limit As Double)
   Dim maxAngleDegrees As Double
   maxAngleDegrees = limit 'UP TO, BUT NOT INCLUDING LIMIT
   Dim origPrec As Long
   Dim degPart As Long
   Dim minPart As Long
   Dim secPart As Double
   Dim isNeg As Boolean
   If IsPlusMinusAngleString(theTextbox.text, origPrec, degPart, minPart, secPart, isNeg) Then
      Dim value As Double
      value = DmsToDec(degPart, minPart, secPart)
      If value >= maxAngleDegrees Then
'OUT OF RANGE
         theTextbox.text = backupVariable
         Beep
      Else
         Dim newPrec As Long
         newPrec = MinLong(origPrec, MAX_PRECISION_OG)
'ADD NEGATIVE SIGN IF NEEDED
         Dim formattedEntry As String
         formattedEntry = DirString(degPart, minPart, secPart, newPrec, DIR_TYPE_AZIMUTH, GetAngleStyle())
         If isNeg Then
'CHECK TO MAKE SURE ROUNDING DOESN'T MAKE IT ZERO
            If IsDeltaString(formattedEntry, origPrec, degPart, minPart, secPart) Then
                If degPart <> 0 Or minPart <> 0 Or secPart <> 0# Then
                   formattedEntry = STRING_MINUS & formattedEntry
                End If
            Else
'SHOULD NEVER REACH HERE
               theTextbox.text = backupVariable
               Beep
            End If
         End If
'SAVE FORMATTED ENTRY
         theTextbox.text = formattedEntry
         backupVariable = theTextbox.text
      End If
   Else
'INVALID STRING
      theTextbox.text = backupVariable
      Beep
   End If
End Sub


'SINGLE PATH ADJUSTMENT RADIO BUTTON
Private Sub SingleCompassRuleOption_Click()
   PointsAdjustmentSub
End Sub



'TWO PATH ADJUSTMENT RADIO BUTTON
Private Sub TwoPointAdjustmentOption_Click()
   PointsAdjustmentSub
End Sub



'HOLDING OBSERVATION COMBOBOX
Private Sub ChooseTwoPtObsComboBox_DropButtonClick()
   RewriteRedrawCompassRuleFile
End Sub



'ADJUST TO COORDINATE NORTHING TEXTBOX
Private Sub TwoPtNorthTextBox_AfterUpdate()
   TwoPtNorthTextBoxSub
   RewriteRedrawCompassRuleFile
End Sub

Public Sub TwoPtNorthTextBoxSub()
   NorthingFieldSub TwoPtNorthTextBox, OldTwoPointNorthing
End Sub

Private Sub TwoPtNorthTextBox_Enter()
   SelectAllText TwoPtNorthTextBox
End Sub



'ADJUST TO COORDINATE EASTING TEXTBOX
Private Sub TwoPtEastTextBox_AfterUpdate()
   TwoPtEastTextBoxSub
   RewriteRedrawCompassRuleFile
End Sub

Public Sub TwoPtEastTextBoxSub()
   EastingFieldSub TwoPtEastTextBox, OldTwoPointEasting
End Sub

Private Sub TwoPtEastTextBox_Enter()
   SelectAllText TwoPtEastTextBox
End Sub



'ADJUST TO COORDINATE PICK BUTTON
Private Sub TwoPtPickButton_Click()
'PICK TWO PATH INTERMEDIATE POINT
   FrmCompassRule.Hide

   Dim ThePickedPoint As Point3d
   If PickSub(COMMAND_NAME_COMPASS_RULE_2D, "Pick the intermediate point", ThePickedPoint) Then
      TwoPtNorthTextBox.text = FormatNumber(ThePickedPoint.Y, START_COORD_PREC, vbTrue, vbFalse, vbFalse)
      TwoPtNorthTextBoxSub
      TwoPtEastTextBox.text = FormatNumber(ThePickedPoint.X, START_COORD_PREC, vbTrue, vbFalse, vbFalse)
      TwoPtEastTextBoxSub
      RewriteRedrawCompassRuleFile
   End If

   FrmCompassRule.Show
End Sub



'---BEGIN COMPASS RULE SOLUTION RULES FRAME---
'RERUN COURSES AT PRECISION RADIO BUTTON
Private Sub HoldingCoursesOption_Click()
   SolutionRulesSub
End Sub



'1 SECOND RADIO BUTTON
Private Sub SecondOption_Click()
   RewriteRedrawCompassRuleFile
End Sub



'0.1 SECOND RADIO BUTTON
Private Sub TenthSecondOption_Click()
   RewriteRedrawCompassRuleFile
End Sub



'O.01' RADIO BUTTON
Private Sub HundredthOption_Click()
   RewriteRedrawCompassRuleFile
End Sub



'0.001' RADIO BUTTON
Private Sub ThousandthOption_Click()
   RewriteRedrawCompassRuleFile
End Sub



'HOLD COORDINATES, INVERSE COURSES RADIO BUTTON
Private Sub InverseCourseOption_Click()
   SolutionRulesSub
End Sub

'---END COMPASS RULE SOLUTION RULES FRAME---


'MOVE ALL CHECKBOX
Private Sub TranslationCheckBox_Click()
   RotationStates
   RewriteRedrawCompassRuleFile
End Sub



'HOLDING OBSERVATION FOR TRANSLATION COMBOBOX
Private Sub ChooseMoveObsComboBox_DropButtonClick()
   RewriteRedrawCompassRuleFile
End Sub



'ROTATION CHECKBOX
Private Sub RotationCheckBox_Click()
   RotationTextStates
   RewriteRedrawCompassRuleFile
End Sub



'ROTATION TEXTBOX
Private Sub RotationTextBox_AfterUpdate()
   RotationTextBoxSub
   RewriteRedrawCompassRuleFile
End Sub

Public Sub RotationTextBoxSub()
   PlusMinusAngleEntry RotationTextBox, OldRotation, 360
End Sub

Private Sub RotationTextBox_Enter()
   SelectAllText RotationTextBox
End Sub



'MOVE TO COORDINATE NORTHING TEXTBOX
Private Sub MoveToNorthTextBox_AfterUpdate()
   MoveToNorthTextBoxSub
   RewriteRedrawCompassRuleFile
End Sub

Public Sub MoveToNorthTextBoxSub()
   NorthingFieldSub MoveToNorthTextBox, OldMoveToNorthing
End Sub

Private Sub NorthingFieldSub(northTextbox As TextBox, backupVariable As String)
   Dim theValue As Double
   Dim origPrec As Long
   If IsNorthingString(northTextbox.text, theValue, origPrec) Then
      northTextbox.text = DoubleToNorthingString(theValue, START_COORD_PREC)
      backupVariable = northTextbox.text
   Else
      northTextbox.text = backupVariable
   End If
End Sub

Private Sub MoveToNorthTextBox_Enter()
   SelectAllText MoveToNorthTextBox
End Sub



'MOVE TO COORDINATE EASTING TEXTBOX
Private Sub MoveToEastTextBox_AfterUpdate()
   MoveToEastTextBoxSub
   RewriteRedrawCompassRuleFile
End Sub

Public Sub MoveToEastTextBoxSub()
   EastingFieldSub MoveToEastTextBox, OldMoveToEasting
End Sub

Private Sub EastingFieldSub(eastTextbox As TextBox, backupVariable As String)
   Dim theValue As Double
   Dim origPrec As Long
   If IsEastingString(eastTextbox.text, theValue, origPrec) Then
      eastTextbox.text = DoubleToEastingString(theValue, START_COORD_PREC)
      backupVariable = eastTextbox.text
   Else
      eastTextbox.text = backupVariable
   End If
End Sub

Private Sub MoveToEastTextBox_Enter()
   SelectAllText MoveToEastTextBox
End Sub



'MOVE TO COORDINATE PICK BUTTON
Private Sub PickMoveToButton_Click()
'PICK MOVE TO POINT
   FrmCompassRule.Hide
    
   Dim ThePickedPoint As Point3d
   If PickSub(COMMAND_NAME_COMPASS_RULE_2D, "Pick point to move to.", ThePickedPoint) Then
      MoveToNorthTextBox.text = FormatNumber(ThePickedPoint.Y, 4, vbTrue, vbFalse, vbFalse)
      MoveToNorthTextBoxSub
      MoveToEastTextBox.text = FormatNumber(ThePickedPoint.X, 4, vbTrue, vbFalse, vbFalse)
      MoveToEastTextBoxSub
      RewriteRedrawCompassRuleFile
   End If

   FrmCompassRule.Show
End Sub






Private Sub fillMoveAllObsCombo()
  ChooseMoveObsComboBox.Clear
  FillObsCombo ChooseMoveObsComboBox, 0, (RawEntriesListBox.ListCount - 1)
  If (LastForesightOption.value = True) And (ToBeginningOption.value = False) Then
     ChooseMoveObsComboBox.AddItem RawEntriesListBox.ListCount & " ; " & CloseNameTextBox.text & " ; " & CloseDescTextBox.text
  End If
End Sub


Private Sub fillTwoPtObsCombo()
   ChooseTwoPtObsComboBox.Clear
   Dim NumberOfTraverses As Long
   NumberOfTraverses = TraversesListBox.ListCount
   If (NumberOfTraverses >= 2) And (LastForesightOption.value = True) Then
      Dim BeginRawIndex As Long
      Dim PreviousRefNum As Long
      Dim pointName As String
      Dim bSString As String
      Dim fSString As String
      Dim hDString As String
      Dim descriptionString As String
      GetTravListLine 1, BeginRawIndex, pointName, bSString, fSString, hDString, descriptionString
      Dim EndRawIndex As Long
      EndRawIndex = RawEntriesListBox.ListCount - 1
      FillObsCombo ChooseTwoPtObsComboBox, BeginRawIndex, EndRawIndex
   ElseIf (NumberOfTraverses >= 3) And (LastForesightOption.value = False) Then
      GetTravListLine 1, BeginRawIndex, pointName, bSString, fSString, hDString, descriptionString
      Dim refNum As Long
      GetTravListLine (NumberOfTraverses - 1), refNum, pointName, bSString, fSString, hDString, descriptionString
      EndRawIndex = refNum - 1
      FillObsCombo ChooseTwoPtObsComboBox, BeginRawIndex, EndRawIndex
   End If
End Sub



Private Function TwoPtObsComboRefNum() As Long
   Dim TheListIndex As Long
   TheListIndex = ChooseTwoPtObsComboBox.listIndex
   If TheListIndex < 0 Then
      TwoPtObsComboRefNum = -1
      Exit Function
   End If
   TwoPtObsComboRefNum = GetTwoPtObsComboRefNum(TheListIndex)
End Function



Private Function GetTwoPtObsComboRefNum(index As Long) As Long
   If index < 0 Then
      GetTwoPtObsComboRefNum = -1
      Exit Function
   End If
   If index >= ChooseTwoPtObsComboBox.ListCount Then
      GetTwoPtObsComboRefNum = -1
      Exit Function
   End If
   Dim theText As String
   theText = ChooseTwoPtObsComboBox.List(index)
   Dim xSplit2 As Variant
   xSplit2 = Split(theText, ";")
   theText = xSplit2(LBound(xSplit2))
   GetTwoPtObsComboRefNum = CLng(theText)
End Function



Private Sub FillObsCombo(TheComboBox As ComboBox, beginIndex As Long, EndIndex As Long)
   Dim loopIndex As Long
   For loopIndex = beginIndex To EndIndex
      Dim name As String
      name = RawEntriesListBox.List(loopIndex, RAW_COLUMN_POINT_NAME)
      Dim Desc As String
      Desc = RawEntriesListBox.List(loopIndex, RAW_COLUMN_DESCRIPTION)
      TheComboBox.AddItem loopIndex & " ; " & name & " ; " & Desc
   Next loopIndex
End Sub



Private Sub PointsAdjustmentSub()
   IntermediatePointMiscloseStates
   RewriteRedrawCompassRuleFile
End Sub



Private Sub SolutionRulesSub()
   SolutionRulesStates
   RewriteRedrawCompassRuleFile
End Sub



'**************************************************************************************
'//////////////////////////////////REPORTS TAB\\\\\\\\\\\\\\\\\\\\\\\\\\\\\\\\\\\\\\\\\
'**************************************************************************************
'DATE TEXTBOX
Private Sub DateTextBox_AfterUpdate()
   RewriteCompassRuleFile
End Sub

Private Sub DateTextBox_Enter()
   SelectAllText DateTextBox
End Sub



'FILL DATE BUTTON
Private Sub DateButton_Click()
   DateTextBox.text = Now
   DateTextBox_AfterUpdate
End Sub



'PROJECT TEXTBOX
Private Sub ProjectTextBox_AfterUpdate()
   RewriteCompassRuleFile
End Sub

Private Sub ProjectTextBox_Enter()
   SelectAllText ProjectTextBox
End Sub



'ORIGIN TEXTBOX
Private Sub OriginTextBox_AfterUpdate()
   RewriteCompassRuleFile
End Sub

Private Sub OriginTextBox_Enter()
   SelectAllText OriginTextBox
End Sub



'AZIMUTH TEXTBOX
Private Sub AzimuthTextBox_AfterUpdate()
   RewriteCompassRuleFile
End Sub

Private Sub AzimuthTextBox_Enter()
   SelectAllText OriginTextBox
End Sub



'FIELDBOOK TEXTBOX
Private Sub FieldBookTextBox_AfterUpdate()
   RewriteCompassRuleFile
End Sub

Private Sub FieldBookTextBox_Enter()
   SelectAllText FieldBookTextBox
End Sub



'NOTES TEXTBOX
Private Sub NotesTextBox_AfterUpdate()
   RewriteCompassRuleFile
End Sub

Private Sub NotesTextBox_Enter()
   SelectAllText NotesTextBox
End Sub




'---BEGIN INV. PREC. WHEN AMBIGUOS FRAME---
'1 SEC RADIO BUTTON
Private Sub Inv1secOption_Click()
   ReportAnglePrecSave
End Sub



'0.1 SEC RADIO BUTTON
Private Sub InvTenthSecOption_Click()
   ReportAnglePrecSave
End Sub



Private Sub ReportAnglePrecSave()
   If Inv1secOption.value = True Then
      SaveSetting APP_NAME, SECTION_COMPASS_RULE_2D, KEY_REPROT_ANGLE_PREC, OPTION_PREC_ANG_SEC
   Else
      SaveSetting APP_NAME, SECTION_COMPASS_RULE_2D, KEY_REPROT_ANGLE_PREC, OPTION_PREC_ANG_SEC1
   End If
End Sub



'0.01' RADIO BUTTON
Private Sub hundredthFootOption_Click()
   ReportDistancePrecSave
End Sub



'0.001' RADIO BUTTON
Private Sub ThousandthFootOption_Click()
   ReportDistancePrecSave
End Sub



Private Sub ReportDistancePrecSave()
   If hundredthFootOption.value = True Then
      SaveSetting APP_NAME, SECTION_COMPASS_RULE_2D, KEY_REPORT_DISTANCE_PREC, OPTION_PREC_DIST_FT01
   Else
      SaveSetting APP_NAME, SECTION_COMPASS_RULE_2D, KEY_REPORT_DISTANCE_PREC, OPTION_PREC_DIST_FT001
   End If
End Sub

'---END INV. PREC. WHEN AMBIGUOS FRAME---



'INCLUDE SIDE SHOTS CHECKBOX
Private Sub IncludeSideShotsCheckBox_Click()
   SaveCheckBoxSetting IncludeSideShotsCheckBox, SECTION_COMPASS_RULE_2D, KEY_REPORT_OPTION_SIDESHOTS
End Sub



'INCLUDE FILENAME CHECKBOX
Private Sub ReportFilenameCheckBox_Click()
   SaveCheckBoxSetting ReportFilenameCheckBox, SECTION_COMPASS_RULE_2D, KEY_OPTION_FILENAME
   IncludePathStates
End Sub



'INCLUDE PATH CHECKBOX
Private Sub IncludePathCheckBox_Click()
   SaveCheckBoxSetting IncludePathCheckBox, SECTION_COMPASS_RULE_2D, KEY_OPTION_PATH
End Sub




'---BEGIN EXPORT TO ASCII FILE FRAME---
'EXPORT BUTTON
Private Sub ExportButton_Click()
'CHECK IF ANYTHING TO EXPORT
   If TraversesListBox.ListCount <= 0 Then
      MsgBox "Nothing to export"
      Exit Sub
   End If

'DISABLE USERFORM
   Me.enabled = False

'CREATE NEW COORDINATE FILE
   Dim CoordFilename As String
   Dim CurrentFullFileName As String
   CurrentFullFileName = GetSetting(APP_NAME, SECTION_COMPASS_RULE_2D, KEY_FILENAME_COORDINATE, "")
   If GetNewCoordFilename(CurrentFullFileName, CoordFilename) Then
      CreateNewCoordinateFile CoordFilename
      SaveSetting APP_NAME, SECTION_COMPASS_RULE_2D, KEY_FILENAME_COORDINATE, CoordFilename
'WRITE COORDINATE FILE
      ExportCoords CoordFilename
   End If

'REENABLE USERFORM
   Me.enabled = True
End Sub



'INCLUDE SIDE SHOTS CHECKBOX
Private Sub ExportSidesCheckBox_Click()
   SaveCheckBoxSetting IncludeSideShotsCheckBox, SECTION_COMPASS_RULE_2D, KEY_INCLUDE_SIDES
End Sub

'---END EXPORT TO ASCII FILE FRAME---


'GENERATE REPORT BUTTON
Private Sub ReportButton_Click()
'CHECK IF ANYTHING TO REPORT
   If TraversesListBox.ListCount <= 0 Then
      MsgBox "Nothing to report"
      Exit Sub
   End If

'DISABLE USERFORM
   Me.enabled = False

'CREATE NEW REPORT FILE
   Dim ReportFilename As String
   Dim CurrentFullFileName As String
   If GetReportFilename(ReportFilename) Then
      CreateNewCoordinateFile ReportFilename
'WRITE REPORT FILE
      GenerateReport ReportFilename

'DISPLAY IT TO USER
      ShellExecuteNormal ReportFilename
   End If

'REENABLE USERFORM
   Me.enabled = True
End Sub



'**************************************************************************************
'/////////////////////////////TRAVERSE SETTINGS TAB\\\\\\\\\\\\\\\\\\\\\\\\\\\\\\\\\\\\
'**************************************************************************************
'---BEGIN TRAVERSE TEXT FRAME---
'TRAVERSE TEXT LEVEL COMBOBOX
Private Sub TraverseTextLevelComboBox_AfterUpdate()
   If Not LevelBoxOnUpdate(TraverseTextLevelComboBox, SECTION_COMPASS_RULE_2D, KEY_TRAV_TEXT_LEVEL) Then
      PopulateTraverseTextLevelComboBox
      Beep
   End If
End Sub

Private Sub TraverseTextLevelComboBox_Change()
   RedrawCompassRuleFile
End Sub

Private Sub PopulateTraverseTextLevelComboBox()
   PopulateLevelBox TraverseTextLevelComboBox, SECTION_COMPASS_RULE_2D, KEY_TRAV_TEXT_LEVEL
End Sub



'TRAVERSE TEXT COLOR COMBOBOX
Private Sub TraverseTextColorComboBox_AfterUpdate()
   ColorBoxOnUpdate TraverseTextColorComboBox, SECTION_COMPASS_RULE_2D, KEY_TRAV_TEXT_COLOR
End Sub

Private Sub TraverseTextColorComboBox_Change()
   RedrawCompassRuleFile
End Sub

Private Sub PopulateTraverseTextColorComboBox()
   PopulateColorBox TraverseTextColorComboBox, SECTION_COMPASS_RULE_2D, KEY_TRAV_TEXT_COLOR
End Sub



'COLOR CHOOSER BUTTON
Private Sub TraverseTextColorChooserButton_Click()
   Dim MyColor As String
   If ChooseMyTableColor(MyColor) Then
      TraverseTextColorComboBox.text = MyColor
      TraverseTextColorComboBox_AfterUpdate
   End If
End Sub



'TRAVERSE TEXT LINESTYLE COMBOBOX
Private Sub TraverseTextStyleComboBox_AfterUpdate()
   If Not LineStyleBoxOnUpdate(TraverseTextStyleComboBox, SECTION_COMPASS_RULE_2D, KEY_TRAV_TEXT_STYLE) Then
      PopulateTraverseTextStyleComboBox
      Beep
   End If
End Sub

Private Sub TraverseTextStyleComboBox_Change()
   RedrawCompassRuleFile
End Sub

Private Sub PopulateTraverseTextStyleComboBox()
   PopulateLinestyleBox TraverseTextStyleComboBox, SECTION_COMPASS_RULE_2D, KEY_TRAV_TEXT_STYLE
End Sub




'TRAVERSE TEXT WEIGHT COMBOBOX
Private Sub TraverseTextWeightComboBox_AfterUpdate()
   WeightBoxOnUpdate TraverseTextWeightComboBox, SECTION_COMPASS_RULE_2D, KEY_TRAV_TEXT_WEIGHT
End Sub

Private Sub TraverseTextWeightComboBox_Change()
   RedrawCompassRuleFile
End Sub

Private Sub PopulateTraverseTextWeightComboBox()
   PopulateWeightBox TraverseTextWeightComboBox, SECTION_COMPASS_RULE_2D, KEY_TRAV_TEXT_WEIGHT
End Sub




'TRAVERSE TEXT FONT COMBOBOX
Private Sub TraverseTextFontComboBox_AfterUpdate()
'PROCESS DESCRIPTION TEXT FONT BOX ENTRY
   If Not FontBoxOnUpdate(TraverseTextFontComboBox, SECTION_COMPASS_RULE_2D, KEY_TRAV_TEXT_FONT) Then
      PopulateTraverseTextFontComboBox
      Beep
   End If
End Sub

Private Sub TraverseTextFontComboBox_Change()
   RedrawCompassRuleFile
End Sub

Private Sub PopulateTraverseTextFontComboBox()
'POPULATE DESCRIPTION TEXT FONT BOX
   PopulateFontBox TraverseTextFontComboBox, SECTION_COMPASS_RULE_2D, KEY_TRAV_TEXT_FONT
End Sub



'POINT NAME CHECKBOX
Private Sub TraversePointNameCheckBox_Click()
   SaveCheckBoxSetting TraversePointNameCheckBox, SECTION_COMPASS_RULE_2D, KEY_OPTION_TRAV_PT_NAME_CHK
   RedrawCompassRuleFile
End Sub



'DESCRIPTION CHECKBOX
Private Sub TraverseDescriptionCheckBox_Click()
   SaveCheckBoxSetting TraverseDescriptionCheckBox, SECTION_COMPASS_RULE_2D, KEY_OPTION_TRAV_DESC_CHK
   RedrawCompassRuleFile
End Sub

'ELEVATION CHECKBOX
Private Sub ElevCheckBox_Click()
   SaveCheckBoxSetting ElevCheckBox, SECTION_COMPASS_RULE_2D, KEY_OPTION_TRAV_ELEV_CHK
   RedrawCompassRuleFile
End Sub

'---END TRAVERSE TEXT FRAME---



'---BEGIN TRAVERSE LINE FRAME---
'TRAVERSE LINE LEVEL COMBOBOX
Private Sub TraverseLineLevelComboBox_AfterUpdate()
   If Not LevelBoxOnUpdate(TraverseLineLevelComboBox, SECTION_COMPASS_RULE_2D, KEY_TRAV_LINE_LEVEL) Then
      PopulateTraverseLineLevelComboBox
      Beep
   End If
End Sub

Private Sub TraverseLineLevelComboBox_Change()
   RedrawCompassRuleFile
End Sub

Private Sub PopulateTraverseLineLevelComboBox()
   PopulateLevelBox TraverseLineLevelComboBox, SECTION_COMPASS_RULE_2D, KEY_TRAV_LINE_LEVEL
End Sub




'TRAVERSE LINE COLOR COMBOBOX
Private Sub TraverseLineColorComboBox_AfterUpdate()
   ColorBoxOnUpdate TraverseLineColorComboBox, SECTION_COMPASS_RULE_2D, KEY_TRAV_LINE_COLOR
End Sub

Private Sub TraverseLineColorComboBox_Change()
   RedrawCompassRuleFile
End Sub

Private Sub PopulateTraverseLineColorComboBox()
   PopulateColorBox TraverseLineColorComboBox, SECTION_COMPASS_RULE_2D, KEY_TRAV_LINE_COLOR
End Sub




'COLOR CHOOSER BUTTON
Private Sub TraverseLineColorChooserButton_Click()
   Dim MyColor As String
   If ChooseMyTableColor(MyColor) Then
      TraverseLineColorComboBox.text = MyColor
      TraverseLineColorComboBox_AfterUpdate
   End If
End Sub




'TRAVERSE LINE LINESTYLE COMBOBOX
Private Sub TraverseLineStyleComboBox_AfterUpdate()
   If Not LineStyleBoxOnUpdate(TraverseLineStyleComboBox, SECTION_COMPASS_RULE_2D, KEY_TRAV_LINE_STYLE) Then
      PopulateTraverseLineStyleComboBox
      Beep
   End If
End Sub

Private Sub TraverseLineStyleComboBox_Change()
   RedrawCompassRuleFile
End Sub

Private Sub PopulateTraverseLineStyleComboBox()
   PopulateLinestyleBox TraverseLineStyleComboBox, SECTION_COMPASS_RULE_2D, KEY_TRAV_LINE_STYLE
End Sub




'TRAVERSE LINE WEIGHT COMBOBOX
Private Sub TraverseLineWeightComboBox_AfterUpdate()
   WeightBoxOnUpdate TraverseLineWeightComboBox, SECTION_COMPASS_RULE_2D, KEY_TRAV_LINE_WEIGHT
End Sub

Private Sub TraverseLineWeightComboBox_Change()
   RedrawCompassRuleFile
End Sub

Private Sub PopulateTraverseLineWeightComboBox()
   PopulateWeightBox TraverseLineWeightComboBox, SECTION_COMPASS_RULE_2D, KEY_TRAV_LINE_WEIGHT
End Sub

'---END TRAVERSE LINE FRAME---



'---BEGIN TRAVERSE SYMBOL FRAME---
'*********TRAVERSE SYMBOL LEVEL BOX***********
Private Sub TraverseSymbolLevelComboBox_AfterUpdate()
   If Not LevelBoxOnUpdate(TraverseSymbolLevelComboBox, SECTION_COMPASS_RULE_2D, KEY_TRAV_SYMBOL_LEVEL) Then
      PopulateTraverseSymbolLevelComboBox
      Beep
   End If
End Sub

Private Sub TraverseSymbolLevelComboBox_Change()
   RedrawCompassRuleFile
End Sub

Private Sub PopulateTraverseSymbolLevelComboBox()
   PopulateLevelBox TraverseSymbolLevelComboBox, SECTION_COMPASS_RULE_2D, KEY_TRAV_SYMBOL_LEVEL
End Sub

'*********TRAVERSE SYMBOL COLOR BOX***********
Private Sub TraverseSymbolColorComboBox_AfterUpdate()
   ColorBoxOnUpdate TraverseSymbolColorComboBox, SECTION_COMPASS_RULE_2D, KEY_TRAV_SYMBOL_COLOR
End Sub

Private Sub TraverseSymbolColorComboBox_Change()
   RedrawCompassRuleFile
End Sub

Private Sub PopulateTraverseSymbolColorComboBox()
   PopulateColorBox TraverseSymbolColorComboBox, SECTION_COMPASS_RULE_2D, KEY_TRAV_SYMBOL_COLOR
End Sub

Private Sub TraverseSymbolColorChooserButton_Click()
   Dim MyColor As String
   If ChooseMyTableColor(MyColor) Then
      TraverseSymbolColorComboBox.text = MyColor
      TraverseSymbolColorComboBox_AfterUpdate
   End If
End Sub

'*********TRAVERSE SYMBOL LINESTYLE BOX***********
Private Sub TraverseSymbolStyleComboBox_AfterUpdate()
   If Not LineStyleBoxOnUpdate(TraverseSymbolStyleComboBox, SECTION_COMPASS_RULE_2D, KEY_TRAV_SYMBOL_STYLE) Then
      PopulateTraverseSymbolStyleComboBox
      Beep
   End If
End Sub

Private Sub TraverseSymbolStyleComboBox_Change()
   RedrawCompassRuleFile
End Sub

Private Sub PopulateTraverseSymbolStyleComboBox()
   PopulateLinestyleBox TraverseSymbolStyleComboBox, SECTION_COMPASS_RULE_2D, KEY_TRAV_SYMBOL_STYLE
End Sub

'*********TRAVERSE SYMBOL WEIGHT BOX***********
Private Sub TraverseSymbolWeightComboBox_AfterUpdate()
   WeightBoxOnUpdate TraverseSymbolWeightComboBox, SECTION_COMPASS_RULE_2D, KEY_TRAV_SYMBOL_WEIGHT
End Sub

Private Sub TraverseSymbolWeightComboBox_Change()
   RedrawCompassRuleFile
End Sub

Private Sub PopulateTraverseSymbolWeightComboBox()
   PopulateWeightBox TraverseSymbolWeightComboBox, SECTION_COMPASS_RULE_2D, KEY_TRAV_SYMBOL_WEIGHT
End Sub


'*********TRAVERSE SYMBOL OPTIONS***********
'SYMBOL 1 RADIO BUTTON
Private Sub OptionSetupSym1_Click()
   SaveTravSym
End Sub

Private Sub OptionSetupSym1_Change()
   RedrawCompassRuleFile
End Sub

'SYMBOL 1 IMAGE
Private Sub ImageSetupSym1_Click()
   OptionSetupSym1.value = True
End Sub

'SYMBOL 2 RADIO BUTTON
Private Sub OptionSetupSym2_Click()
   SaveTravSym
End Sub

Private Sub OptionSetupSym2_Change()
   RedrawCompassRuleFile
End Sub

'SYMBOL 2 IMAGE
Private Sub ImageSetupSym2_Click()
   OptionSetupSym2.value = True
End Sub

'SYMBOL 3 RADIO BUTTON
Private Sub OptionSetupSym3_Click()
   SaveTravSym
End Sub

Private Sub OptionSetupSym3_Change()
   RedrawCompassRuleFile
End Sub

'SYMBOL 3 IMAGE
Private Sub ImageSetupSym3_Click()
   OptionSetupSym3.value = True
End Sub

'SYMBOL 4 RADIO BUTTON
Private Sub OptionSetupSym4_Click()
   SaveTravSym
End Sub

Private Sub OptionSetupSym4_Change()
   RedrawCompassRuleFile
End Sub

'SYMBOL 4 IMAGE
Private Sub ImageSetupSym4_Click()
   OptionSetupSym4.value = True
End Sub

'SYMBOL 5 RADIO BUTTON
Private Sub OptionSetupSym5_Click()
   SaveTravSym
End Sub

Private Sub OptionSetupSym5_Change()
   RedrawCompassRuleFile
End Sub

'SYMBOL 5 IMAGE
Private Sub ImageSetupSym5_Click()
   OptionSetupSym5.value = True
End Sub

'SYMBOL 6 RADIO BUTTON
Private Sub OptionSetupSym6_Click()
   SaveTravSym
End Sub

Private Sub OptionSetupSym6_Change()
   RedrawCompassRuleFile
End Sub

'SYMBOL 6 IMAGE
Private Sub ImageSetupSym6_Click()
   OptionSetupSym6.value = True
End Sub

'SYMBOL NONE RADIO BUTTON
Private Sub OptionSetupSymNone_Click()
   SaveTravSym
End Sub

Private Sub OptionSetupSymNone_Change()
   RedrawCompassRuleFile
End Sub

Private Sub SaveTravSym()
   If OptionSetupSym1.value = True Then
      Dim Sym As String
      Sym = SYMBOL_1
   ElseIf OptionSetupSym2.value = True Then
      Sym = SYMBOL_2
   ElseIf OptionSetupSym3.value = True Then
      Sym = SYMBOL_3
   ElseIf OptionSetupSym4.value = True Then
      Sym = SYMBOL_4
   ElseIf OptionSetupSym5.value = True Then
      Sym = SYMBOL_5
   ElseIf OptionSetupSym6.value = True Then
      Sym = SYMBOL_6
   Else
      Sym = SYMBOL_NONE
   End If
   SaveSetting APP_NAME, SECTION_COMPASS_RULE_2D, KEY_TRAV_SYMBOL, Sym
End Sub

'---END TRAVERSE SYMBOL FRAME---



'---BEGIN TRAVERSE TEXT OFFSET FRAME---
'POINT NAME UP/DOWN
Private Sub TravNameUDOffsetTextBox_AfterUpdate()
   SaveElevationEntry TravNameUDOffsetTextBox, SECTION_COMPASS_RULE_2D, KEY_TRAV_NAME_OFFSET_UD
   RedrawCompassRuleFile
End Sub

Private Sub TravNameUDOffsetTextBox_Enter()
   SelectAllText TravNameUDOffsetTextBox
End Sub



'POINT NAME LEFT/RIGHT
Private Sub TravNameLROffsetTextBox_AfterUpdate()
   SaveElevationEntry TravNameLROffsetTextBox, SECTION_COMPASS_RULE_2D, KEY_TRAV_NAME_OFFSET_LR
   RedrawCompassRuleFile
End Sub

Private Sub TravNameLROffsetTextBox_Enter()
   SelectAllText TravNameLROffsetTextBox
End Sub



'DESCRIPTION UP/DOWN
Private Sub TravDescUDOffsetTextBox_AfterUpdate()
   SaveElevationEntry TravDescUDOffsetTextBox, SECTION_COMPASS_RULE_2D, KEY_TRAV_DESC_OFFSET_UD
   RedrawCompassRuleFile
End Sub

Private Sub TravDescUDOffsetTextBox_Enter()
   SelectAllText TravDescUDOffsetTextBox
End Sub



'DESCRIPTION LEFT/RIGHT
Private Sub TravDescLROffsetTextBox_AfterUpdate()
   SaveElevationEntry TravDescLROffsetTextBox, SECTION_COMPASS_RULE_2D, KEY_TRAV_DESC_OFFSET_LR
   RedrawCompassRuleFile
End Sub

Private Sub TravDescLROffsetTextBox_Enter()
   SelectAllText TravDescLROffsetTextBox
End Sub



'ELEVATION UP/DOWN
Private Sub elUDOSTextBox_AfterUpdate()
   SaveElevationEntry elUDOSTextBox, SECTION_COMPASS_RULE_2D, KEY_TRAV_ELEV_OFFSET_UD
   RedrawCompassRuleFile
End Sub

Private Sub elUDOSTextBox_Enter()
   SelectAllText elUDOSTextBox
End Sub



'ELEVATION LEFT/RIGHT
Private Sub elLRLOSTextBox_AfterUpdate()
   SaveElevationEntry elLRLOSTextBox, SECTION_COMPASS_RULE_2D, KEY_TRAV_ELEV_OFFSET_LR
   RedrawCompassRuleFile
End Sub

Private Sub elLRLOSTextBox_Enter()
   SelectAllText elLRLOSTextBox
End Sub

'---END TRAVERSE TEXT OFFSET FRAME---



'SETTINGS BUTTON
Private Sub SettingsButton_Click()
   Setting
   RedrawCompassRuleFile
End Sub


'**************SOUND CHECK BOX**************
'Private Sub SoundCheckBox_Click()
'   SaveCheckBoxSetting SoundCheckBox, SECTION_COMPASS_RULE_2D, Key_Compass_Rule_Option_Sound
'End Sub
'++++++++++++++++++++++++++++++++++++++++++

'**************************************************************************************
'///////////////////////////SIDE SHOT SETTINGS TAB\\\\\\\\\\\\\\\\\\\\\\\\\\\\\\\\\\\\\
'**************************************************************************************
'---BEGIN SIDE SHOT TEXT FRAME---
'SIDE SHOT TEXT LEVEL COMBOBOX
Private Sub SideShotTextLevelComboBox_AfterUpdate()
   If Not LevelBoxOnUpdate(SideShotTextLevelComboBox, SECTION_COMPASS_RULE_2D, KEY_SIDE_TEXT_LEVEL) Then
      PopulateSideShotTextLevelComboBox
      Beep
   End If
End Sub

Private Sub SideShotTextLevelComboBox_Change()
   RedrawCompassRuleFile
End Sub

Private Sub PopulateSideShotTextLevelComboBox()
   PopulateLevelBox SideShotTextLevelComboBox, SECTION_COMPASS_RULE_2D, KEY_SIDE_TEXT_LEVEL
End Sub



'SIDE SHOT TEXT COLOR COMBOBOX
Private Sub SideShotTextColorComboBox_AfterUpdate()
   ColorBoxOnUpdate SideShotTextColorComboBox, SECTION_COMPASS_RULE_2D, KEY_SIDE_TEXT_COLOR
End Sub

Private Sub SideShotTextColorComboBox_Change()
   RedrawCompassRuleFile
End Sub

Private Sub PopulateSideShotTextColorComboBox()
   PopulateColorBox SideShotTextColorComboBox, SECTION_COMPASS_RULE_2D, KEY_SIDE_TEXT_COLOR
End Sub



'COLOR CHOOSER BUTTON
Private Sub SideShotTextColorChooserButton_Click()
   Dim MyColor As String
   If ChooseMyTableColor(MyColor) Then
      SideShotTextColorComboBox.text = MyColor
      SideShotTextColorComboBox_AfterUpdate
   End If
End Sub



'SIDE SHOT TEXT LINESTYLE COMBOBOX
Private Sub SideShotTextStyleComboBox_AfterUpdate()
   If Not LineStyleBoxOnUpdate(SideShotTextStyleComboBox, SECTION_COMPASS_RULE_2D, KEY_SIDE_TEXT_STYLE) Then
      PopulateSideShotTextStyleComboBox
      Beep
   End If
End Sub

Private Sub SideShotTextStyleComboBox_Change()
   RedrawCompassRuleFile
End Sub

Private Sub PopulateSideShotTextStyleComboBox()
   PopulateLinestyleBox SideShotTextStyleComboBox, SECTION_COMPASS_RULE_2D, KEY_SIDE_TEXT_STYLE
End Sub



'SIDE SHOT TEXT WEIGHT COMBOBOX
Private Sub SideShotTextWeightComboBox_AfterUpdate()
   WeightBoxOnUpdate SideShotTextWeightComboBox, SECTION_COMPASS_RULE_2D, KEY_SIDE_TEXT_WEIGHT
End Sub

Private Sub SideShotTextWeightComboBox_Change()
   RedrawCompassRuleFile
End Sub

Private Sub PopulateSideShotTextWeightComboBox()
   PopulateWeightBox SideShotTextWeightComboBox, SECTION_COMPASS_RULE_2D, KEY_SIDE_TEXT_WEIGHT
End Sub



'SIDE SHOT TEXT FONT COMBOBOX
Private Sub SideShotTextFontComboBox_AfterUpdate()
   If Not FontBoxOnUpdate(SideShotTextFontComboBox, SECTION_COMPASS_RULE_2D, KEY_SIDE_TEXT_FONT) Then
      PopulateSideShotTextFontComboBox
      Beep
   End If
End Sub

Private Sub SideShotTextFontComboBox_Change()
   RedrawCompassRuleFile
End Sub

Private Sub PopulateSideShotTextFontComboBox()
   PopulateFontBox SideShotTextFontComboBox, SECTION_COMPASS_RULE_2D, KEY_SIDE_TEXT_FONT
End Sub



'POINT NAME CHECKBOX
Private Sub SideShotTextPointNameCheckBox_Click()
   SaveCheckBoxSetting SideShotTextPointNameCheckBox, SECTION_COMPASS_RULE_2D, KEY_OPTION_SIDE_PT_NAME_CHK
   RedrawCompassRuleFile
End Sub



'DESCRIPTION CHECKBOX
Private Sub SideShotTextDescriptionCheckBox_Click()
   SaveCheckBoxSetting SideShotTextDescriptionCheckBox, SECTION_COMPASS_RULE_2D, KEY_OPTION_SIDE_DESC_CHK
   RedrawCompassRuleFile
End Sub

'---END SIDE SHOT TEXT FRAME---



'---BEGIN SIDE SHOT LINE FRAME---
'SIDE SHOT LINE LEVEL COMBOBOX
Private Sub SideShotLineLevelComboBox_AfterUpdate()
   If Not LevelBoxOnUpdate(SideShotLineLevelComboBox, SECTION_COMPASS_RULE_2D, KEY_SIDE_LINE_LEVEL) Then
      PopulateSideShotLineLevelComboBox
      Beep
   End If
End Sub

Private Sub SideShotLineLevelComboBox_Change()
   RedrawCompassRuleFile
End Sub

Private Sub PopulateSideShotLineLevelComboBox()
   PopulateLevelBox SideShotLineLevelComboBox, SECTION_COMPASS_RULE_2D, KEY_SIDE_LINE_LEVEL
End Sub



'SIDE SHOT LINE COLOR COMBOBOX
Private Sub SideShotLineColorComboBox_AfterUpdate()
   ColorBoxOnUpdate SideShotLineColorComboBox, SECTION_COMPASS_RULE_2D, KEY_SIDE_LINE_COLOR
End Sub

Private Sub SideShotLineColorComboBox_Change()
   RedrawCompassRuleFile
End Sub

Private Sub PopulateSideShotLineColorComboBox()
   PopulateColorBox SideShotLineColorComboBox, SECTION_COMPASS_RULE_2D, KEY_SIDE_LINE_COLOR
End Sub



'COLOR CHOOSER BUTTON
Private Sub SideShotLineColorChooserButton_Click()
   Dim MyColor As String
   If ChooseMyTableColor(MyColor) Then
      SideShotLineColorComboBox.text = MyColor
      SideShotLineColorComboBox_AfterUpdate
   End If
End Sub



'SIDE SHOT LINE LINESTYLE COMBOBOX
Private Sub SideShotLineStyleComboBox_AfterUpdate()
   If Not LineStyleBoxOnUpdate(SideShotLineStyleComboBox, SECTION_COMPASS_RULE_2D, KEY_SIDE_LINE_STYLE) Then
      PopulateSideShotLineStyleComboBox
      Beep
   End If
End Sub

Private Sub SideShotLineStyleComboBox_Change()
   RedrawCompassRuleFile
End Sub

Private Sub PopulateSideShotLineStyleComboBox()
   PopulateLinestyleBox SideShotLineStyleComboBox, SECTION_COMPASS_RULE_2D, KEY_SIDE_LINE_STYLE
End Sub




'SIDE SHOT LINE WEIGHT COMBOBOX
Private Sub SideShotLineWeightComboBox_AfterUpdate()
   WeightBoxOnUpdate SideShotLineWeightComboBox, SECTION_COMPASS_RULE_2D, KEY_SIDE_LINE_WEIGHT
End Sub

Private Sub SideShotLineWeightComboBox_Change()
   RedrawCompassRuleFile
End Sub

Private Sub PopulateSideShotLineWeightComboBox()
   PopulateWeightBox SideShotLineWeightComboBox, SECTION_COMPASS_RULE_2D, KEY_SIDE_LINE_WEIGHT
End Sub

'---END SIDE SHOT LINE FRAME---



'---BEGIN SIDE SHOT SYMBOL FRAME---
'SIDE SHOT SYMBOL LEVEL COMBOBOX
Private Sub SideShotSymbolLevelComboBox_AfterUpdate()
   If Not LevelBoxOnUpdate(SideShotSymbolLevelComboBox, SECTION_COMPASS_RULE_2D, KEY_SIDE_SYMBOL_LEVEL) Then
      PopulateSideShotLineLevelComboBox
      Beep
   End If
End Sub

Private Sub SideShotSymbolLevelComboBox_Change()
   RedrawCompassRuleFile
End Sub

Private Sub PopulateSideShotSymbolLevelComboBox()
   PopulateLevelBox SideShotSymbolLevelComboBox, SECTION_COMPASS_RULE_2D, KEY_SIDE_SYMBOL_LEVEL
End Sub




'SIDE SHOT SYMBOL COLOR COMBOBOX
Private Sub SideShotSymbolColorComboBox_AfterUpdate()
   ColorBoxOnUpdate SideShotSymbolColorComboBox, SECTION_COMPASS_RULE_2D, KEY_SIDE_SYMBOL_COLOR
End Sub

Private Sub SideShotSymbolColorComboBox_Change()
   RedrawCompassRuleFile
End Sub

Private Sub PopulateSideShotSymbolColorComboBox()
   PopulateColorBox SideShotSymbolColorComboBox, SECTION_COMPASS_RULE_2D, KEY_SIDE_SYMBOL_COLOR
End Sub



'COLOR CHOOSER BUTTON
Private Sub SideShotSymbolColorChooserButton_Click()
   Dim MyColor As String
   If ChooseMyTableColor(MyColor) Then
      SideShotSymbolColorComboBox.text = MyColor
      SideShotSymbolColorComboBox_AfterUpdate
   End If
End Sub



'SIDE SHOT SYMBOL LINESTYLE COMBOBOX
Private Sub SideShotSymbolStyleComboBox_AfterUpdate()
   If Not LineStyleBoxOnUpdate(SideShotSymbolStyleComboBox, SECTION_COMPASS_RULE_2D, KEY_SIDE_SYMBOL_STYLE) Then
      PopulateSideShotSymbolStyleComboBox
      Beep
   End If
End Sub

Private Sub SideShotSymbolStyleComboBox_Change()
   RedrawCompassRuleFile
End Sub

Private Sub PopulateSideShotSymbolStyleComboBox()
   PopulateLinestyleBox SideShotSymbolStyleComboBox, SECTION_COMPASS_RULE_2D, KEY_SIDE_SYMBOL_STYLE
End Sub




'SIDE SHOT SYMBOL WEIGHT COMBOBOX
Private Sub SideShotSymbolWeightComboBox_AfterUpdate()
   WeightBoxOnUpdate SideShotSymbolWeightComboBox, SECTION_COMPASS_RULE_2D, KEY_SIDE_SYMBOL_WEIGHT
End Sub

Private Sub SideShotSymbolWeightComboBox_Change()
   RedrawCompassRuleFile
End Sub

Private Sub PopulateSideShotSymbolWeightComboBox()
   PopulateWeightBox SideShotSymbolWeightComboBox, SECTION_COMPASS_RULE_2D, KEY_SIDE_SYMBOL_WEIGHT
End Sub

'---END SIDE SHOT SYMBOL FRAME---


'---BEGIN SIDE SHOT TEXT OFFSET FRAME---
'POINT NAME UP/DOWN TEXTBOX
Private Sub SideNameUDOffsetTextBox_AfterUpdate()
   SaveElevationEntry SideNameUDOffsetTextBox, SECTION_COMPASS_RULE_2D, KEY_SIDE_NAME_OFFSET_UD
   RedrawCompassRuleFile
End Sub

Private Sub SideNameUDOffsetTextBox_Enter()
   SelectAllText SideNameUDOffsetTextBox
End Sub



'POINT NAME LEFT/RIGHT TEXTBOX
Private Sub SideNameLROffsetTextBox_AfterUpdate()
   SaveElevationEntry SideNameLROffsetTextBox, SECTION_COMPASS_RULE_2D, KEY_SIDE_NAME_OFFSET_LR
   RedrawCompassRuleFile
End Sub

Private Sub SideNameLROffsetTextBox_Enter()
   SelectAllText SideNameLROffsetTextBox
End Sub



'DESCRIPTION UP/DOWN TEXTBOX
Private Sub SideDescUDOffsetTextBox_AfterUpdate()
   SaveElevationEntry SideDescUDOffsetTextBox, SECTION_COMPASS_RULE_2D, KEY_SIDE_DESC_OFFSET_UD
   RedrawCompassRuleFile
End Sub

Private Sub SideDescUDOffsetTextBox_Enter()
   SelectAllText SideDescUDOffsetTextBox
End Sub



'DECRIPITION LEFT/RIGHT TEXTBOX
Private Sub SideDescLROffsetTextBox_AfterUpdate()
   SaveElevationEntry SideDescLROffsetTextBox, SECTION_COMPASS_RULE_2D, KEY_SIDE_DESC_OFFSET_LR
   RedrawCompassRuleFile
End Sub

Private Sub SideDescLROffsetTextBox_Enter()
   SelectAllText SideDescLROffsetTextBox
End Sub

'---END SIDE SHOT TEXT OFFSET FRAME---



'TURN SIDE SHOTS OFF CHECKBOX
Private Sub SidesOffCheckBox_Click()
   SaveCheckBoxSetting DiagramOffCheckBox, SECTION_COMPASS_RULE_2D, KEY_OPTION_SIDE_SHOTS_OFF
   RedrawCompassRuleFile
End Sub



'USE MINI CELL CHECKBOX
Private Sub UseMiniCellCheckBox_Click()
   SaveCheckBoxSetting UseMiniCellCheckBox, SECTION_COMPASS_RULE_2D, KEY_OPTION_CELL_USE_CELL_CHK
   RedrawCompassRuleFile
End Sub



'---BEGIN SIDE SHOT MINI CELL FRAME---
'SIDE SHOT TEXT LEVEL COMBOBOX
Private Sub MiniCellLevelComboBox_AfterUpdate()
   If Not LevelBoxOnUpdate(MiniCellLevelComboBox, SECTION_COMPASS_RULE_2D, KEY_MINI_CELL_LEVEL) Then
      PopulateMiniCellLevelComboBox
      Beep
   End If
End Sub

Private Sub MiniCellLevelComboBox_Change()
   RedrawCompassRuleFile
End Sub

Private Sub PopulateMiniCellLevelComboBox()
   PopulateLevelBox MiniCellLevelComboBox, SECTION_COMPASS_RULE_2D, KEY_MINI_CELL_LEVEL
End Sub



'SIDE SHOT TEXT COLOR COMBOBOX
Private Sub MiniCellColorComboBox_AfterUpdate()
   ColorBoxOnUpdate MiniCellColorComboBox, SECTION_COMPASS_RULE_2D, KEY_MINI_CELL_COLOR
End Sub

Private Sub MiniCellColorComboBox_Change()
   RedrawCompassRuleFile
End Sub

Private Sub PopulateMiniCellColorComboBox()
   PopulateColorBox MiniCellColorComboBox, SECTION_COMPASS_RULE_2D, KEY_MINI_CELL_COLOR
End Sub



'COLOR CHOOSEER BUTTON
Private Sub MiniCellColorChooserButton_Click()
   Dim MyColor As String
   If ChooseMyTableColor(MyColor) Then
      MiniCellColorComboBox.text = MyColor
      MiniCellColorComboBox_AfterUpdate
   End If
End Sub



'SIDE SHOT TEXT LINESTYLE COMBOBOX
Private Sub MiniCellstyleComboBox_AfterUpdate()
   If Not LineStyleBoxOnUpdate(MiniCellstyleComboBox, SECTION_COMPASS_RULE_2D, KEY_MINI_CELL_STYLE) Then
      PopulateMiniCellstyleComboBox
      Beep
   End If
End Sub

Private Sub MiniCellstyleComboBox_Change()
   RedrawCompassRuleFile
End Sub

Private Sub PopulateMiniCellstyleComboBox()
   PopulateLinestyleBox MiniCellstyleComboBox, SECTION_COMPASS_RULE_2D, KEY_MINI_CELL_STYLE
End Sub



'SIDE SHOT TEXT WEIGHT COMBOBOX
Private Sub MiniCellWeightComboBox_AfterUpdate()
   WeightBoxOnUpdate MiniCellWeightComboBox, SECTION_COMPASS_RULE_2D, KEY_MINI_CELL_WEIGHT
End Sub

Private Sub MiniCellWeightComboBox_Change()
   RedrawCompassRuleFile
End Sub

Private Sub PopulateMiniCellWeightComboBox()
   PopulateWeightBox MiniCellWeightComboBox, SECTION_COMPASS_RULE_2D, KEY_MINI_CELL_WEIGHT
End Sub



'SIDE SHOT TEXT FONT COMBOBOX
Private Sub MiniCellFontComboBox_AfterUpdate()
'PROCESS DESCRIPTION TEXT FONT BOX ENTRY
   If Not FontBoxOnUpdate(MiniCellFontComboBox, SECTION_COMPASS_RULE_2D, KEY_MINI_CELL_FONT) Then
      PopulateMiniCellFontComboBox
      Beep
   End If
End Sub

Private Sub MiniCellFontComboBox_Change()
   RedrawCompassRuleFile
End Sub

Private Sub PopulateMiniCellFontComboBox()
   PopulateFontBox MiniCellFontComboBox, SECTION_COMPASS_RULE_2D, KEY_MINI_CELL_FONT
End Sub



'FONT SIZE TEXTBOX
Private Sub FontSizeTextBox_AfterUpdate()
   SaveNonnegativeEntry FontSizeTextBox, SECTION_COMPASS_RULE_2D, KEY_CELL_TEXT_FONT_SIZE, 10, MAX_PRECISION_RADIUS, False, 0.5

   RedrawCompassRuleFile
End Sub

'---END SIDE SHOT MINI CELL FRAME---



'---BEGIN MINI CELL TEXT OFFSET FRAME---
'POINT NAME UP/DOWN TEXTBOX
Private Sub MiniCellNameUDTextBox_AfterUpdate()
   SaveElevationEntry MiniCellNameUDTextBox, SECTION_COMPASS_RULE_2D, KEY_CELL_NAME_OFFSET_UD
   RedrawCompassRuleFile
End Sub

Private Sub MiniCellNameUDTextBox_Enter()
   SelectAllText MiniCellNameUDTextBox
End Sub



'POINT NAME LEFT/RIGHT TEXTBOX
Private Sub MiniCellLRNameTextBox_AfterUpdate()
   SaveElevationEntry MiniCellLRNameTextBox, SECTION_COMPASS_RULE_2D, KEY_CELL_NAME_OFFSET_LR
   RedrawCompassRuleFile
End Sub

Private Sub MiniCellLRNameTextBox_Enter()
   SelectAllText MiniCellLRNameTextBox
End Sub



'DESCRIPTION UP/DOWN TEXTBOX
Private Sub MiniCellUDDescTextBox_AfterUpdate()
   SaveElevationEntry MiniCellUDDescTextBox, SECTION_COMPASS_RULE_2D, KEY_CELL_DESC_OFFSET_UD
   RedrawCompassRuleFile
End Sub

Private Sub MiniCellUDDescTextBox_Enter()
   SelectAllText MiniCellUDDescTextBox
End Sub



'DESCRIPTION LEFT/RIGHT TEXTBOX
Private Sub MinicellLRDescTextBox_AfterUpdate()
   SaveElevationEntry MinicellLRDescTextBox, SECTION_COMPASS_RULE_2D, KEY_CELL_DESC_OFFSET_LR
   RedrawCompassRuleFile
End Sub

Private Sub MinicellLRDescTextBox_Enter()
   SelectAllText MinicellLRDescTextBox
End Sub

'---END MINI CELL TEXT OFFSET FRAME---



'**************************************************************************************
'///////////////////////////DROP DIAGRAM SETTINGS TAB\\\\\\\\\\\\\\\\\\\\\\\\\\\\\\\\\\
'**************************************************************************************
'---BEGIN DROP DIAGRAM FRAME---
'DROP DIAGRAM LEVEL COMBOBOX
Private Sub DropLevelComboBox_Change()
   If Not LevelBoxOnUpdate(DropLevelComboBox, SECTION_COMPASS_RULE_2D, KEY_DIAGRAM_LEVEL) Then
      PopulateDropLevelComboBox
      Beep
   End If
   RedrawCompassRuleFile
End Sub

Private Sub PopulateDropLevelComboBox()
   PopulateLevelBox DropLevelComboBox, SECTION_COMPASS_RULE_2D, KEY_DIAGRAM_LEVEL
End Sub



'DROP DIAGRAM PRELIMINARY COLOR COMBOBOX
Private Sub DropPreColorComboBox_AfterUpdate()
   ColorBoxOnUpdate DropPreColorComboBox, SECTION_COMPASS_RULE_2D, KEY_DIAGRAM_PRE_COLOR
End Sub

Private Sub DropPreColorComboBox_Change()
   RedrawCompassRuleFile
End Sub

Private Sub PopulateDropPreColorComboBox()
   PopulateColorBox DropPreColorComboBox, SECTION_COMPASS_RULE_2D, KEY_DIAGRAM_PRE_COLOR
End Sub



'COLOR CHOOSER BUTTON
Private Sub PreColorPickButton_Click()
   Dim MyColor As String
   If ChooseMyTableColor(MyColor) Then
      DropPreColorComboBox.text = MyColor
      DropPreColorComboBox_AfterUpdate
   End If
End Sub



'DROP DIAGRAM FINAL COLOR COMBOBOX
Private Sub DropFinColorComboBox_AfterUpdate()
   ColorBoxOnUpdate DropFinColorComboBox, SECTION_COMPASS_RULE_2D, KEY_DIAGRAM_FIN_COLOR
End Sub

Private Sub DropFinColorComboBox_Change()
   RedrawCompassRuleFile
End Sub

Private Sub PopulateDropFinColorComboBox()
   PopulateColorBox DropFinColorComboBox, SECTION_COMPASS_RULE_2D, KEY_DIAGRAM_FIN_COLOR
End Sub




'COLOR CHOOSER BUTTON
Private Sub FinColorPickButton_Click()
   Dim MyColor As String
   If ChooseMyTableColor(MyColor) Then
      DropFinColorComboBox.text = MyColor
      DropFinColorComboBox_AfterUpdate
   End If
End Sub



'DROP DIAGRAM STYLE COMBOBOX
Private Sub DropStyleComboBox_Change()
   If Not LineStyleBoxOnUpdate(DropStyleComboBox, SECTION_COMPASS_RULE_2D, KEY_DIAGRAM_STYLE) Then
      PopulateDropStyleComboBox
      Beep
   End If
   RedrawCompassRuleFile
End Sub

Private Sub PopulateDropStyleComboBox()
   PopulateLinestyleBox DropStyleComboBox, SECTION_COMPASS_RULE_2D, KEY_DIAGRAM_STYLE
End Sub



'DROP DIAGRAM POINT NAME CHECKBOX
Private Sub DropNameCheckBox_Click()
   SaveCheckBoxSetting DropNameCheckBox, SECTION_COMPASS_RULE_2D, KEY_DIAGRAM_OPTION_POINT_NAME
   RedrawCompassRuleFile
End Sub



'DROP DIAGRAM WEIGHT COMBOBOX
Private Sub DropWeightComboBox_Change()
   WeightBoxOnUpdate DropWeightComboBox, SECTION_COMPASS_RULE_2D, KEY_DIAGRAM_WEIGHT
   RedrawCompassRuleFile
End Sub

Private Sub PopulateDropWeightComboBox()
   PopulateWeightBox DropWeightComboBox, SECTION_COMPASS_RULE_2D, KEY_DIAGRAM_WEIGHT
End Sub



'DROP DIAGRAM POINT DESCRIPTION CHECKBOX
Private Sub DropDescCheckBox_Click()
   SaveCheckBoxSetting DropDescCheckBox, SECTION_COMPASS_RULE_2D, KEY_DIAGRAM_OPTION_DESCRIPTION
   RedrawCompassRuleFile
End Sub



'DROP DIAGRAM FONT COMBOBOX
Private Sub DropFontComboBox_Change()
   If Not FontBoxOnUpdate(DropFontComboBox, SECTION_COMPASS_RULE_2D, KEY_DIAGRAM_FONT) Then
      PopulateDropFontComboBox
      Beep
   End If
   RedrawCompassRuleFile
End Sub

Private Sub PopulateDropFontComboBox()
   PopulateFontBox DropFontComboBox, SECTION_COMPASS_RULE_2D, KEY_DIAGRAM_FONT
End Sub



'LEADER LINE LEVEL COMBOBOX
Private Sub LevelComboBox2_Change()
   If Not LevelBoxOnUpdate(LevelComboBox2, SECTION_COMPASS_RULE_2D, KEY_LEVEL2) Then
      PopulateLevelComboBox2
      Beep
   End If
   RedrawCompassRuleFile
End Sub

Private Sub PopulateLevelComboBox2()
   PopulateLevelBox LevelComboBox2, SECTION_COMPASS_RULE_2D, KEY_LEVEL2
End Sub




'DROP DIAGRAM LEADER LINE CHECKBOX
Private Sub LeaderLineCheckBox_Click()
   SaveCheckBoxSetting LeaderLineCheckBox, SECTION_COMPASS_RULE_2D, KEY_DIAGRAM_OPTION_LEADER
   RedrawCompassRuleFile
End Sub

'---END DROP DIAGRAM FRAME---



'TURN OFF DROP DIAGRAMS CHECKBOX
Private Sub DiagramOffCheckBox_Click()
   SaveCheckBoxSetting DiagramOffCheckBox, SECTION_COMPASS_RULE_2D, KEY_OPTION_DROP_DIAGRAM_OFF
   RedrawCompassRuleFile
End Sub



'---BEGIN DROP SNAP DIAGRAM FRAME---
'CALCULATE AVERAGE DROP BUTTON
Private Sub CalcAverageButton_Click()
'CALC THE RAW
   Dim ThePointsArray As Variant
   ThePointsArray = CalcRaw(False, Nothing)

'APPLY APPROPRIATE ADJUSTMENTS
'COMPASS RULE
   CompassRulePointsArray ThePointsArray

'COORDINATE TRANSFORMATION IF ANY
   TransformPointsArray ThePointsArray

'CALCULATE THE AVERAGE DROP
   CalcDropAverage ThePointsArray
End Sub



'DROP SNAP DIAGRAM X-AXIS TEXTBOX
Private Sub XAxisOffsetTextBox_AfterUpdate()
   SnapOffsetEntry XAxisOffsetTextBox, KEY_X_AXIS_OFFSET
   UpdateOppLabels
End Sub

Private Sub XAxisOffsetTextBox_Enter()
   SelectAllText XAxisOffsetTextBox
End Sub



'DROP SNAP DIAGRAM Y-AXIS TEXTBOX
Private Sub YAxisOffsetTextBox_AfterUpdate()
   SnapOffsetEntry YAxisOffsetTextBox, KEY_Y_AXIS_OFFSET
   UpdateOppLabels
End Sub

Private Sub YAxisOffsetTextBox_Enter()
   SelectAllText YAxisOffsetTextBox
End Sub

Private Sub SnapOffsetEntry(ByRef theTextbox As TextBox, ByVal Key As String)
   If IsNumeric(theTextbox.text) Then
      Dim theValue As Double
      theValue = Round(CDbl(theTextbox.text), 2)
      If (theValue < 100) And (theValue > -100) Then
         theTextbox.text = FormatNumber(CDbl(theTextbox.text), 2, vbTrue, vbFalse, vbFalse)
         SaveSetting APP_NAME, SECTION_COMPASS_RULE_2D, Key, theTextbox.text
      Else
         RestoreTextBox theTextbox, Key
      End If
   Else
      RestoreTextBox theTextbox, Key
   End If
End Sub

Private Sub RestoreTextBox(ByRef theTextbox As TextBox, ByVal Key As String)
   theTextbox.text = GetSetting(APP_NAME, SECTION_COMPASS_RULE_2D, Key, "0.00")
   Beep
End Sub



'DRAW OPPOSITES CHECKBOX
Private Sub OppositesCheckBox_Click()
   UpdateOppLabels
   SaveCheckBoxSetting OppositesCheckBox, SECTION_COMPASS_RULE_2D, KEY_OPTION_OPPOSITES
End Sub



'PLACE DROP SNAP DIAGRAM BUTTON
Private Sub DrawSnapButton_Click()
   Me.Hide
   CommandState.StartPrimitive New CompassRuleDropSnap
End Sub

'---END DROP SNAP DIAGRAM FRAME---


'**************************************************************************************
'/////////////////////////////////////TEMPLATES\\\\\\\\\\\\\\\\\\\\\\\\\\\\\\\\\\\\\\\\
'**************************************************************************************
'************TRAVERSE SETTINGS TAB***********
Private Function CreateTraverseTextTextTemplate() As TextElement
   Set CreateTraverseTextTextTemplate = CreateTextTemplate(SECTION_COMPASS_RULE_2D, _
                                                           TraverseTextFontComboBox, _
                                                           KEY_TRAV_TEXT_FONT, _
                                                           TraverseTextLevelComboBox, _
                                                           KEY_TRAV_TEXT_LEVEL, _
                                                           TraverseTextWeightComboBox, _
                                                           TraverseTextColorComboBox, _
                                                           TraverseTextStyleComboBox, _
                                                           KEY_TRAV_TEXT_STYLE, , _
                                                           msdTextJustificationLeftCenter)
End Function



Private Function CreateTraverseLineTemplate() As LineElement
   Set CreateTraverseLineTemplate = CreateLineTemplate(SECTION_COMPASS_RULE_2D, _
                                                       TraverseLineLevelComboBox, _
                                                       KEY_TRAV_LINE_LEVEL, _
                                                       TraverseLineWeightComboBox, _
                                                       TraverseLineColorComboBox, _
                                                       TraverseLineStyleComboBox, _
                                                       KEY_TRAV_LINE_STYLE)
End Function



Private Function CreateTraverseSymbolTemplate() As LineElement
   Set CreateTraverseSymbolTemplate = CreateLineTemplate(SECTION_COMPASS_RULE_2D, _
                                                         TraverseSymbolLevelComboBox, _
                                                         KEY_TRAV_SYMBOL_LEVEL, _
                                                         TraverseSymbolWeightComboBox, _
                                                         TraverseSymbolColorComboBox, _
                                                         TraverseSymbolStyleComboBox, _
                                                         KEY_TRAV_SYMBOL_STYLE)
End Function


'********SIDE SHOT SETTINGS TAB**************
Private Function CreateSideShotTextTextTemplate() As TextElement
   Set CreateSideShotTextTextTemplate = CreateTextTemplate(SECTION_COMPASS_RULE_2D, _
                                                           SideShotTextFontComboBox, _
                                                           KEY_SIDE_TEXT_FONT, _
                                                           SideShotTextLevelComboBox, _
                                                           KEY_SIDE_TEXT_LEVEL, _
                                                           SideShotTextWeightComboBox, _
                                                           SideShotTextColorComboBox, _
                                                           SideShotTextStyleComboBox, _
                                                           KEY_SIDE_TEXT_STYLE, , _
                                                           msdTextJustificationLeftCenter)
End Function



Private Function CreateSideShotLineTemplate() As LineElement
   Set CreateSideShotLineTemplate = CreateLineTemplate(SECTION_COMPASS_RULE_2D, _
                                                       SideShotLineLevelComboBox, _
                                                       KEY_SIDE_LINE_LEVEL, _
                                                       SideShotLineWeightComboBox, _
                                                       SideShotLineColorComboBox, _
                                                       SideShotLineStyleComboBox, _
                                                       KEY_SIDE_LINE_STYLE)
End Function



Private Function CreateSideShotSymbolTemplate() As LineElement
   Set CreateSideShotSymbolTemplate = CreateLineTemplate(SECTION_COMPASS_RULE_2D, _
                                                         SideShotSymbolLevelComboBox, _
                                                         KEY_SIDE_SYMBOL_LEVEL, _
                                                         SideShotSymbolWeightComboBox, _
                                                         SideShotSymbolColorComboBox, _
                                                         SideShotSymbolStyleComboBox, _
                                                         KEY_SIDE_SYMBOL_STYLE)
End Function



Private Function CreateMiniCellTextTemplate() As TextElement
   Dim charSize As Double
   charSize = CDbl(FontSizeTextBox.text)
   Set CreateMiniCellTextTemplate = CreateTextTemplate(SECTION_COMPASS_RULE_2D, _
                                                       MiniCellFontComboBox, _
                                                       KEY_MINI_CELL_FONT, _
                                                       MiniCellLevelComboBox, _
                                                       KEY_MINI_CELL_LEVEL, _
                                                       MiniCellWeightComboBox, _
                                                       MiniCellColorComboBox, _
                                                       MiniCellstyleComboBox, _
                                                       KEY_MINI_CELL_STYLE, charSize, _
                                                       msdTextJustificationLeftCenter)
End Function



'********DROP DIAGRAM SETTINGS TAB***********
'==============PRELIMINARY DROP DIAGRAM TEXT TEMPLATE==============
Public Function CreatePreDropDiagramTextTemplate() As TextElement
   Set CreatePreDropDiagramTextTemplate = CreateTextTemplate(SECTION_COMPASS_RULE_2D, _
                                                             DropFontComboBox, _
                                                             KEY_DIAGRAM_FONT, _
                                                             DropLevelComboBox, _
                                                             KEY_DIAGRAM_LEVEL, _
                                                             DropWeightComboBox, _
                                                             DropPreColorComboBox, _
                                                             DropStyleComboBox, _
                                                             KEY_DIAGRAM_STYLE, , _
                                                             msdTextJustificationLeftCenter)
End Function





'==============FINAL DROP DIAGRAM TEXT TEMPLATE==============
Private Function CreateFinDropDiagramTextTemplate() As TextElement
   Set CreateFinDropDiagramTextTemplate = CreateTextTemplate(SECTION_COMPASS_RULE_2D, _
                                                             DropFontComboBox, _
                                                             DropFontComboBox, _
                                                             DropLevelComboBox, _
                                                             KEY_DIAGRAM_LEVEL, _
                                                             DropWeightComboBox, _
                                                             DropFinColorComboBox, _
                                                             DropStyleComboBox, _
                                                             KEY_DIAGRAM_STYLE, , _
                                                             msdTextJustificationLeftCenter)
End Function



Private Function CreateDropLeaderTemplate() As LineElement
   Set CreateDropLeaderTemplate = CreateLineTemplate(SECTION_COMPASS_RULE_2D, _
                                                     LevelComboBox2, _
                                                     KEY_LEVEL2, _
                                                     DropWeightComboBox, _
                                                     DropPreColorComboBox, _
                                                     DropStyleComboBox, _
                                                     KEY_DIAGRAM_STYLE)
End Function



'**************************************************************************************
'////////////////////////////////////////DISPLAY\\\\\\\\\\\\\\\\\\\\\\\\\\\\\\\\\\\\\\\
'**************************************************************************************
Private Sub UpdateCaption()
   If Me.FileLoaded Then
'FILE LOADED, INCLUDE FILENAME
      Me.Caption = COMMAND_NAME_COMPASS_RULE_2D & "-" & GetJustTheCompassRuleFilename()
   Else
'NO FILE LOADED, JUST USE COMMAND NAME
      Me.Caption = COMMAND_NAME_COMPASS_RULE_2D
   End If
End Sub


Public Sub ClearAverageDrop()
   AverageXLabel.Caption = ""
   AverageYLabel.Caption = ""
   NumberOfDropsLabel.Caption = ""
End Sub



Private Sub UpdateStatistics(NumSetups As Long, _
                             NumSideshots As Long, _
                             NumLegs As Long, _
                             travLength As Double, _
                             ClosingObsPoint As Point2d)
   ClearStats
   SetupsNumLabel.Caption = FormatNumber(NumSetups, 0, False, vbFalse, vbFalse)
   SideshotsNumberLabel.Caption = FormatNumber(NumSideshots, 0, False, vbFalse, vbFalse)
   TravLengthLabel.Caption = FormatNumber(travLength, 3, vbTrue, vbFalse, vbTrue)
   NumberOfLegsLabel.Caption = FormatNumber(NumLegs, 0, vbFalse, vbFalse, vbFalse)
   If NoneYetOption.value = True Or NumLegs < 2 Then
      NorthMisclosureLabel.Caption = NOT_APPLICABLE_STRING
      EastingMiscloseLabel.Caption = NOT_APPLICABLE_STRING
      MiscloseDistanceLabel.Caption = NOT_APPLICABLE_STRING
      MiscloseDirectionLabel.Caption = NOT_APPLICABLE_STRING
      TraversePrecLabel.Caption = NOT_APPLICABLE_STRING
   Else
      If ToPointOption.value = True Then
         Dim ClosingPoint As Point2d
         ClosingPoint.Y = GetNorthing(CloseNorthTextBox)
         ClosingPoint.X = GetEasting(CloseEastTextBox)
      Else
         ClosingPoint.Y = GetNorthing(TextNorthing)
         ClosingPoint.X = GetEasting(TextEasting)
      End If
      Dim Misclosure As Point2d
      Misclosure.Y = ClosingObsPoint.Y - ClosingPoint.Y
      Misclosure.X = ClosingObsPoint.X - ClosingPoint.X
      NorthMisclosureLabel.Caption = FormatNumber(Misclosure.Y, 4, vbTrue, vbFalse, vbFalse)
      EastingMiscloseLabel.Caption = FormatNumber(Misclosure.X, 4, vbTrue, vbFalse, vbFalse)
      MiscloseDistanceLabel.Caption = FormatNumber(InverseDistance(Misclosure.Y, Misclosure.X), 3, vbTrue, vbFalse, vbFalse)
      MiscloseDirectionLabel.Caption = SAzToAzimuthStr((InverseAz(Misclosure.Y, Misclosure.X)), 4, GetAngleStyle())
      TraversePrecLabel.Caption = PrecisionString(MiscloseDistanceLabel.Caption, TravLengthLabel.Caption)
   End If
End Sub



Private Sub UpdateStats()
   Dim RawArray As Variant
   RawArray = CalcRaw(False, Nothing)
   CompassRulePointsArray RawArray
End Sub



Private Sub ClearStats()
   SetupsNumLabel.Caption = ""
   SideshotsNumberLabel.Caption = ""
   NumberOfLegsLabel.Caption = ""
   TravLengthLabel.Caption = ""
   NorthMisclosureLabel.Caption = ""
   EastingMiscloseLabel.Caption = ""
   MiscloseDistanceLabel.Caption = ""
   MiscloseDirectionLabel.Caption = ""
   TraversePrecLabel.Caption = ""
End Sub



Private Sub ClearRerunStats()
   RerunMisNorthLabel.Caption = ""
   RerunMisEastLabel.Caption = ""
   RerunMisDisLabel.Caption = ""
   RerunIntNorthMisLabel.Caption = ""
   RerunIntEastMisLabel.Caption = ""
   RerunIntDistMisLabel.Caption = ""
End Sub



Private Sub UpdateOppLabels()
   If OppositesCheckBox.value Then
      OppositeXLabel.Caption = OppositeString(XAxisOffsetTextBox)
      OppositeYLabel.Caption = OppositeString(YAxisOffsetTextBox)
      OppHeadLabel.Visible = True
   Else
      OppositeXLabel.Caption = STRING_SPACE
      OppositeYLabel.Caption = STRING_SPACE
      OppHeadLabel.Visible = False
   End If
End Sub



Private Function OppositeString(ByVal NumString As String) As String
   Dim offset As Double
   offset = CDbl(NumString)
   offset = -offset
   OppositeString = FormatNumber(offset, 2, vbTrue, vbFalse, vbFalse)
End Function



'**************************************************************************************
'/////////////////////////////////CONTROL STATES\\\\\\\\\\\\\\\\\\\\\\\\\\\\\\\\\\\\\\\
'**************************************************************************************
Private Sub AllButtonStates()
   Dim enabledState As Boolean
   enabledState = Me.FileLoaded

   Dim BackColor As OLE_COLOR
   BackColor = BackOLE_COLOR(enabledState)

'ENTRY PAGE
'REDRAW BUTTON
   RedrawButton.enabled = enabledState

'SAVE AS NEW BUTTON
   CopyNewButton.enabled = enabledState

'STARTING POINT FRAME
   FrameStart.enabled = enabledState

'STARTING POINT DRAW SYMBOL AND LABEL CHECK BOX
   DrawStartCheckBox.enabled = enabledState

'BACK SIGHT AZIMUTH
   FirstBSLabel.enabled = enabledState
   FirstBSAzTextBox.enabled = enabledState
   FirstBSAzTextBox.BackColor = BackColor

'STARTING POINT
   TextElevation.enabled = enabledState
   TextElevation.BackColor = BackColor
   TextNorthing.enabled = enabledState
   TextNorthing.BackColor = BackColor
   TextEasting.enabled = enabledState
   TextEasting.BackColor = BackColor
   ButtonPick.enabled = enabledState
   PickZButton.enabled = enabledState
   LabelEl.enabled = enabledState
   LabelNorthing.enabled = enabledState
   LabelEasting.enabled = enabledState

'TRAVERSES FRAME
   TraversesFrame.enabled = enabledState
  
'TRAVERSES LISTBOX
   TraversesListBox.enabled = enabledState
   TraversesListBox.BackColor = BackColor
   
'TRAVERSE EDIT/DELETE BUTTONS
   TravEditDeleteStates

'TRAVERSES ADD BUTTON
   TraversesAddButton.enabled = enabledState

'SIDESHOTS FRAME
   SideShotsFrame.enabled = enabledState
   
'SIDESHOTS LISTBOX
   SideshotsListBox.enabled = enabledState
   SideshotsListBox.BackColor = BackColor

'SIDESHOTS EDIT/DELETE BUTTON IF SHOULD
   SideEditDeleteStates
   
'SIDESHOTS INSERT BUTTON
   SideInsertStates

'DROP DIAGRAM AZIMUTH
   DropAzimuthLabel.enabled = enabledState
   DropAzimuthTextBox.enabled = enabledState
   DropAzimuthTextBox.BackColor = BackColor
   Plus180Button.enabled = enabledState

'DROP DIAGRAM MARK AND UNMARK BUTTONS
   MarkAllDropsButton.enabled = enabledState
   UnmarkAllDropsButton.enabled = enabledState
   
'TRAVERSES LABELS
   LineLabel.enabled = enabledState
   PointNameLabel.enabled = enabledState
   BSLabel.enabled = enabledState
   FSLabel.enabled = enabledState
   HDLabel.enabled = enabledState
   DescriptionLabel.enabled = enabledState

'SIDE SHOTS LABELS
   SideRefLabel.enabled = enabledState
   SideFSLabel.enabled = enabledState
   SideHDLabel.enabled = enabledState
   SidePointNameLabel.enabled = enabledState
   SideDescriptionLabel.enabled = enabledState
   SideBSLabel.enabled = enabledState
   SideUseDropLabel.enabled = enabledState
  
'CLOSURE PAGE
'CLOSURE TYPE
   ClosureTypeFrame.enabled = enabledState
   NoneYetOption.enabled = enabledState
   ToBeginningOption.enabled = enabledState
   ToPointOption.enabled = enabledState
   ClosureTypeStates

'CLOSING POINT OBSERVATION
   ClosingPointObsStates

'STATISTICS PANE
   StatisticsOnOff enabledState

'ADJUSTMENT PAGE
   AdjustmentsOnOff enabledState
   TransformationOnOff enabledState
   ChooseInterPointOnOff enabledState
   ChooseTranslationOnOff enabledState

'REPORTS PAGE
   TextFieldsOnOff enabledState
   InversePrecisionOnOff enabledState
   FilenameStates
   IncludeSideshotsStates
   ExportCoordinatesOnOff enabledState
   
'DROP DIAGRAM SETTINGS PAGE
   DropSnapOnOff enabledState
End Sub



Private Sub ClosingPointObsStates()
   Dim enabledState As Boolean
   enabledState = (Not NoneYetOption.value) And ClosureTypeFrame.enabled
   ClosingPointFrame.enabled = enabledState
   LastForesightOption.enabled = enabledState
   LastTraverseOption.enabled = enabledState
   CPNameAndDescStates
End Sub



Private Sub TravEditDeleteStates()
'CHECK IF A TRAVERSE IS SELECTED
   If TraversesListBox.listIndex >= 0 Then
      Dim state As Boolean
      state = True
   Else
      state = False
   End If

'ENABLE/DISABLE EDIT AND DELETE BUTTONS
'TRAVERSES DELETE BUTTON
   TraversesDeleteButton.enabled = state
   
'TRAVERSES EDIT BUTTON
   TraversesEditButton.enabled = state
End Sub



Private Sub SideInsertStates()
'INITIALIZE FLAG
   Dim state As Boolean
   state = False

'CHECK IF A TRAVERSE IS SELECTED
   If TraversesListBox.listIndex >= 0 Then
         state = True
   End If

'ENABLE/DISABLE INSERT BUTTON
   SideShotsAddButton.enabled = state
   FileInsertButton.enabled = state
End Sub



Private Sub SideEditDeleteStates()
'INITIALIZE FLAG
   Dim state As Boolean
   state = False

'CHECK IF A TRAVERSE IS SELECTED
   If TraversesListBox.listIndex >= 0 Then
'CHECK IF A SIDE SHOT IS SELECTED
      If SideshotsListBox.listIndex >= 0 Then
         state = True
      End If
   End If

'ENABLE/DISABLE EDIT AND DELETE BUTTONS
'SIDE SHOTS DELETE BUTTON
   SideShotsDeleteButton.enabled = state
   
'SIDE SHOTS EDIT BUTTON
   SideShotsEditButton.enabled = state
End Sub



Private Sub ClosureTypeStates()
   Dim enabledState As Boolean
   enabledState = ToPointOption.value And ToPointOption.enabled
   Dim BackColor As OLE_COLOR
   BackColor = BackOLE_COLOR(enabledState)

   CloseNorthLabel.enabled = enabledState
   CloseNorthTextBox.BackColor = BackColor
   CloseNorthTextBox.enabled = enabledState
   CloseEastLabel.enabled = enabledState
   CloseEastTextBox.BackColor = BackColor
   CloseEastTextBox.enabled = enabledState
   ClosePointPickButton.enabled = enabledState
End Sub



Private Sub CPNameAndDescStates()
   If LastForesightOption.value And LastForesightOption.enabled And (Not ToBeginningOption.value) Then
      NameAndStateOnOff True
   Else
      NameAndStateOnOff False
   End If
End Sub



Private Sub StatisticsOnOff(ByVal state As Boolean)
   If Not state Then
      ClearStats
   End If

   StatisticsFrame.enabled = state
   NumOfSetupsLabel.enabled = state
   SetupsNumLabel.enabled = state
   LengthOfTravLabel.enabled = state
   TravLengthLabel.enabled = state
   SidesNumberLabel.enabled = state
   SideshotsNumberLabel.enabled = state
   MiscloseNorthLabel.enabled = state
   NorthMisclosureLabel.enabled = state
   EastingMisclosureLabel.enabled = state
   EastingMiscloseLabel.enabled = state
   MisclosureDistanceLabel.enabled = state
   MiscloseDistanceLabel.enabled = state
   MisclosureDirectionLabel.enabled = state
   MiscloseDirectionLabel.enabled = state
   PrecisionLabel.enabled = state
   TraversePrecLabel.enabled = state
   NumberLegsLabel.enabled = state
   NumberOfLegsLabel.enabled = state
End Sub



Private Sub DropSnapOnOff(ByVal enabledState As Boolean)
   Dim BackColor As OLE_COLOR
   BackColor = BackOLE_COLOR(enabledState)

   SnapFrame.enabled = enabledState
   XAxisLabel.enabled = enabledState
   XAxisOffsetTextBox.enabled = enabledState
   XAxisOffsetTextBox.BackColor = BackColor
   YAxisLabel.enabled = enabledState
   YAxisOffsetTextBox.enabled = enabledState
   YAxisOffsetTextBox.BackColor = BackColor
   DrawSnapButton.enabled = enabledState
   OppositesCheckBox.enabled = enabledState
   OppositeXLabel.enabled = enabledState
   OppositeYLabel.enabled = enabledState
   OppHeadLabel.enabled = enabledState
   AverageLabel.enabled = enabledState
   DropXAxisLabel.enabled = enabledState
   DropYAxisLabel.enabled = enabledState
   AverageXLabel.enabled = enabledState
   AverageYLabel.enabled = enabledState
   CalcAverageButton.enabled = enabledState
   NumberOfDropsLabel.enabled = enabledState
   DropCountLabel.enabled = enabledState
End Sub



Private Sub NameAndStateOnOff(ByVal enabledState As Boolean)
   Dim BackColor As OLE_COLOR
   BackColor = BackOLE_COLOR(enabledState)

   NameAndDescCheckBox.enabled = enabledState
   CloseNameLabel.enabled = enabledState
   CloseNameTextBox.BackColor = BackColor
   CloseNameTextBox.enabled = enabledState
   CloseDescLabel.enabled = enabledState
   CloseDescTextBox.enabled = enabledState
   CloseDescTextBox.BackColor = BackColor
   ElevationLabel.enabled = enabledState
   ElevationTextBox.enabled = enabledState
   ElevationTextBox.BackColor = BackColor
   IncludeElCheckBox.enabled = enabledState
End Sub



Private Sub SolutionRulesOnOff(state As Boolean)
   SolutionFrame.enabled = state
   HoldingCoursesOption.enabled = state
   InverseCourseOption.enabled = state
   SolutionRulesStates
End Sub



Private Sub SolutionRulesStates()
   If HoldingCoursesOption.value = True And HoldingCoursesOption.enabled Then
      HoldingPrecisionOptionOnOff True
   Else
      HoldingPrecisionOptionOnOff False
   End If
End Sub



Private Sub HoldingPrecisionOptionOnOff(state As Boolean)
   SecondOption.enabled = state
   HundredthOption.enabled = state
   ThousandthOption.enabled = state
   TenthSecondOption.enabled = state
   RerunClosureFrame.enabled = state
   RerunMisNorthingLabel.enabled = state
   RerunMisNorthLabel.enabled = state
   RerunMisEastingLabel.enabled = state
   RerunMisEastLabel.enabled = state
   RerunMisDistanceLabel.enabled = state
   RerunMisDisLabel.enabled = state
   IntermediatePointMiscloseStates
End Sub



Private Sub IntermediatePointMiscloseStates()
   If RerunClosureFrame.enabled And TwoPointAdjustmentOption.value = True Then
      IntermediatePointMiscloseOnOff True
   Else
      IntermediatePointMiscloseOnOff False
   End If
End Sub



Private Sub IntermediatePointMiscloseOnOff(state As Boolean)
   IntermediatePointLabel.enabled = state
   RerunIntNorthingMisLabel.enabled = state
   RerunIntNorthMisLabel.enabled = state
   RerunIntEastingMisLabel.enabled = state
   RerunIntEastMisLabel.enabled = state
   RerunIntDistanceMisLabel.enabled = state
   RerunIntDistMisLabel.enabled = state
End Sub



Private Sub TransformationOnOff(ByVal enabledState As Boolean)
   TranslationCheckBox.enabled = enabledState
   MoveAllHoldingObsLabel.enabled = enabledState
   ChooseMoveObsComboBox.enabled = enabledState
   TranslationCoordLabel.enabled = enabledState
   MoveToNorthLabel.enabled = enabledState
   MoveToNorthTextBox.enabled = enabledState
   MoveToEastLabel.enabled = enabledState
   MoveToEastTextBox.enabled = enabledState
   PickMoveToButton.enabled = enabledState
   RotationStates
End Sub



Private Sub ChooseTranslationOnOff(ByVal enabledState As Boolean)
   Dim BackColor As OLE_COLOR
   BackColor = BackOLE_COLOR(enabledState)

   TranslationCoordLabel.enabled = enabledState
   MoveToNorthLabel.enabled = enabledState
   MoveToEastLabel.enabled = enabledState
   MoveToNorthTextBox.enabled = enabledState
   MoveToEastTextBox.enabled = enabledState
   PickMoveToButton.enabled = enabledState
   MoveAllHoldingObsLabel.enabled = enabledState
   ChooseMoveObsComboBox.enabled = enabledState
   MoveToNorthTextBox.BackColor = BackColor
   MoveToEastTextBox.BackColor = BackColor
   ChooseMoveObsComboBox.BackColor = BackColor
End Sub



Private Sub RotationStates()
   RotationCheckBox.enabled = TranslationCheckBox.enabled And TranslationCheckBox.value
   RotationTextStates
End Sub



Private Sub RotationTextStates()
   If RotationCheckBox.value And RotationCheckBox.enabled Then
      RotationTextBox.enabled = True
      RotationTextBox.BackColor = BackOLE_COLOR(True)
   Else
      RotationTextBox.enabled = False
      RotationTextBox.BackColor = BackOLE_COLOR(False)
   End If
End Sub



Private Sub ChooseInterPointOnOff(enabledState As Boolean)
   Dim BackColor As OLE_COLOR
   BackColor = BackOLE_COLOR(enabledState)
   
   TwoPtHoldingObsLabel.enabled = enabledState
   ChooseTwoPtObsComboBox.enabled = enabledState
   ChooseTwoPtObsComboBox.BackColor = BackColor
   TwoPtMoveToLabel.enabled = enabledState
   TwoPtNorthLabel.enabled = enabledState
   TwoPtNorthTextBox.enabled = enabledState
   TwoPtNorthTextBox.BackColor = BackColor
   TwoPtEastLabel.enabled = enabledState
   TwoPtEastTextBox.enabled = enabledState
   TwoPtEastTextBox.BackColor = BackColor
   TwoPtPickButton.enabled = enabledState
End Sub



Private Sub AngluarErrorAngleStates()
   If AngularAdjustmentCheckBox.enabled And AngularAdjustmentCheckBox.value = True Then
      AngularAdjustmentTextBox.enabled = True
      AngularAdjustmentTextBox.BackColor = BackOLE_COLOR(True)
   Else
      AngularAdjustmentTextBox.enabled = False
      AngularAdjustmentTextBox.BackColor = BackOLE_COLOR(False)
   End If
End Sub



Private Sub AngluarErrorStates()
   If ApplyAdjustmentCheckBox.enabled And ApplyAdjustmentCheckBox.value = True Then
      AngularAdjustmentCheckBox.enabled = True
   Else
      AngularAdjustmentCheckBox.enabled = False
   End If
   AngluarErrorAngleStates
End Sub



Private Sub ApplyStates()
   Dim enabled As Boolean
   enabled = False
   If TraversesListBox.ListCount < 2 Then
   ElseIf (TraversesListBox.ListCount = 2) And LastTraverseOption.value Then
   ElseIf (TraversesListBox.ListCount = 2) And ToBeginningOption.value Then
   ElseIf NoneYetOption.value Then
   Else
      enabled = True
   End If
   ApplyAdjustmentCheckBox.enabled = enabled
   CompassRuleStates
End Sub



Private Sub CompassRuleStates()
   If ApplyAdjustmentCheckBox.enabled And ApplyAdjustmentCheckBox.value = True Then
      Dim enabledState As Boolean
      enabledState = True
   Else
      enabledState = False
   End If
   
   AngularAdjustmentCheckBox.enabled = enabledState
   SingleCompassRuleOption.enabled = enabledState
   TwoPointAdjustmentOption.enabled = enabledState
   InverseCourseOption.enabled = enabledState
   HoldingCoursesOption.enabled = enabledState
   SolutionFrame.enabled = enabledState
   CompassRuleStatusFrame.enabled = enabledState
   CompassRuleStatusLabel.enabled = enabledState
   AngluarErrorStates
   SolutionRulesStates
   UpdateStats
End Sub



Private Sub AdjustmentsOnOff(state As Boolean)
   PreliminaryOption.enabled = state
   FinalOption.enabled = state
   ApplyAdjustmentCheckBox.enabled = state
   ApplyStates
End Sub




Private Sub TextFieldsOnOff(ByVal enabledState As Boolean)
   Dim BackColor As OLE_COLOR
   BackColor = BackOLE_COLOR(enabledState)
   
   DateLabel.enabled = enabledState
   DateTextBox.enabled = enabledState
   DateTextBox.BackColor = BackColor
   ProjectLabel.enabled = enabledState
   ProjectTextBox.enabled = enabledState
   ProjectTextBox.BackColor = BackColor
   OriginLabel.enabled = enabledState
   OriginTextBox.enabled = enabledState
   OriginTextBox.BackColor = BackColor
   AzimuthLabel.enabled = enabledState
   AzimuthTextBox.enabled = enabledState
   AzimuthTextBox.BackColor = BackColor
   FieldBookLabel.enabled = enabledState
   FieldBookTextBox.enabled = enabledState
   FieldBookTextBox.BackColor = BackColor
   NotesLabel.enabled = enabledState
   NotesTextBox.enabled = enabledState
   NotesTextBox.BackColor = BackColor
   ReportButton.enabled = enabledState
   DateButton.enabled = enabledState
End Sub



Private Sub IncludeSideshotsStates()
   IncludeSideShotsCheckBox.enabled = Me.FileLoaded
End Sub



Private Sub IncludePathStates()
   If ReportFilenameCheckBox.value = True And ReportFilenameCheckBox.enabled Then
      IncludePathCheckBox.enabled = True
   Else
      IncludePathCheckBox.enabled = False
   End If
End Sub



Private Sub FilenameStates()
   ReportFilenameCheckBox.enabled = Me.FileLoaded
   IncludePathStates
End Sub



Private Sub InversePrecisionOnOff(state As Boolean)
   InversePrecisionFrame.enabled = state
   Inv1secOption.enabled = state
   InvTenthSecOption.enabled = state
   hundredthFootOption.enabled = state
   ThousandthFootOption.enabled = state
End Sub



Private Sub ExportCoordinatesOnOff(state As Boolean)
   ExportFrame.enabled = state
   ExportButton.enabled = state
   ExportSidesCheckBox.enabled = state
End Sub



'**************************************************************************************
'///////////////////////////////////////FORM EVENTS\\\\\\\\\\\\\\\\\\\\\\\\\\\\\\\\\\\\
'**************************************************************************************
Private Sub UserForm_Initialize()
'BRING ENTRY PAGE TO FRONT
   Me.MultiPage1.value = 0

'MOVE INTO LAST POSITION
   If GetSetting(APP_NAME, SECTION_COMPASS_RULE_2D, KEY_START_TOP, "") = "" Then
      Me.StartUpPosition = 1
   Else
      Me.StartUpPosition = 0
      Me.Top = CDbl(GetSetting(APP_NAME, SECTION_COMPASS_RULE_2D, KEY_START_TOP, WINDOW_DEFAULT_TOP))
      Me.Left = CDbl(GetSetting(APP_NAME, SECTION_COMPASS_RULE_2D, KEY_START_LEFT, WINDOW_DEFAULT_LEFT))
   End If
   
'SET SIZE OF TRAVERSES LISTBOX COLUMNS
   TraversesListBox.ColumnCount = 6
   Dim ColumnWidthString As String
   ColumnWidthString = FormatNumber(0.46 * Column_Width_Multiplier, 2) & " in; " & _
                       FormatNumber(0.83 * Column_Width_Multiplier, 2) & " in; " & _
                       FormatNumber(1.3 * Column_Width_Multiplier, 2) & " in; " & _
                       FormatNumber(0.83 * Column_Width_Multiplier, 2) & " in; " & _
                       FormatNumber(0.83 * Column_Width_Multiplier, 2) & " in; " & _
                       FormatNumber(0.7 * Column_Width_Multiplier, 2) & " in"
   TraversesListBox.ColumnWidths = ColumnWidthString

'SET SIZE OF RAW DATA LISTBOX COLUMNS
   RawEntriesListBox.ColumnCount = 7
   ColumnWidthString = ColumnWidthString & "; " & FormatNumber(0.1 * Column_Width_Multiplier, 2) & " in"
   RawEntriesListBox.ColumnWidths = ColumnWidthString
   
   DropsListBox.ColumnCount = 4


'HIDE RAW DATA LISTBOX
   RawEntriesListBox.Visible = False
   DropsListBox.Visible = False

'SET SIZE OF SIDE SHOTS LISTBOX COLUMNS
   ColumnWidthString = FormatNumber(0.46 * Column_Width_Multiplier, 2) & " in; " & _
                       FormatNumber(0.83 * Column_Width_Multiplier, 2) & " in; " & _
                       FormatNumber(0.83 * Column_Width_Multiplier, 2) & " in; " & _
                       FormatNumber(0.7 * Column_Width_Multiplier, 2) & " in; " & _
                       FormatNumber(0.83 * Column_Width_Multiplier, 2) & " in; " & _
                       FormatNumber(1.3 * Column_Width_Multiplier, 2) & " in;" & _
                       FormatNumber(0.1 * Column_Width_Multiplier, 2) & " in"
   SideshotsListBox.ColumnCount = 7
   SideshotsListBox.ColumnWidths = ColumnWidthString

'POPULATE TRAVERSE LINE SETTINGS BOXES
   PopulateTraverseLineLevelComboBox
   PopulateTraverseLineColorComboBox
   PopulateTraverseLineStyleComboBox
   PopulateTraverseLineWeightComboBox

'POPULATE TRAVERSE SYMBOL SETTINGS BOXES
   PopulateTraverseSymbolLevelComboBox
   PopulateTraverseSymbolColorComboBox
   PopulateTraverseSymbolStyleComboBox
   PopulateTraverseSymbolWeightComboBox

'POPULATE SIDE SHOT LINE SETTINGS BOXES
   PopulateSideShotLineLevelComboBox
   PopulateSideShotLineColorComboBox
   PopulateSideShotLineStyleComboBox
   PopulateSideShotLineWeightComboBox

'POPULATE SIDE SHOT SYMBOL SETTINGS BOXES
   PopulateSideShotSymbolLevelComboBox
   PopulateSideShotSymbolColorComboBox
   PopulateSideShotSymbolStyleComboBox
   PopulateSideShotSymbolWeightComboBox
   
'POPULATE TRAVERSE TEXT SETTINGS BOXES
   PopulateTraverseTextLevelComboBox
   PopulateTraverseTextColorComboBox
   PopulateTraverseTextStyleComboBox
   PopulateTraverseTextWeightComboBox
   PopulateTraverseTextFontComboBox
   InitializeCheckBox TraversePointNameCheckBox, SECTION_COMPASS_RULE_2D, KEY_OPTION_TRAV_PT_NAME_CHK
   InitializeCheckBox TraverseDescriptionCheckBox, SECTION_COMPASS_RULE_2D, KEY_OPTION_TRAV_DESC_CHK
   InitializeCheckBox ElevCheckBox, SECTION_COMPASS_RULE_2D, KEY_OPTION_TRAV_ELEV_CHK

'POPULATE SIDE SHOT TEXT SETTINGS BOXES
   PopulateSideShotTextLevelComboBox
   PopulateSideShotTextColorComboBox
   PopulateSideShotTextStyleComboBox
   PopulateSideShotTextWeightComboBox
   PopulateSideShotTextFontComboBox
   InitializeCheckBox SideShotTextPointNameCheckBox, SECTION_COMPASS_RULE_2D, KEY_OPTION_SIDE_PT_NAME_CHK
   InitializeCheckBox SideShotTextDescriptionCheckBox, SECTION_COMPASS_RULE_2D, KEY_OPTION_SIDE_DESC_CHK

'POPULATE MINI CELL TEXT SETTINGS BOXES
   PopulateMiniCellLevelComboBox
   PopulateMiniCellColorComboBox
   PopulateMiniCellstyleComboBox
   PopulateMiniCellWeightComboBox
   PopulateMiniCellFontComboBox
   InitializeCheckBox UseMiniCellCheckBox, SECTION_COMPASS_RULE_2D, KEY_OPTION_CELL_USE_CELL_CHK
   FontSizeTextBox.text = GetSetting(APP_NAME, SECTION_COMPASS_RULE_2D, KEY_CELL_TEXT_FONT_SIZE, "0.50")

'INITIALIZE TRAVERSE TEXT OFFSET TEXT BOXES
   TravNameUDOffsetTextBox.text = GetSetting(APP_NAME, SECTION_COMPASS_RULE_2D, KEY_TRAV_NAME_OFFSET_UD, "1.00")
   TravNameLROffsetTextBox.text = GetSetting(APP_NAME, SECTION_COMPASS_RULE_2D, KEY_TRAV_NAME_OFFSET_LR, "1.00")
   TravDescUDOffsetTextBox.text = GetSetting(APP_NAME, SECTION_COMPASS_RULE_2D, KEY_TRAV_DESC_OFFSET_UD, "-0.45")
   TravDescLROffsetTextBox.text = GetSetting(APP_NAME, SECTION_COMPASS_RULE_2D, KEY_TRAV_DESC_OFFSET_LR, "1.00")
   elUDOSTextBox.text = GetSetting(APP_NAME, SECTION_COMPASS_RULE_2D, KEY_TRAV_ELEV_OFFSET_UD, "-2.00")
   elLRLOSTextBox.text = GetSetting(APP_NAME, SECTION_COMPASS_RULE_2D, KEY_TRAV_ELEV_OFFSET_LR, "1.00")

'INITIALIZE SIDE SHOT TEXT OFFSET TEXT BOXES
   SideNameUDOffsetTextBox.text = GetSetting(APP_NAME, SECTION_COMPASS_RULE_2D, KEY_SIDE_NAME_OFFSET_UD, "1.00")
   SideNameLROffsetTextBox.text = GetSetting(APP_NAME, SECTION_COMPASS_RULE_2D, KEY_SIDE_NAME_OFFSET_LR, "1.00")
   SideDescUDOffsetTextBox.text = GetSetting(APP_NAME, SECTION_COMPASS_RULE_2D, KEY_SIDE_DESC_OFFSET_UD, "-1.00")
   SideDescLROffsetTextBox.text = GetSetting(APP_NAME, SECTION_COMPASS_RULE_2D, KEY_SIDE_DESC_OFFSET_LR, "1.00")

'INITIALIZE MINI CELL TEXT OFFSET TEXT BOXES
   MiniCellNameUDTextBox.text = GetSetting(APP_NAME, SECTION_COMPASS_RULE_2D, KEY_CELL_NAME_OFFSET_UD, "1.00")
   MiniCellLRNameTextBox.text = GetSetting(APP_NAME, SECTION_COMPASS_RULE_2D, KEY_CELL_NAME_OFFSET_LR, "1.00")
   MiniCellUDDescTextBox.text = GetSetting(APP_NAME, SECTION_COMPASS_RULE_2D, KEY_CELL_DESC_OFFSET_UD, "-1.00")
   MinicellLRDescTextBox.text = GetSetting(APP_NAME, SECTION_COMPASS_RULE_2D, KEY_CELL_DESC_OFFSET_LR, "1.00")

'INITIALIZE FILENAME AND PATH CHECK BOXES
   InitializeCheckBox ReportFilenameCheckBox, SECTION_COMPASS_RULE_2D, KEY_OPTION_FILENAME
   InitializeCheckBox IncludePathCheckBox, SECTION_COMPASS_RULE_2D, KEY_OPTION_PATH

'INITIALIZE DRAW START CHECK BOX
   DrawStartCheckBox.value = True
   
'INITIALIZE SETUP SYMBOL
   Dim Options As String
   Options = GetSetting(APP_NAME, SECTION_COMPASS_RULE_2D, KEY_TRAV_SYMBOL, SYMBOL_1)
   Select Case Options
      Case SYMBOL_NONE
         OptionSetupSymNone.value = True
      Case SYMBOL_1
         OptionSetupSym1.value = True
      Case SYMBOL_2
         OptionSetupSym2.value = True
      Case SYMBOL_3
         OptionSetupSym3.value = True
      Case SYMBOL_4
         OptionSetupSym4.value = True
      Case SYMBOL_5
         OptionSetupSym5.value = True
      Case SYMBOL_6
         OptionSetupSym6.value = True
   End Select

'INITIALIZE REPORT INVERSE PRECISION
   Options = GetSetting(APP_NAME, SECTION_COMPASS_RULE_2D, KEY_REPROT_ANGLE_PREC, OPTION_PREC_ANG_SEC)
   Select Case Options
      Case OPTION_PREC_ANG_SEC
         Inv1secOption.value = True
      Case Else
         InvTenthSecOption.value = True
   End Select
   
   Options = GetSetting(APP_NAME, SECTION_COMPASS_RULE_2D, KEY_REPORT_DISTANCE_PREC, OPTION_PREC_DIST_FT01)
   Select Case Options
      Case OPTION_PREC_DIST_FT01
         hundredthFootOption.value = True
      Case Else
         ThousandthFootOption.value = True
   End Select

'INITIALIZE INCLUDE SIDE SHOTS CHECK BOX
   InitializeCheckBox IncludeSideShotsCheckBox, SECTION_COMPASS_RULE_2D, KEY_REPORT_OPTION_SIDESHOTS

'INITIALIZE DROP DIAGRAM SETTINGS
   PopulateDropLevelComboBox
   PopulateDropPreColorComboBox
   PopulateDropFinColorComboBox
   PopulateDropStyleComboBox
   PopulateDropWeightComboBox
   PopulateDropFontComboBox
   PopulateLevelComboBox2
   
'INITIALIZE DROP DIAGRAM CHECK BOXES
   InitializeCheckBox LeaderLineCheckBox, SECTION_COMPASS_RULE_2D, KEY_DIAGRAM_OPTION_LEADER
   InitializeCheckBox DropNameCheckBox, SECTION_COMPASS_RULE_2D, KEY_DIAGRAM_OPTION_POINT_NAME
   InitializeCheckBox DropDescCheckBox, SECTION_COMPASS_RULE_2D, KEY_DIAGRAM_OPTION_DESCRIPTION

'INITIALIZE DROP SNAP DIAGRAM OFFSET
   XAxisOffsetTextBox.text = GetSetting(APP_NAME, SECTION_COMPASS_RULE_2D, KEY_X_AXIS_OFFSET, "0.00")
   YAxisOffsetTextBox.text = GetSetting(APP_NAME, SECTION_COMPASS_RULE_2D, KEY_Y_AXIS_OFFSET, "0.00")

'INITIALIZE TURN OFF DROP DIAGRAM CHECK BOX
   InitializeCheckBox DiagramOffCheckBox, SECTION_COMPASS_RULE_2D, KEY_OPTION_DROP_DIAGRAM_OFF, False

'INITIALIZE TURN OFF SIDE SHOTS CHECK BOX
   InitializeCheckBox SidesOffCheckBox, SECTION_COMPASS_RULE_2D, KEY_OPTION_SIDE_SHOTS_OFF, False

'INITIALIZE OPPOSITES CHECK BOX
   InitializeCheckBox OppositesCheckBox, SECTION_COMPASS_RULE_2D, KEY_OPTION_OPPOSITES
   UpdateOppLabels

'INITIALIZE EXPORT TO ASCII FILE INCLUDE SIDE SHOTS CHECKBOX
   InitializeCheckBox ExportSidesCheckBox, SECTION_COMPASS_RULE_2D, KEY_INCLUDE_SIDES, False

'SET LIMIT ON FIRST BS AZIMUTH
   FirstBSAzTextBox.MaxLength = MAX_LEN_DIR_STRING

'INITIALIZE FORM VALUES
   InitNewCRForm

'SET CAPTION ON TITLE BAR
   UpdateCaption

'SET TAB INDEX
   TextElevation.TabIndex = 0
   TextNorthing.TabIndex = 1
   TextEasting.TabIndex = 2
   FirstBSAzTextBox.TabIndex = 3

'INITIALIZE STATES
   Me.FileLoaded = False
   AllButtonStates
End Sub


Private Sub UserForm_QueryClose(Cancel As Integer, CloseMode As Integer)
'SAVE USERFORM POSITION
   SaveSetting APP_NAME, SECTION_COMPASS_RULE_2D, KEY_START_TOP, FormatNumber(Me.Top, 2)
   SaveSetting APP_NAME, SECTION_COMPASS_RULE_2D, KEY_START_LEFT, FormatNumber(Me.Left, 2)
End Sub

Attribute VB_Name = "FrmCurveSolver"
Attribute VB_Base = "0{CFEE224E-7814-46B7-AA3C-98C37989C561}{2528A1E9-3A35-4C1B-A7E8-816B0C90305F}"
Attribute VB_GlobalNameSpace = False
Attribute VB_Creatable = False
Attribute VB_PredeclaredId = True
Attribute VB_Exposed = False
Attribute VB_TemplateDerived = False
Attribute VB_Customizable = False











'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.



'GENERAL NOTES:
'ALL THESE ROUTINES WERE WRITTEN BY JASON LOOK.  THEY ARE NOT
'WRITTEN IN THE STYLE COMMONLY USED BY PROFESSIONAL PROGRAMMERS.
'THEY ARE WRITTEN IN THE STYLE PREFERRED BY JASON.  JASON IS NOT
'A PROFESSIONAL PROGRAMMER!

'PROGRAM ASSUMES MASTER UNIT IS FOOT OR SURVEY FOOT, SOME KIND OF FOOT

Option Explicit

Private Const PRECISION_ANG_SEC           As Long = 4
Private Const PRECISION_ANG_TENTH_SEC     As Long = 5

Private Const PRECISION_LINEAR            As Long = 2 'TWO DECIMAL PLACES

Private Const ERROR_ENTRY_BAD_FORMAT      As Integer = 1
Private Const ERROR_DELTA_TOO_SMALL       As Integer = 2
Private Const ERROR_PC_STATION_TOO_SMALL  As Integer = 3
Private Const ERROR_DISTANCE_TOO_SMALL    As Integer = 4
Private Const ERROR_DISTANCE_TOO_BIG      As Integer = 5
Private Const ERROR_RADIUS_TOO_SMALL      As Integer = 6
Private Const ERROR_RADIUS_TOO_BIG        As Integer = 7
Private Const ERROR_PT_STATION_TOO_SMALL  As Integer = 8
Private Const ERROR_CURVE_TOO_LARGE       As Integer = 9
Private Const ERROR_PROGRAM_ISSUE         As Integer = 10
Private Const ERROR_STATION_MISMATCH      As Integer = 11
Private Const ERROR_BAD_SPIRAL_ANGLE      As Integer = 12
Private Const ERROR_BAD_SPIRAL_LENGTH     As Integer = 13
Private Const ERROR_RESULT_TOO_BIG        As Integer = 14


Private Const ELEMENT_TYPE_LINE           As Integer = 1
Private Const ELEMENT_TYPE_CURVE          As Integer = 2
Private Const ELEMENT_TYPE_LEADER         As Integer = 3
Private Const ELEMENT_TYPE_DATA           As Integer = 4
Private Const ELEMENT_TYPE_SPIRAL         As Integer = 5
Private Const ELEMENT_TYPE_SPIRAL_DATA    As Integer = 6

Private Const TEXT_PT_TO_PC               As String = "(P.T. to P.C.)"
Private Const TEXT_PREFIX_STATION         As String = "Sta. "
Private Const TEXT_PREFIX_PC              As String = "P.C. "
Private Const TEXT_PREFIX_PT              As String = "P.T. "
Private Const TEXT_PREFIX_TS              As String = "TS "
Private Const TEXT_PREFIX_SC              As String = "SC "
Private Const TEXT_PREFIX_CS              As String = "CS "
Private Const TEXT_PREFIX_ST              As String = "ST "


Private Const DEFAULT_CURVE_DATA_HEADING  As String = "Curve Data"
Private Const DEFAULT_SPIRAL_DATA_HEADING As String = "Spiral Data"

Private angleStyleGlobal                  As Integer
Private stationStyleGlobal                As Integer
Private finishedLoadingGlobal             As Boolean
Private tangentSolvedGlobal               As Boolean
Private ElementTypeGlobal                 As Integer
Private anchorPointGlobal                 As Point3d
Public doAdditional                       As Boolean

Private picktype                          As Long
'DIRECTIONS
Private Const PICK_TYPE_LINE_DIR          As Long = 1
Private Const PICK_TYPE_TAN_IN            As Long = 2
Private Const PICK_TYPE_SPIRAL_TAN_IN     As Long = 3
Private Const LAST_DIR_FIELD              As Long = 10
'STATIONS
Private Const PICK_TYPE_PC_STA            As Long = 11
Private Const PICK_TYPE_PT_STA            As Long = 12
Private Const PICK_TYPE_START_STA         As Long = 13
Private Const LAST_STA_FIELD              As Long = 20





'*************************************************************************************************************
'**************************************INTERFACE WITH IPRIMITIVE CLASS****************************************
'CREATE THE PERMANENT GRAPHIC ELEMENTS WHEN POINT IS PICKED
Public Sub PermGraphic(CurrentPosition As Point3d, TheView As view)
'QUIT IF READ ONLY
   If ActiveModelReference.IsReadOnly = True Then
      Exit Sub
   End If

'DRAW LINE PORTION OF BASELINE
   If ElementTypeGlobal = ELEMENT_TYPE_LINE Then
      DrawSolvedLine CurrentPosition, TheView
      Exit Sub
   End If

'DRAW CURVE PORTION OF BASELINE
   If ElementTypeGlobal = ELEMENT_TYPE_CURVE Then
      DrawPermBaseCurve CurrentPosition, TheView
      Exit Sub
   End If

'DRAW SPIRAL PORTION OF BASELINE
   If ElementTypeGlobal = ELEMENT_TYPE_SPIRAL Then
      DrawPermBaseSpiral CurrentPosition, TheView
      Exit Sub
   End If

'DRAW LEADER LINE WITH DIRECTION AND DISTANCE
   If ElementTypeGlobal = ELEMENT_TYPE_LEADER Then
      Dim textTemplate As TextElement
      Set textTemplate = CreateBaseTextTemplate()
      Dim leaderCell As CellElement
      Dim leadLengthChars As Double
      Dim leaderTextCell As CellElement
      Set leaderTextCell = CreateLeaderText(CurrentPosition, TheView, textTemplate, leaderCell, leadLengthChars)
      ActiveModelReference.AddElement leaderTextCell
      leaderTextCell.Redraw
'IF LEADER IS AT LEAST ONE CHARACTER LONG, THEN ADD IT TO DRAWING
      If leadLengthChars > 1 Then
         ActiveModelReference.AddElement leaderCell
         leaderCell.Redraw
      End If
      Exit Sub
   End If

'DRAW CURVE DATA
   If ElementTypeGlobal = ELEMENT_TYPE_DATA Then
      Set textTemplate = CreateCurveDataTextTemplate()
      Dim CurveDataCell As CellElement
      Set CurveDataCell = CreateCurveDataCell(CurrentPosition, _
                                              TheViewRotRadians(TheView), _
                                              textTemplate, _
                                              SolveDeltaLabel.Caption, _
                                              SolveHalfDeltaLabel.Caption, _
                                              RadLabel, _
                                              SolveTangentLabel.Caption, _
                                              SolveLongChordLabel, _
                                              CurveLengthLabel, _
                                              CurveDataPrefixTextBox.text, _
                                              HeadingTextBox.text, _
                                              AlignRightOption.value)
      ActiveModelReference.AddElement CurveDataCell
      CurveDataCell.Redraw
   End If

'DRAW SPIRAL PORTION OF BASELINE
   If ElementTypeGlobal = ELEMENT_TYPE_CURVE Then
      DrawPermBaseSpiral CurrentPosition, TheView
      Exit Sub
   End If
   
'DRAW SPRIRAL DATA
   If ElementTypeGlobal = ELEMENT_TYPE_SPIRAL_DATA Then
      Set textTemplate = CreateCurveDataTextTemplate()
      If SpiralAngleButton.value Then
         Dim thetaString As String
         thetaString = SpiralAngleTextBox.text
      Else
         thetaString = SpiralAngleCalcedLabel.Caption
      End If
      Dim MYcell As CellElement
      Set MYcell = CreateSpiralData(thetaString, _
                                    LengthTextBox.text, _
                                    SpiralPrefixTextBox.text, _
                                    SpiralHeadingTextBox.text, _
                                    CurrentPosition, _
                                    textTemplate, _
                                    TheViewRotRadians(TheView))
      ActiveModelReference.AddElement MYcell
      MYcell.Redraw
      Exit Sub
   End If
End Sub



'CREATE TEMPORARY GRAPHIC ELEMENTS FOR DYNAMICS
Public Function TempGraphic(CurrentPosition As Point3d, TheView As view) As Element
   Dim template As LineElement
   Set template = CreateTempLine()
'CREATE TEMPORARY LINE ELEMENT FOR DYNAMICS
   If ElementTypeGlobal = ELEMENT_TYPE_LINE Then
      Dim sAzOfLine As Double
      Set TempGraphic = CreateLinePart(CurrentPosition, template, sAzOfLine)
      Exit Function
   End If

'CREATE TEMPORARY ORPHAN CELL FOR DYNAMICS
   If ElementTypeGlobal = ELEMENT_TYPE_CURVE Then
      Set TempGraphic = CreateTempCurve(CurrentPosition, template)
      Exit Function
   End If

'CREATE SPIRAL TEMPORARY ORPHAN CELL FOR DYNAMICS
   If ElementTypeGlobal = ELEMENT_TYPE_SPIRAL Then
      Set TempGraphic = CreateTempSpiral(CurrentPosition, template)
      Exit Function
   End If

'CREATE TEMPORARY LEADER LINE WITH DIRECTION AND DISTANCE
   If ElementTypeGlobal = ELEMENT_TYPE_LEADER Then
      Dim textTemplate As TextElement
      Set textTemplate = CreateBaseTextTemplate()
      Dim leadLengthChars As Double
      Dim leaderCell As CellElement
      Dim cellArray(2) As Element
      Set cellArray(0) = CreateLeaderText(CurrentPosition, TheView, textTemplate, leaderCell, leadLengthChars)
      Set cellArray(1) = leaderCell
      Set TempGraphic = CreateCellElement1(vbNullString, cellArray, CurrentPosition)
      Exit Function
   End If

'CREATE TEMPORARY CURVE DATA FOR PLACEMENT
   If ElementTypeGlobal = ELEMENT_TYPE_DATA Then
      Dim tether As LineElement
      Set tether = CreateLineElement2(template, CurrentPosition, anchorPointGlobal)
      tether.color = GetTetherColor()
      Set textTemplate = CreateCurveDataTextTemplate()
      Dim CurveDataCell As CellElement
      Set CurveDataCell = CreateCurveDataCell(CurrentPosition, _
                                              TheViewRotRadians(TheView), _
                                              textTemplate, _
                                              SolveDeltaLabel.Caption, _
                                              SolveHalfDeltaLabel.Caption, _
                                              RadLabel, _
                                              SolveTangentLabel.Caption, _
                                              SolveLongChordLabel, _
                                              CurveLengthLabel, _
                                              CurveDataPrefixTextBox.text, _
                                              HeadingTextBox.text, _
                                              AlignRightOption.value)
      Set cellArray(0) = CurveDataCell
      Set cellArray(1) = tether
      Set TempGraphic = CreateCellElement1(vbNullString, cellArray, CurrentPosition)
      Exit Function
   End If

'CREATE TEMPORARY SPIRAL DATA FOR PLACEMENT
   If ElementTypeGlobal = ELEMENT_TYPE_SPIRAL_DATA Then
      Set textTemplate = CreateCurveDataTextTemplate()
      Set tether = CreateLineElement2(template, CurrentPosition, anchorPointGlobal)
      tether.color = GetTetherColor()
      If SpiralAngleButton.value Then
         Dim thetaString As String
         thetaString = SpiralAngleTextBox.text
      Else
         thetaString = SpiralAngleCalcedLabel.Caption
      End If
      thetaString = ReplaceDegreeSymbol2(thetaString)
      Set cellArray(1) = tether
      Set cellArray(0) = CreateSpiralData(thetaString, _
                                          LengthTextBox.text, _
                                          SpiralPrefixTextBox.text, _
                                          SpiralHeadingTextBox.text, _
                                          CurrentPosition, _
                                          textTemplate, _
                                          TheViewRotRadians(TheView))
      Set TempGraphic = CreateCellElement1(vbNullString, cellArray, CurrentPosition)
      Exit Function
   End If
End Function



'*************************************************************************************************************
'*****************************************INTERFACE WITH ILOCATE CLASS****************************************
'INTERFACE FOR PICKING TEXT ROUTINE
Public Sub EnterText(ByVal Entry As String)
   If picktype < LAST_DIR_FIELD Then
'DIRECTION TEXT
      Dim origPrec As Long
      Dim degPart As Long
      Dim minPart As Long
      Dim secPart As Double
      Dim dirType As Integer
      Dim quad As Integer
      If IsDirString(Entry, origPrec, degPart, minPart, secPart, dirType, quad) Then
         Select Case picktype
            Case PICK_TYPE_TAN_IN
               OptionTangentIn.value = True
               TangentInTextBox.text = Entry
               TangentInTextBox_AfterUpdate
            Case PICK_TYPE_LINE_DIR
               LineDirectionTextBox.text = Entry
               LineDirectionTextBox_AfterUpdate
            Case PICK_TYPE_SPIRAL_TAN_IN
               SpiralTanInTextBox.text = Entry
               SpiralTanInTextBox_AfterUpdate
         End Select
      End If
   ElseIf picktype < LAST_STA_FIELD Then
'STATION TEXT
      Dim searchString As String
      searchString = UCase(Trim(TEXT_PREFIX_STATION))
      Dim sPos As Long
      sPos = InStr(1, UCase(Entry), searchString)
      If sPos > 0 Then
         Dim subPos As Long
         subPos = sPos + Len(searchString) - 1
         Dim possibleStationString As String
         possibleStationString = right(Entry, Len(Entry) - subPos)
      Else
         possibleStationString = Entry
      End If
      Select Case picktype
         Case PICK_TYPE_PC_STA
            PCStaTextBox.text = possibleStationString
            PCStaTextBox_AfterUpdate
         Case PICK_TYPE_PT_STA
            LinePTStaTextBox.text = possibleStationString
            LinePTStaTextBox_AfterUpdate
         Case PICK_TYPE_START_STA
            StartStationTextBox.text = possibleStationString
            StartStationTextBox_AfterUpdate
      End Select
   End If
End Sub



Private Sub LaunchPickText(dirType As Long)
   picktype = dirType
   Dim myTool As New CurveSolverLocateText
   Set myTool.hostForm = Me
   CommandState.StartLocate myTool
   Me.Hide
End Sub



'*************************************************************************************************************
'*******************************************CURVE SOLUTION TAB************************************************
'LEFT HAND CURVE OPTION
Private Sub OptionLeft_Click()
   SaveCurveOrientation
   CalcCurve
End Sub



'RIGHT HAND CURVE OPTION
Private Sub OptionRight_Click()
   SaveCurveOrientation
   CalcCurve
End Sub



Private Sub SaveCurveOrientation()
   If OptionLeft.value = True Then
      SaveSetting APP_NAME, SECTION_CURVE_SOLVER, KEY_ROTATION, OPTION_LEFT
   Else
      SaveSetting APP_NAME, SECTION_CURVE_SOLVER, KEY_ROTATION, OPTION_RIGHT
   End If
End Sub



'PC STATION TEXTBOX
Private Sub PCStaTextBox_AfterUpdate()
   SaveStationEntry PCStaTextBox, SECTION_CURVE_SOLVER, KEY_PC_STA_CURVE, stationStyleGlobal, PRECISION_LINEAR
   CalcCurve
End Sub

Private Sub PCStaTextBox_Enter()
   SelectAllText PCStaTextBox
End Sub



'PICK PC STATION FROM TEXT BUTTON
Private Sub PickPCStaButton_Click()
   LaunchPickText PICK_TYPE_PC_STA
End Sub



'RADIUS TEXTBOX
Private Sub RadiusTextBox_AfterUpdate()
   SaveNonnegativeEntry RadiusTextBox, SECTION_CURVE_SOLVER, KEY_RADIUS, MAX_RADIUS, MAX_PRECISION_RADIUS, False, 100.2, PRECISION_LINEAR
   CalcCurve
End Sub

Private Sub RadiusTextBox_Enter()
   SelectAllText RadiusTextBox
End Sub



'CURVE TANGENT IN OPTION BUTTON
Private Sub OptionTangentIn_Click()
   SaveCurveInType
   ControlsStatesCurve
   CalcCurve
End Sub



'CURVE TANGENT IN TEXTBOX
Private Sub TangentInTextBox_AfterUpdate()
   SaveDirEntry TangentInTextBox, SECTION_CURVE_SOLVER, KEY_TANGENT_IN, angleStyleGlobal, AngPrec()
   CalcCurve
End Sub

Private Sub TangentInTextBox_Enter()
   SelectAllText TangentInTextBox
End Sub



'PICK TANGENT IN TEXT
Private Sub PickButton_Click()
   LaunchPickText PICK_TYPE_TAN_IN
End Sub



'P.C. TO C.C. OPTION BUTTON
Private Sub OptionPCtoCC_Click()
   SaveCurveInType
   ControlsStatesCurve
   CalcCurve
End Sub



'P.C. TO C.C. TEXTBOX
Private Sub PCtoCCTextBox_AfterUpdate()
   SaveDirEntry PCtoCCTextBox, SECTION_CURVE_SOLVER, KEY_PC2CC, angleStyleGlobal, AngPrec()
   CalcCurve
End Sub

Private Sub PCtoCCTextBox_Enter()
   SelectAllText PCtoCCTextBox
End Sub



Private Sub SaveCurveInType()
   If OptionTangentIn.value Then
      SaveSetting APP_NAME, SECTION_CURVE_SOLVER, KEY_CURVE_IN_TYPE, OPTION_CURVE_IN_TYPE_TANGENT
   Else
      SaveSetting APP_NAME, SECTION_CURVE_SOLVER, KEY_CURVE_IN_TYPE, OPTION_CURVE_IN_TYPE_PC2CC
   End If
End Sub



'+180 BUTTON
Private Sub Plus180Button_Click()
   Plus180 PCtoCCTextBox
   PCtoCCTextBox_AfterUpdate
End Sub



'DELTA OPTION BUTTON
Private Sub OptionDelta_Click()
   SaveCurveOutType
   ControlsStatesCurve
   CalcCurve
End Sub



'DELTA TEXTBOX
Private Sub DeltaTextBox_AfterUpdate()
   SaveDeltaEntry DeltaTextBox, SECTION_CURVE_SOLVER, KEY_DELTA, angleStyleGlobal, AngPrec()
   CalcCurve
End Sub

Private Sub DeltaTextBox_Enter()
   SelectAllText DeltaTextBox
End Sub



'P.T. STATION OPTION BUTTON
Private Sub OptionPTSta_Click()
   SaveCurveOutType
   ControlsStatesCurve
   CalcCurve
End Sub



'P.T. STATION TEXTBOX
Private Sub PTStaTextBox_AfterUpdate()
   SaveStationEntry PTStaTextBox, SECTION_CURVE_SOLVER, KEY_PT_STA_CURVE, stationStyleGlobal, PRECISION_LINEAR
   CalcCurve
End Sub

Private Sub PTStaTextBox_Enter()
   SelectAllText PTStaTextBox
End Sub



'TANGENT OUT OPTION BUTON
Private Sub OptionTangentOut_Click()
   SaveCurveOutType
   ControlsStatesCurve
   CalcCurve
End Sub



'TANGENT OUT TEXTBOX
Private Sub TangentOutTextBox_AfterUpdate()
   SaveDirEntry TangentOutTextBox, SECTION_CURVE_SOLVER, KEY_TANGENT_OUT, angleStyleGlobal, AngPrec()
   CalcCurve
End Sub

Private Sub TangentOutTextBox_Enter()
   SelectAllText TangentOutTextBox
End Sub



'C.C. TO P.T. OPTION BUTTON
Private Sub OptionAzCCtoPT_Click()
   SaveCurveOutType
   ControlsStatesCurve
   CalcCurve
End Sub



'C.C. TO P.T. TEXTBOX
Private Sub CCtoPTTextBox_AfterUpdate()
   SaveDirEntry CCtoPTTextBox, SECTION_CURVE_SOLVER, KEY_CC2PT, angleStyleGlobal, AngPrec()
   CalcCurve
End Sub

Private Sub CCtoPTTextBox_Enter()
   SelectAllText CCtoPTTextBox
End Sub



Private Sub SaveCurveOutType()
   If OptionDelta.value Then
      SaveSetting APP_NAME, SECTION_CURVE_SOLVER, KEY_CURVE_OUT_TYPE, OPTION_CURVE_OUT_TYPE_DELTA
   ElseIf OptionPTSta.value Then
      SaveSetting APP_NAME, SECTION_CURVE_SOLVER, KEY_CURVE_OUT_TYPE, OPTION_CURVE_OUT_TYPE_PT_STA
   ElseIf OptionTangentOut.value Then
      SaveSetting APP_NAME, SECTION_CURVE_SOLVER, KEY_CURVE_OUT_TYPE, OPTION_CURVE_OUT_TYPE_TAN_OUT
   ElseIf OptionAzCCtoPT.value Then
      SaveSetting APP_NAME, SECTION_CURVE_SOLVER, KEY_CURVE_OUT_TYPE, OPTION_CURVE_OUT_TYPE_CC2PC
   End If
End Sub



'PASS TO LINE BUTTON
Private Sub PassToLineButton_Click()
'MAKE SURE NOTHING UNENTERED
   CalcCurve

'MAKE SURE SOLUTION FOUND
   If Not PassToLineButton.enabled Then
      Exit Sub
   End If
   
'PASS ON APPROPRIATE VALUES
   If OptionPTSta.value Then
      LinePTStaTextBox.text = PTStaTextBox.text
   Else
      LinePTStaTextBox.text = PtStaCalcedLabel.Caption
   End If
   LinePTStaTextBox_AfterUpdate
   
   If OptionTangentOut.value Then
      LineDirectionTextBox.text = TangentOutTextBox.text
   Else
      LineDirectionTextBox.text = TanOutCalcedLabel.Caption
   End If
      LineDirectionTextBox_AfterUpdate
   
'BRING LINE TAB TO FOREGROUND
   Me.MainMultiPage.value = 4

'SET FOCUS TO NEXT FIELD
   If LinePCStationTextBox.enabled Then
      LinePCStationTextBox.SetFocus
   End If
   If LineDistanceTextBox.enabled Then
      LineDistanceTextBox.SetFocus
   End If
End Sub



'DRAW IT FROM P.C. OPTION BUTTON
Private Sub OptionPC_Click()
   SaveDrawFrom
   CalcCurve
End Sub



'DRAW IT FROM P.I. OPTION BUTTON
Private Sub OptionPI_Click()
   SaveDrawFrom
   CalcCurve
End Sub



Private Sub SaveDrawFrom()
   If OptionPC.value Then
      SaveSetting APP_NAME, SECTION_CURVE_SOLVER, KEY_DRAW_FROM, OPTION_PC
   Else
      SaveSetting APP_NAME, SECTION_CURVE_SOLVER, KEY_DRAW_FROM, OPTION_PI
   End If
End Sub



'DRAW IT BUTTON
Private Sub DrawItButton_Click()
'MAKE SURE NO UNENTERED VALUES
   CalcCurve

'MAKE SURE SOLUTION FOUND
   If DrawItButton.enabled Then
'CANCEL FLAG
      doAdditional = False
'PLACE THE ELEMENT
      ElementTypeGlobal = ELEMENT_TYPE_CURVE
      Me.Hide
      Dim myTool As New CurveSolverPrimitive
      Set myTool.hostForm = Me
      CommandState.StartPrimitive myTool
   End If
End Sub



'PASS TO SPIRAL BUTTON
Private Sub CToSpButton_Click()
'MAKE SURE NOTHING UNENTERED
   CalcCurve

'MAKE SURE SOLUTION FOUND
   If Not CToSpButton.enabled Then
      Exit Sub
   End If

'SET APPROPRIATE SPIRAL
   OutgoingOption.value = True
   LHSpiralOption.value = OptionLeft.value
   RHSpiralOption.value = OptionRight.value

'PASS ON APPROPRIATE VALUES
   If OptionPTSta.value Then
      StartStationTextBox.text = PTStaTextBox.text
   Else
      StartStationTextBox.text = PtStaCalcedLabel.Caption
   End If
   StartStationTextBox_AfterUpdate
   
   If OptionTangentOut.value Then
      SpiralTanInTextBox.text = TangentOutTextBox.text
   Else
      SpiralTanInTextBox.text = TanOutCalcedLabel.Caption
   End If
      SpiralTanInTextBox_AfterUpdate
      
   RadiusButton.value = True
   RadTextBox.text = RadiusTextBox.text
   RadTextBox_AfterUpdate
   
'BRING LINE TAB TO FOREGROUND
   Me.MainMultiPage.value = 5

'SET FOCUS TO NEXT FIELD
   LengthTextBox.SetFocus
End Sub



'*************************************************************************************************************
'*********************************************CURVE OPTIONS TAB***********************************************
'DRAW RADIAL LINES CHECKBOX
Private Sub RadialCheckbox_Click()
   SaveCheckBoxSetting RadialCheckbox, SECTION_CURVE_SOLVER, KEY_DRAW_RADIALS
End Sub



'R= ON P.C. CHECKBOX
Private Sub RequalsPCCheckBox_Click()
   SaveCheckBoxSetting RequalsPCCheckBox, SECTION_CURVE_SOLVER, KEY_DRAW_RAD_ON_PC
End Sub



'R= ON P.T. CHECKBOX
Private Sub RequalsPTCheckBox_Click()
   SaveCheckBoxSetting RequalsPTCheckBox, SECTION_CURVE_SOLVER, KEY_DRAW_RAD_ON_PT
End Sub



'DRAW TANGENT LINES CHECKBOX
Private Sub TangentLinesCheckBox_Click()
   SaveCheckBoxSetting TangentLinesCheckBox, SECTION_CURVE_SOLVER, KEY_DRAW_TANGENTS
End Sub



'CURVE LABEL P.C. STATION CHECKBOX
Private Sub PCStationCheckBox_Click()
   SaveCheckBoxSetting PCStationCheckBox, SECTION_CURVE_SOLVER, KEY_LABEL_PC
   ControlsStatesCurveOptions
End Sub



'CURVE P.C. PREFIX "P.C." OPTION BUTTON
Private Sub OptionPCPrefix_Click()
   SavePCPrefixOption
   ControlsStatesCurveOptions
End Sub



'CURVE P.C. PREFIX OTHER OPTION BUTTON
Private Sub OptionOtherPCPrefix_Click()
   SavePCPrefixOption
   ControlsStatesCurveOptions
End Sub



Private Sub SavePCPrefixOption()
   If OptionPCPrefix.value Then
      SaveSetting APP_NAME, SECTION_CURVE_SOLVER, KEY_LABEL_PC_OTHER, OPTION_FALSE
   Else
      SaveSetting APP_NAME, SECTION_CURVE_SOLVER, KEY_LABEL_PC_OTHER, OPTION_TRUE
   End If
End Sub



'CURVE P.C. PREFIX OTHER TEXTBOX
Private Sub PCprefixTextBox_AfterUpdate()
   SaveSetting APP_NAME, SECTION_CURVE_SOLVER, KEY_LABEL_PC_OTHER_TEXT, PCprefixTextBox.text
End Sub



'CURVE LABEL P.T. STATION CHECKBOX
Private Sub PTStationCheckBox_Click()
   SaveCheckBoxSetting PTStationCheckBox, SECTION_CURVE_SOLVER, KEY_LABEL_PT
   ControlsStatesCurveOptions
End Sub



'CURVE LABEL P.T. STATION PREFIX "P.T." OPTION BUTTON
Private Sub OptionPTPrefix_Click()
   SavePTPrefixOption
   ControlsStatesCurveOptions
End Sub



'CURVE LABEL P.T. STATION PREFIX OTHER OPTION BUTTON
Private Sub OptionOtherPTPrefix_Click()
   SavePTPrefixOption
   ControlsStatesCurveOptions
End Sub



Private Sub SavePTPrefixOption()
   If OptionPCPrefix.value Then
      SaveSetting APP_NAME, SECTION_CURVE_SOLVER, KEY_LABEL_PT_OTHER, OPTION_FALSE
   Else
      SaveSetting APP_NAME, SECTION_CURVE_SOLVER, KEY_LABEL_PT_OTHER, OPTION_TRUE
   End If
End Sub



'CURVE LABEL P.T. STATION PREFIX OTHER TEXTBOX
Private Sub PTprefixTextBox_AfterUpdate()
   SaveSetting APP_NAME, SECTION_CURVE_SOLVER, KEY_LABEL_PT_OTHER_TEXT, PTprefixTextBox.text
End Sub



'DRAW SYMBOL ON P.C. CHECKBOX
Private Sub PCSymbolCheckBox_Click()
   SaveCheckBoxSetting PCSymbolCheckBox, SECTION_CURVE_SOLVER, KEY_DRAW_PC_SYMBOL
End Sub



'DRAW SYMBOL ON P.T. CHECKBOX
Private Sub PTSymbolCheckBox_Click()
   SaveCheckBoxSetting PTSymbolCheckBox, SECTION_CURVE_SOLVER, KEY_DRAW_PT_SYMBOL
End Sub



'DRAW CURVE DATA CHECKBOX
Private Sub CurveDataCheckBox_Click()
   SaveCheckBoxSetting CurveDataCheckBox, SECTION_CURVE_SOLVER, KEY_CURVE_DATA
   ControlsStatesCurveOptions
End Sub



'PREFIX TEXTBOX
Private Sub CurveDataPrefixTextBox_AfterUpdate()
   SaveSetting APP_NAME, SECTION_CURVE_SOLVER, KEY_PREFIX, CurveDataPrefixTextBox.text
End Sub



'HEADING TEXTBOX
Private Sub HeadingTextBox_AfterUpdate()
   SaveSetting APP_NAME, SECTION_CURVE_SOLVER, KEY_HEADING, HeadingTextBox.text
End Sub



'ALIGN LEFT OPTION BUTTON
Private Sub AlignLeftOption_Click()
    SaveAlignCurveDataOption
End Sub



'ALIGN RIGHT OPTION BUTTON
Private Sub AlignRightOption_Click()
   SaveAlignCurveDataOption
End Sub



Private Sub SaveAlignCurveDataOption()
   If AlignLeftOption.value Then
      SaveSetting APP_NAME, SECTION_CURVE_SOLVER, KEY_ALIGNED, OPTION_LEFT
   Else
      SaveSetting APP_NAME, SECTION_CURVE_SOLVER, KEY_ALIGNED, OPTION_RIGHT
   End If
End Sub



'*************************************************************************************************************
'*********************************************SETTINGS TAB1***************************************************
'BASELINE LEVEL COMBOBOX
Private Sub BaselineLevelComboBox_AfterUpdate()
   If Not LevelBoxOnUpdate(BaselineLevelComboBox, SECTION_CURVE_SOLVER, KEY_BASELINE_LEVEL) Then
      PopulateLevelBox BaselineLevelComboBox, SECTION_CURVE_SOLVER, KEY_BASELINE_LEVEL
      Beep
   End If
End Sub

'BASELINE COLOR COMBOBOX
Private Sub BaselineColorComboBox_AfterUpdate()
   ColorBoxOnUpdate BaselineColorComboBox, SECTION_CURVE_SOLVER, KEY_BASELINE_COLOR
End Sub

'BASELINE COLOR CHOOSER
Private Sub BaselineColorChooserButton_Click()
   Dim MyColor As String
   If ChooseMyTableColor(MyColor) Then
      BaselineColorComboBox.text = MyColor
      BaselineColorComboBox_AfterUpdate
   End If
End Sub

'BASELINE STYLE COMBOBOX
Private Sub BaselineStyleComboBox_AfterUpdate()
   If Not LineStyleBoxOnUpdate(BaselineStyleComboBox, SECTION_CURVE_SOLVER, KEY_BASELINE_STYLE) Then
      PopulateLinestyleBox BaselineStyleComboBox, SECTION_CURVE_SOLVER, KEY_BASELINE_STYLE
      Beep
   End If
End Sub

'BASELINE WEIGHT COMBOBOX
Private Sub BaselineWeightComboBox_AfterUpdate()
   WeightBoxOnUpdate BaselineWeightComboBox, SECTION_CURVE_SOLVER, KEY_BASELINE_WEIGHT
End Sub





'RADIAL AND TANGENT LINES LEVEL COMBOBOX
Private Sub RadialLinesLevelComboBox_AfterUpdate()
   If Not LevelBoxOnUpdate(RadialLinesLevelComboBox, SECTION_CURVE_SOLVER, KEY_RADIALS_LEVEL) Then
      PopulateLevelBox RadialLinesLevelComboBox, SECTION_CURVE_SOLVER, KEY_RADIALS_LEVEL
      Beep
   End If
End Sub

'RADIAL AND TANGENT LINES COLOR COMBOBOX
Private Sub RadialLinesColorComboBox_AfterUpdate()
   ColorBoxOnUpdate RadialLinesColorComboBox, SECTION_CURVE_SOLVER, KEY_RADIALS_COLOR
End Sub

'RADIAL AND TANGENT LINES COLOR CHOOSER
Private Sub RadialsColorChooserButton_Click()
   Dim MyColor As String
   If ChooseMyTableColor(MyColor) Then
      RadialLinesColorComboBox.text = MyColor
      RadialLinesColorComboBox_AfterUpdate
   End If
End Sub

'RADIAL AND TANGENT LINES STYLE COMBOBOX
Private Sub RadialLinesStyleComboBox_AfterUpdate()
   If Not LineStyleBoxOnUpdate(RadialLinesStyleComboBox, SECTION_CURVE_SOLVER, KEY_RADIALS_STYLE) Then
      PopulateLinestyleBox RadialLinesStyleComboBox, SECTION_CURVE_SOLVER, KEY_RADIALS_STYLE
      Beep
   End If
End Sub

'RADIAL AND TANGENT LINES WEIGHT COMBOBOX
Private Sub RadialLinesWeightComboBox_AfterUpdate()
   WeightBoxOnUpdate RadialLinesWeightComboBox, SECTION_CURVE_SOLVER, KEY_RADIALS_WEIGHT
End Sub




'TEXT LEVEL COMBOBOX
Private Sub OtherTextLevelComboBox_AfterUpdate()
   If Not LevelBoxOnUpdate(OtherTextLevelComboBox, SECTION_CURVE_SOLVER, KEY_TEXT_LEVEL) Then
      PopulateLevelBox OtherTextLevelComboBox, SECTION_CURVE_SOLVER, KEY_TEXT_LEVEL
      Beep
   End If
End Sub

'TEXT COLOR COMBOBOX
Private Sub OtherTextColorComboBox_AfterUpdate()
   ColorBoxOnUpdate OtherTextColorComboBox, SECTION_CURVE_SOLVER, KEY_TEXT_COLOR
End Sub

'TEXT COLOR CHOOSER
Private Sub TextColorChooserButton_Click()
   Dim MyColor As String
   If ChooseMyTableColor(MyColor) Then
      OtherTextColorComboBox.text = MyColor
      OtherTextColorComboBox_AfterUpdate
   End If
End Sub

'TEXT STYLE COMBOBOX
Private Sub OtherTextStyleComboBox_AfterUpdate()
   If Not LineStyleBoxOnUpdate(OtherTextStyleComboBox, SECTION_CURVE_SOLVER, KEY_TEXT_STYLE) Then
      PopulateLinestyleBox OtherTextStyleComboBox, SECTION_CURVE_SOLVER, KEY_TEXT_STYLE
      Beep
   End If
End Sub

'TEXT WEIGHT COMBOBOX
Private Sub OtherTextWeightComboBox_AfterUpdate()
   WeightBoxOnUpdate OtherTextWeightComboBox, SECTION_CURVE_SOLVER, KEY_TEXT_WEIGHT
End Sub


'TEXT FONT COMBOBOX
Private Sub OtherTextFontComboBox_AfterUpdate()
   If Not FontBoxOnUpdate(OtherTextFontComboBox, SECTION_CURVE_SOLVER, KEY_TEXT_FONT) Then
      PopulateFontBox OtherTextFontComboBox, SECTION_CURVE_SOLVER, KEY_TEXT_FONT
      Beep
   End If
End Sub



'*************************************************************************************************************
'*********************************************SETTINGS TAB2***************************************************
'CURVE DATA LEVEL COMBOBOX
Private Sub CurveDataLevelComboBox_AfterUpdate()
   If Not LevelBoxOnUpdate(CurveDataLevelComboBox, SECTION_CURVE_SOLVER, KEY_CURVE_DATA_LEVEL) Then
      PopulateLevelBox CurveDataLevelComboBox, SECTION_CURVE_SOLVER, KEY_CURVE_DATA_LEVEL
      Beep
   End If
End Sub

'CURVE DATA COLOR COMBOBOX
Private Sub CurveDataColorComboBox_AfterUpdate()
   ColorBoxOnUpdate CurveDataColorComboBox, SECTION_CURVE_SOLVER, KEY_CURVE_DATA_COLOR
End Sub

'CURVE DATA COLOR CHOOSER
Private Sub CurveDataColorChooserButton_Click()
   Dim MyColor As String
   If ChooseMyTableColor(MyColor) Then
      CurveDataColorComboBox.text = MyColor
      CurveDataColorComboBox_AfterUpdate
   End If
End Sub

'CURVE DATA STYLE COMBOBOX
Private Sub CurveDataStyleComboBox_AfterUpdate()
   If Not LineStyleBoxOnUpdate(CurveDataStyleComboBox, SECTION_CURVE_SOLVER, KEY_CURVE_DATA_STYLE) Then
      PopulateLinestyleBox CurveDataStyleComboBox, SECTION_CURVE_SOLVER, KEY_CURVE_DATA_STYLE
      Beep
   End If
End Sub

'CURVE DATA WEIGHT COMBOBOX
Private Sub CurveDataWeightComboBox_AfterUpdate()
   WeightBoxOnUpdate CurveDataWeightComboBox, SECTION_CURVE_SOLVER, KEY_CURVE_DATA_WEIGHT
End Sub

'CURVE DATA FONT COMBOBOX
Private Sub CurveDataFontComboBox_AfterUpdate()
   If Not FontBoxOnUpdate(CurveDataFontComboBox, SECTION_CURVE_SOLVER, KEY_CURVE_DATA_FONT) Then
      PopulateFontBox CurveDataFontComboBox, SECTION_CURVE_SOLVER, KEY_CURVE_DATA_FONT
      Beep
   End If
End Sub




'SYMBOL LEVEL COMBOBOX
Private Sub SymbolsLevelComboBox_AfterUpdate()
   If Not LevelBoxOnUpdate(SymbolsLevelComboBox, SECTION_CURVE_SOLVER, KEY_SYMBOL_LEVEL) Then
      PopulateLevelBox SymbolsLevelComboBox, SECTION_CURVE_SOLVER, KEY_SYMBOL_LEVEL
      Beep
   End If
End Sub

'SYMBOL COLOR COMBOBOX
Private Sub SymbolsColorComboBox_AfterUpdate()
   ColorBoxOnUpdate SymbolsColorComboBox, SECTION_CURVE_SOLVER, KEY_SYMBOL_COLOR
End Sub

'SYMBOL COLOR CHOOSER
Private Sub SymbolColorChooserButton_Click()
   Dim MyColor As String
   If ChooseMyTableColor(MyColor) Then
      SymbolsColorComboBox.text = MyColor
      SymbolsColorComboBox_AfterUpdate
   End If
End Sub

'SYMBOL STYLE COMBOBOX
Private Sub SymbolsStyleComboBox_AfterUpdate()
   If Not LineStyleBoxOnUpdate(SymbolsStyleComboBox, SECTION_CURVE_SOLVER, KEY_SYMBOL_STYLE) Then
      PopulateLinestyleBox SymbolsStyleComboBox, SECTION_CURVE_SOLVER, KEY_SYMBOL_STYLE
      Beep
   End If
End Sub

'SYMBOL WEIGHT COMBOBOX
Private Sub SymbolsWeightComboBox_AfterUpdate()
   WeightBoxOnUpdate SymbolsWeightComboBox, SECTION_CURVE_SOLVER, KEY_SYMBOL_WEIGHT
End Sub



'ROUNDING PRECISION MODE 1 SECOND
Private Sub OptionSecond_Click()
   SaveSetting APP_NAME, SECTION_CURVE_SOLVER, KEY_PRECISION_ANG, OPTION_PREC_ANG_SEC
   UpdateAngleTextPrecision
End Sub



'ROUNDING PRECISION MODE 0.1 SECOND
Private Sub OptionTenthOfASecond_Click()
   SaveSetting APP_NAME, SECTION_CURVE_SOLVER, KEY_PRECISION_ANG, OPTION_PREC_ANG_SEC1
   UpdateAngleTextPrecision
End Sub



'SPIRAL MODE CHECKBOX
Private Sub SpiralCheckBox_Click()
   SaveCheckBoxSetting SpiralCheckBox, SECTION_CURVE_SOLVER, KEY_SPIRAL_MODE
   SetSpiralStates
End Sub



'SETTINGS BUTTON
Private Sub SettingsButton_Click()
   Setting
End Sub



'*************************************************************************************************************
'*********************************************LINE SOLVER TAB*************************************************
'LINE P.T. STATION TEXTBOX
Private Sub LinePTStaTextBox_AfterUpdate()
   SaveStationEntry LinePTStaTextBox, SECTION_CURVE_SOLVER, KEY_PT_STA_LINE, stationStyleGlobal, PRECISION_LINEAR
   CalcTangent
End Sub

Private Sub LinePTStaTextBox_Enter()
   SelectAllText LinePTStaTextBox
End Sub



'P.T. STATION PICK BUTTON
Private Sub PickPTStaButton_Click()
   LaunchPickText PICK_TYPE_PT_STA
End Sub



'LINE DIRECTION TEXTBOX
Private Sub LineDirectionTextBox_AfterUpdate()
   SaveDirEntry LineDirectionTextBox, SECTION_CURVE_SOLVER, KEY_LINE_DIRECTION, angleStyleGlobal, AngPrec()
End Sub

Private Sub LineDirectionTextBox_Enter()
   SelectAllText LineDirectionTextBox
End Sub



'PICK DIRECTION TEXT
Private Sub DirPickButton_Click()
   LaunchPickText PICK_TYPE_LINE_DIR
End Sub



'LINE P.C.STATION TEXTBOX
Private Sub LinePCStationTextBox_AfterUpdate()
   SaveStationEntry LinePCStationTextBox, SECTION_CURVE_SOLVER, KEY_PC_STA_LINE, stationStyleGlobal, PRECISION_LINEAR
   CalcTangent
End Sub

Private Sub LinePCStationTextBox_Enter()
   SelectAllText LinePCStationTextBox
End Sub



'LINE DISTANCE TEXTBOX
Private Sub LineDistanceTextBox_AfterUpdate()
   SaveNonnegativeEntry LineDistanceTextBox, SECTION_CURVE_SOLVER, KEY_DISTANCE, MAX_DISTANCE, MAX_PRECISION_DISTANCE, False, 100#, PRECISION_LINEAR
   CalcTangent
End Sub

Private Sub LineDistanceTextBox_Enter()
   SelectAllText LineDistanceTextBox
End Sub



'LINE P.C. STATION OPTION BUTTON
Private Sub LinePCStaOption_Click()
   SaveLengthType
   ControlsStatesLine
   CalcTangent
End Sub



'LINE DISTANCE OPTION BUTTON
Private Sub LineDistanceOption_Click()
   SaveLengthType
   ControlsStatesLine
   CalcTangent
End Sub



Private Sub SaveLengthType()
   If LinePCStaOption.value Then
      SaveSetting APP_NAME, SECTION_CURVE_SOLVER, KEY_LENGTH_BY, OPTION_STATION
   Else
      SaveSetting APP_NAME, SECTION_CURVE_SOLVER, KEY_LENGTH_BY, OPTION_DISTANCE
   End If
End Sub



'LINE LABEL P.T. STATION CHECKBOX
Private Sub LabelPTStationCheckBox_Click()
   SaveCheckBoxSetting LabelPTStationCheckBox, SECTION_CURVE_SOLVER, KEY_LABEL_PT_LINE
   ControlsStatesLine
End Sub



'LINE LABEL P.T. STATION LEFT OPTION BUTTON
Private Sub LabelPTLeftOption_Click()
   SavePtLineSideType
End Sub



'LINE LABEL P.T. STATION RIGHT OPTION BUTTON
Private Sub LabelPTRightOption_Click()
   SavePtLineSideType
End Sub



Private Sub SavePtLineSideType()
   If LabelPTLeftOption.value Then
      SaveSetting APP_NAME, SECTION_CURVE_SOLVER, KEY_LABEL_PT_LINE_SIDE, OPTION_LEFT
   Else
      SaveSetting APP_NAME, SECTION_CURVE_SOLVER, KEY_LABEL_PT_LINE_SIDE, OPTION_RIGHT
   End If
End Sub



'LINE LABEL P.T. STATION PREFIX P.T. OPTION BUTTON
Private Sub LabelPTOption_Click()
   SavePtLinePrefixType
   ControlsStatesLine
End Sub



'LINE LABEL P.T. STATION PREFIX OTHER OPTION BUTTON
Private Sub LabelPTOtherOption_Click()
   SavePtLinePrefixType
   ControlsStatesLine
End Sub



Private Sub SavePtLinePrefixType()
   If LabelPTOtherOption.value Then
      SaveSetting APP_NAME, SECTION_CURVE_SOLVER, KEY_LABEL_PT_LN_PREFIX_OTHER, OPTION_TRUE
   Else
      SaveSetting APP_NAME, SECTION_CURVE_SOLVER, KEY_LABEL_PT_LN_PREFIX_OTHER, OPTION_FALSE
   End If
End Sub



'LINE LABEL P.T. STATION PREFIX OTHER TEXTBOX
Private Sub LabelPTOtherTextBox_AfterUpdate()
   SaveSetting APP_NAME, SECTION_CURVE_SOLVER, KEY_LABEL_PT_LN_PREFIX_OTH_TXT, LabelPTOtherTextBox.text
End Sub

Private Sub LabelPTOtherTextBox_Enter()
   SelectAllText LabelPTOtherTextBox
End Sub



'LINE LABEL P.C. STATION CHECKBOX
Private Sub LabelPCStationCheckBox_Click()
   SaveCheckBoxSetting LabelPCStationCheckBox, SECTION_CURVE_SOLVER, KEY_LABEL_PC_LINE
   ControlsStatesLine
End Sub



'LINE LABEL P.C. STATION LEFT CHECKBOX
Private Sub LabelPCLeftOption_Click()
   SavePcLineSideType
End Sub



'LINE LABEL P.C. STATION RIGHT CHECKBOX
Private Sub LabelPCRightOption_Click()
   SavePcLineSideType
End Sub



Private Sub SavePcLineSideType()
   If LabelPTLeftOption.value Then
      SaveSetting APP_NAME, SECTION_CURVE_SOLVER, KEY_LABEL_PC_LINE_SIDE, OPTION_LEFT
   Else
      SaveSetting APP_NAME, SECTION_CURVE_SOLVER, KEY_LABEL_PC_LINE_SIDE, OPTION_RIGHT
   End If
End Sub



'LINE LABEL P.C. STATION PREFIX PC CHECKBOX
Private Sub PCLabelOption_Click()
   SavePcLinePrefixType
   ControlsStatesLine
End Sub



'LINE LABEL P.C. STATION PREFIX OTHER CHECKBOX
Private Sub PCOtherOption_Click()
   SavePcLinePrefixType
   ControlsStatesLine
End Sub



Private Sub SavePcLinePrefixType()
   If PCOtherOption.value Then
      SaveSetting APP_NAME, SECTION_CURVE_SOLVER, KEY_LABEL_PC_LN_PREFIX_OTHER, OPTION_TRUE
   Else
      SaveSetting APP_NAME, SECTION_CURVE_SOLVER, KEY_LABEL_PC_LN_PREFIX_OTHER, OPTION_FALSE
   End If
End Sub



'LINE LABEL P.C. STATION PREFIX OTHER TEXTBOX
Private Sub PCOtherTextBox_AfterUpdate()
   SaveSetting APP_NAME, SECTION_CURVE_SOLVER, KEY_LABEL_PC_LN_PREFIX_OTH_TXT, LabelPTOtherTextBox.text
End Sub

Private Sub PCOtherTextBox_Enter()
   SelectAllText PCOtherTextBox
End Sub



'LABEL LINE CHECKBOX
Private Sub LabelLineCheckBox_Click()
   SaveCheckBoxSetting LabelLineCheckBox, SECTION_CURVE_SOLVER, KEY_LABEL_LINE
   ControlsStatesLine
End Sub



'INCLUDE PT TO PC CHECKBOX
Private Sub IncludePTtoPCCheckBox_Click()
   SaveCheckBoxSetting includePTtoPCCheckBox, SECTION_CURVE_SOLVER, KEY_INCLUDE_PT_TO_PC
End Sub



'LINE DRAW SYMBOL ON PT CHECKBOX
Private Sub DrawSymbolPTCheckBox_Click()
   SaveCheckBoxSetting DrawSymbolPTCheckBox, SECTION_CURVE_SOLVER, KEY_DRAW_SYMBOL_PT
End Sub



'LINE DRAW SYMBOL ON PC CHECKBOX
Private Sub DrawSymbolPCCheckBox_Click()
   SaveCheckBoxSetting DrawSymbolPCCheckBox, SECTION_CURVE_SOLVER, KEY_DRAW_SYMBOL_PC
End Sub



'PASS TO CURVE BUTTON
Private Sub PassToCurveButton_Click()
'MAKE SURE NOTHING IS UNENTERED
   CalcTangent
'MAKE SURE THERE WAS A SOLUTION
   If Not PassToCurveButton.enabled Then
      Exit Sub
   End If

'PASS ON APPROPRIATE VALUES
   If LinePCStaOption.value Then
      PCStaTextBox.text = LinePCStationTextBox.text
   Else
      PCStaTextBox.text = PCStaCalcedLabel.Caption
   End If
   PCStaTextBox_AfterUpdate
   OptionTangentIn.value = True
   TangentInTextBox.text = LineDirectionTextBox.text
   TangentInTextBox_AfterUpdate

'BRING CURVE TAB TO FOREGROUND
   Me.MainMultiPage.value = 0

'START IN RADIUS FIELD
   RadiusTextBox.SetFocus
End Sub



'LINE DRAW IT BUTTON
Private Sub DrawLineButton_Click()
'MAKE SURE EVERYTHING IS ENTERED AND OKAY
   CalcTangent
   If DrawLineButton.enabled Then
'SET PLACEMENT TYPE
      ElementTypeGlobal = ELEMENT_TYPE_LINE
'CANCEL FLAG
      doAdditional = False
'PLACE THE ELEMENT
      Me.Hide
      Dim myTool As New CurveSolverPrimitive
      Set myTool.hostForm = Me
      CommandState.StartPrimitive myTool
   End If
End Sub



'PASS TO SPIRAL BUTTON
Private Sub LToSpButton_Click()
'MAKE SURE NOTHING IS UNENTERED
   CalcTangent
'MAKE SURE THERE WAS A SOLUTION
   If Not LToSpButton.enabled Then
      Exit Sub
   End If

'SET APPROPRIATE TYPE OF SPIRAL
   InGoingOption.value = True

'PASS ON APPROPRIATE VALUES
   If LinePCStaOption.value Then
      StartStationTextBox.text = LinePCStationTextBox.text
   Else
      StartStationTextBox.text = PCStaCalcedLabel.Caption
   End If
   StartStationTextBox_AfterUpdate
   SpiralTanInTextBox.text = LineDirectionTextBox.text
   SpiralTanInTextBox_AfterUpdate

'BRING CURVE TAB TO FOREGROUND
   Me.MainMultiPage.value = 5

'START IN NEXT FIELD
   If RadiusButton.value Then
      RadTextBox.SetFocus
   End If
   If SpiralAngleButton.value Then
      SpiralAngleTextBox.SetFocus
   End If
End Sub



'*************************************************************************************************************
'******************************************SPIRAL SOLUTION TAB************************************************
'LEFT HAND SPIRAL CURVE RADIO BUTTON
Private Sub LHSpiralOption_Click()
   SaveSpiralOrientation
   CalcSpiral
End Sub



'RIGHT HAND CURVE RADIO BUTTON
Private Sub RHSpiralOption_Click()
   SaveSpiralOrientation
   CalcSpiral
End Sub



'SAVE SPIRAL ORIENTATION SETTING
Private Sub SaveSpiralOrientation()
   If LHSpiralOption.value = True Then
      SaveSetting APP_NAME, SECTION_CURVE_SOLVER, KEY_SPIRAL_ORIENT, OPTION_LEFT
   Else
      SaveSetting APP_NAME, SECTION_CURVE_SOLVER, KEY_SPIRAL_ORIENT, OPTION_RIGHT
   End If
End Sub



'INGOING RADIO BUTTON
Private Sub InGoingOption_Click()
   SaveSpiralType
   CalcSpiral
End Sub



'OUTGOING RADIO BUTTON
Private Sub OutgoingOption_Click()
   SaveSpiralType
   CalcSpiral
End Sub



'SAVE SPIRAL TYPE SETTING
Private Sub SaveSpiralType()
   Dim addsString As String
   addsString = "Adds """
   Dim prefixString As String
   prefixString = """ prefix to the stationing text."
   Dim enterString As String
   enterString = "Enter the text to replace """
   Dim substitutesString As String
   substitutesString = "Substitutes entered text for """
   Dim inString As String
   inString = """ in the stationing text."
   Dim quoteDotString As String
   quoteDotString = """."
   
   If InGoingOption.value = True Then
      SaveSetting APP_NAME, SECTION_CURVE_SOLVER, KEY_SPIRAL_INGOING, OPTION_TRUE
      SpiralPassButton.Caption = "Pass to Curve"
      SpiralPassButton.ControlTipText = "Pass info. to Simple Curve tab."
      StartDefPrefixOption.Caption = """" & TEXT_PREFIX_TS & """"
      StartDefPrefixOption.ControlTipText = addsString & TEXT_PREFIX_TS & prefixString
      StartPrefixTextBox.ControlTipText = enterString & TEXT_PREFIX_TS & quoteDotString
      StartOtherOption.ControlTipText = substitutesString & TEXT_PREFIX_TS & inString
      EndDefPrefixOption.Caption = """" & TEXT_PREFIX_SC & """"
      EndDefPrefixOption.ControlTipText = addsString & TEXT_PREFIX_SC & prefixString
      EndOtherOption.ControlTipText = substitutesString & TEXT_PREFIX_SC & inString
      EndPrefixTextBox.ControlTipText = enterString & TEXT_PREFIX_SC & quoteDotString
   Else
      SaveSetting APP_NAME, SECTION_CURVE_SOLVER, KEY_SPIRAL_INGOING, OPTION_FALSE
      SpiralPassButton.Caption = "Pass to Line"
      SpiralPassButton.ControlTipText = "Pass info. to Line tab."
      StartDefPrefixOption.Caption = """" & TEXT_PREFIX_CS & """"
      StartDefPrefixOption.ControlTipText = addsString & TEXT_PREFIX_CS & prefixString
      StartPrefixTextBox.ControlTipText = enterString & TEXT_PREFIX_CS & quoteDotString
      StartOtherOption.ControlTipText = substitutesString & TEXT_PREFIX_CS & inString
      EndDefPrefixOption.Caption = """" & TEXT_PREFIX_ST & """"
      EndDefPrefixOption.ControlTipText = addsString & TEXT_PREFIX_ST & prefixString
      EndOtherOption.ControlTipText = substitutesString & TEXT_PREFIX_ST & inString
      EndPrefixTextBox.ControlTipText = enterString & TEXT_PREFIX_ST & quoteDotString
   End If
End Sub



'STARTING STATION TEXTBOX
Private Sub StartStationTextBox_AfterUpdate()
   SaveStationEntry StartStationTextBox, SECTION_CURVE_SOLVER, KEY_STATION_START, stationStyleGlobal, PRECISION_LINEAR
   CalcSpiral
End Sub

Private Sub StartStationTextBox_Enter()
   SelectAllText StartStationTextBox
End Sub



'START STATION PICK BUTTON
Private Sub PickStartStaButton_Click()
   LaunchPickText PICK_TYPE_START_STA
End Sub



'SPIRAL TANGENT IN TEXTBOX
Private Sub SpiralTanInTextBox_AfterUpdate()
   SaveDirEntry SpiralTanInTextBox, SECTION_CURVE_SOLVER, KEY_SPIRAL_TANGENT_IN, angleStyleGlobal, AngPrec()
   CalcSpiral
End Sub

Private Sub SpiralTanInTextBox_Enter()
   SelectAllText SpiralTanInTextBox
End Sub



'SPIRAL TANGENT IN PICK BUTTON
Private Sub PickSpiralTanInButton_Click()
   LaunchPickText PICK_TYPE_SPIRAL_TAN_IN
End Sub



'RADIUS RADIO BUTTON
Private Sub RadiusButton_Click()
   SaveSpiralDefType
   ControlsStatesSpiral
   CalcSpiral
End Sub



'RADIUS TEXTBOX
Private Sub RadTextBox_AfterUpdate()
   SaveNonnegativeEntry RadTextBox, SECTION_CURVE_SOLVER, KEY_SPIRAL_RADIUS, MAX_RADIUS, MAX_PRECISION_RADIUS, False, 500#, PRECISION_LINEAR
   CalcSpiral
End Sub

Private Sub RadTextBox_Enter()
   SelectAllText RadTextBox
End Sub



'SPIRAL ANGLE RADIO BUTTON
Private Sub SpiralAngleButton_Click()
   SaveSpiralDefType
   ControlsStatesSpiral
   CalcSpiral
End Sub


'SAVE SPIRAL DEFINITION TYPE SETTING
Private Sub SaveSpiralDefType()
   If RadiusButton.value = True Then
      SaveSetting APP_NAME, SECTION_CURVE_SOLVER, KEY_SPIRAL_DEF_TYPE, OPTION_RADIUS
   Else
      SaveSetting APP_NAME, SECTION_CURVE_SOLVER, KEY_SPIRAL_DEF_TYPE, OPTION_SPIRAL_ANGLE
   End If
End Sub



'SPIRAL ANGLE TEXTBOX
Private Sub SpiralAngleTextBox_AfterUpdate()
   SaveDeltaEntry SpiralAngleTextBox, SECTION_CURVE_SOLVER, KEY_SPIRAL_ANGLE, angleStyleGlobal, AngPrec()
   CalcSpiral
End Sub

Private Sub SpiralAngleTextBox_Enter()
   SelectAllText SpiralAngleTextBox
End Sub



'SPIRAL LENGTH TEXTBOX
Private Sub LengthTextBox_AfterUpdate()
   SaveNonnegativeEntry LengthTextBox, SECTION_CURVE_SOLVER, KEY_SPIRAL_LEGNTH, MAX_DISTANCE, MAX_PRECISION_DISTANCE, False, 200#, PRECISION_LINEAR
   CalcSpiral
End Sub

Private Sub LengthTextBox_Enter()
   SelectAllText LengthTextBox
End Sub



'LABEL START STATION CHECKBOX
Private Sub StartStaCheckBox_Click()
   SaveCheckBoxSetting StartStaCheckBox, SECTION_CURVE_SOLVER, KEY_LABEL_START
   ControlsStatesSpiral
End Sub



'START STATION PREFIX DEFAULT OPTION RADIO BUTTON
Private Sub StartDefPrefixOption_Click()
   SaveStartPrefixOption
   ControlsStatesSpiral
End Sub



'START STATION PREFIX OTHER OPTION RADIO BUTTON
Private Sub StartOtherOption_Click()
   SaveStartPrefixOption
   ControlsStatesSpiral
End Sub



Private Sub SaveStartPrefixOption()
   If StartDefPrefixOption.value Then
      SaveSetting APP_NAME, SECTION_CURVE_SOLVER, KEY_START_PREFIX_OPTION, OPTION_DEFAULT
   Else
      SaveSetting APP_NAME, SECTION_CURVE_SOLVER, KEY_START_PREFIX_OPTION, OPTION_OTHER
   End If
End Sub



'START STATION PREFIX TEXTBOX
Private Sub StartPrefixTextBox_AfterUpdate()
   SaveSetting APP_NAME, SECTION_CURVE_SOLVER, KEY_START_PREFIX, StartPrefixTextBox.text
End Sub

Private Sub StartPrefixTextBox_Enter()
   SelectAllText StartPrefixTextBox
End Sub



'LABEL END STATION CHECKBOX
Private Sub EndStationCheckBox_Click()
   SaveCheckBoxSetting EndStationCheckBox, SECTION_CURVE_SOLVER, KEY_LABEL_END
   ControlsStatesSpiral
End Sub



'END STATION DEFAULT PREFIX RADIO BUTTON
Private Sub EndDefPrefixOption_Click()
   SaveEndPrefixOption
   ControlsStatesSpiral
End Sub



'END STATION OTHER PREFIX RADIO BUTTON
Private Sub EndOtherOption_Click()
   SaveEndPrefixOption
   ControlsStatesSpiral
End Sub



Private Sub SaveEndPrefixOption()
   If EndDefPrefixOption.value Then
      SaveSetting APP_NAME, SECTION_CURVE_SOLVER, KEY_END_PREFIX_OPTION, OPTION_DEFAULT
   Else
      SaveSetting APP_NAME, SECTION_CURVE_SOLVER, KEY_END_PREFIX_OPTION, OPTION_OTHER
   End If
End Sub



'END STATION PREFIX TEXTBOX
Private Sub EndPrefixTextBox_AfterUpdate()
   SaveSetting APP_NAME, SECTION_CURVE_SOLVER, KEY_END_PREFIX, EndPrefixTextBox.text
End Sub

Private Sub EndPrefixTextBox_Enter()
   SelectAllText EndPrefixTextBox
End Sub



'DRAW TANGENT LINES CHECKBOX
Private Sub SpiralTangentsCheckBox_Click()
   SaveCheckBoxSetting SpiralTangentsCheckBox, SECTION_CURVE_SOLVER, KEY_SPIRAL_DRAW_TANGENTS
End Sub



'DRAW SYMBOL ON START POINT CHECKBOX
Private Sub BeginSymCheckBox_Click()
   SaveCheckBoxSetting BeginSymCheckBox, SECTION_CURVE_SOLVER, KEY_SPIRAL_DRAW_START_SYM
End Sub



'DRAW SYMBOL ON END POINT CHECKBOX
Private Sub EndSymCheckBox_Click()
   SaveCheckBoxSetting EndSymCheckBox, SECTION_CURVE_SOLVER, KEY_SPIRAL_DRAW_END_SYM
End Sub



'DRAW SPIRAL DATA CHECKBOX
Private Sub SpiralDataCheckBox_Click()
   SaveCheckBoxSetting SpiralDataCheckBox, SECTION_CURVE_SOLVER, KEY_SPIRAL_DRAW_SPIRAL_DATA
   ControlsStatesSpiral
End Sub



'SPIRAL DATA PREFIX TEXTBOX
Private Sub SpiralPrefixTextBox_AfterUpdate()
   SaveSetting APP_NAME, SECTION_CURVE_SOLVER, KEY_SPIRAL_DATA_PREFIX, SpiralPrefixTextBox.text
End Sub

Private Sub SpiralPrefixTextBox_Enter()
   SelectAllText SpiralPrefixTextBox
End Sub



'SPIRAL DATA HEADING TEXTBOX
Private Sub SpiralHeadingTextBox_AfterUpdate()
   SaveSetting APP_NAME, SECTION_CURVE_SOLVER, KEY_SPIRAL_DATA_HEADING, SpiralHeadingTextBox.text
End Sub



'SPIRAL DRAW IT BUTTON
Private Sub DrawSpiralButton_Click()
'MAKE SURE NO UNENTERED VALUES
   CalcSpiral

'MAKE SURE SOLUTION FOUND
   If DrawSpiralButton.enabled Then
'CANCEL FLAG
      doAdditional = False
'PLACE THE ELEMENT
      ElementTypeGlobal = ELEMENT_TYPE_SPIRAL
      Me.Hide
      Dim myTool As New CurveSolverPrimitive
      Set myTool.hostForm = Me
      CommandState.StartPrimitive myTool
   End If
End Sub



'PASS TO BUTTON
Private Sub SpiralPassButton_Click()
'INGOING SPIRAL, SO PASS IT TO CURVE
   If InGoingOption.value Then
'PASS ORIENTATION TO CURVE
      OptionLeft.value = LHSpiralOption.value
      OptionRight.value = RHSpiralOption.value
'SET TO DRAW CURVE FROM PC
      OptionPC.value = True
'PASS END STATION
      PCStaTextBox.text = SolvedEndStationLabel.Caption
      SaveStationEntry PCStaTextBox, SECTION_CURVE_SOLVER, KEY_PC_STA_CURVE, stationStyleGlobal, PRECISION_LINEAR
'PASS TANGENT OUT
      OptionTangentIn.value = True
      TangentInTextBox.text = SolvedTanOutLabel.Caption
      SaveDirEntry TangentInTextBox, SECTION_CURVE_SOLVER, KEY_TANGENT_IN, angleStyleGlobal, AngPrec()
'PASS RADIUS
      If RadiusButton.value Then
         RadiusTextBox.text = RadTextBox.text
      Else
         RadiusTextBox.text = RadiusCalcedLabel.Caption
      End If
      SaveNonnegativeEntry RadiusTextBox, SECTION_CURVE_SOLVER, KEY_RADIUS, MAX_RADIUS, MAX_PRECISION_RADIUS, False, 100.2, PRECISION_LINEAR
'SET CONTROL STATES
      ControlsStatesCurve
'RECALC
      CalcCurve
'BRING CURVE PAGE TO FOREGROUND
      Me.MainMultiPage.value = 0
'SET FOCUS TO APPROPRIATE FIELD
      If OptionDelta.value Then
         DeltaTextBox.SetFocus
      ElseIf OptionPTSta.value Then
         PTStaTextBox.SetFocus
      ElseIf OptionTangentOut.value Then
         TangentOutTextBox.SetFocus
      ElseIf OptionAzCCtoPT.value Then
         CCtoPTTextBox.SetFocus
      End If
   End If


'OUTGOING SPIRAL, SO PASS IT TO LINE
   If OutgoingOption.value Then
'PASS ENDING STATION TO LINE
      LinePTStaTextBox.text = SolvedEndStationLabel.Caption
      SaveStationEntry LinePTStaTextBox, SECTION_CURVE_SOLVER, KEY_PT_STA_LINE, stationStyleGlobal, PRECISION_LINEAR
'PASS TANGENT OUT
      LineDirectionTextBox.text = SolvedTanOutLabel.Caption
      SaveDirEntry LineDirectionTextBox, SECTION_CURVE_SOLVER, KEY_LINE_DIRECTION, angleStyleGlobal, AngPrec()
'RECALC
      CalcTangent
'BRING LINE PAGE TO FOREGROUND
      Me.MainMultiPage.value = 4
'SET FOCUS TO APPROPRIATE FIELD
      If LinePCStaOption.value Then
         LinePCStationTextBox.SetFocus
      ElseIf LineDistanceOption.value Then
         LineDistanceTextBox.SetFocus
      End If
   End If
End Sub



'*************************************************************************************************************
'**********************************************USERFORM EVENTS************************************************
Private Sub UserForm_Initialize()
'SET FLAG
   finishedLoadingGlobal = False

'SET ANGLE STYLE
   angleStyleGlobal = STYLE_ANGLE_SPACE Or STYLE_ANGLE_LEAD

'SET STATION STYLE TO ENGLISH
   stationStyleGlobal = 0
   
'INITIALIZE PRECISION OPTIONS
   Dim myOption As String
   myOption = GetSetting(APP_NAME, SECTION_CURVE_SOLVER, KEY_PRECISION_ANG, OPTION_PREC_ANG_SEC)
   If myOption = OPTION_PREC_ANG_SEC Then
      OptionSecond.value = True
   Else
      OptionTenthOfASecond.value = True
   End If

'INITIALIZE CURVE ORIENTATION OPTION
   myOption = GetSetting(APP_NAME, SECTION_CURVE_SOLVER, KEY_ROTATION, OPTION_LEFT)
   If myOption = OPTION_LEFT Then
      OptionLeft.value = True
   Else
      OptionRight.value = True
   End If

'INIALIZE PC STATION TEXTBOX
   LoadStaEntry PCStaTextBox, SECTION_CURVE_SOLVER, KEY_PC_STA_CURVE, stationStyleGlobal, PRECISION_LINEAR
   PCStaTextBox.MaxLength = MAX_LEN_STA_STRING
   PCStaTextBox.ControlTipText = TOOL_TIP_ENTER_STATION

'INITIALIZE RADIUS TEXTBOX
   LoadRadiusEntry RadiusTextBox, SECTION_CURVE_SOLVER, KEY_RADIUS, PRECISION_LINEAR
   RadiusTextBox.MaxLength = MAX_LEN_RADIUS_STRING

'INITIALIZE CURVE DIRECTION OPTION BUTTONS
   myOption = GetSetting(APP_NAME, SECTION_CURVE_SOLVER, KEY_CURVE_IN_TYPE, OPTION_CURVE_IN_TYPE_TANGENT)
   If myOption = OPTION_CURVE_IN_TYPE_TANGENT Then
      OptionTangentIn.value = True
   Else
      OptionPCtoCC.value = True
   End If

'INITIALIZE TANGENT IN TEXTBOX AND CALCED LABEL
   LoadDirEntry TangentInTextBox, SECTION_CURVE_SOLVER, KEY_TANGENT_IN
   TangentInTextBox.MaxLength = MAX_LEN_DIR_STRING
   TangentInTextBox.ControlTipText = TOOL_TIP_ENTER_DIRECTION
   SaveDirEntry TangentInTextBox, SECTION_CURVE_SOLVER, KEY_TANGENT_IN, angleStyleGlobal, AngPrec()
   InitCalcedLabel TanInCalcLabel

'INITIALIZE P.C. TO C.C. TEXTBOX AND CALCED LABEL
   LoadDirEntry PCtoCCTextBox, SECTION_CURVE_SOLVER, KEY_PC2CC
   PCtoCCTextBox.MaxLength = MAX_LEN_DIR_STRING
   PCtoCCTextBox.ControlTipText = TOOL_TIP_ENTER_DIRECTION
   SaveDirEntry PCtoCCTextBox, SECTION_CURVE_SOLVER, KEY_PC2CC, angleStyleGlobal, AngPrec()
   InitCalcedLabel PcToCcCalcedLabel


'INITALIZE CURVE DIRECTION OUT OPTION
   myOption = GetSetting(APP_NAME, SECTION_CURVE_SOLVER, KEY_CURVE_OUT_TYPE, OPTION_CURVE_OUT_TYPE_DELTA)
   Select Case myOption
      Case OPTION_CURVE_OUT_TYPE_DELTA
         OptionDelta.value = True
      Case OPTION_CURVE_OUT_TYPE_PT_STA
         OptionPTSta.value = True
      Case OPTION_CURVE_OUT_TYPE_TAN_OUT
         OptionTangentOut.value = True
      Case Else
         OptionAzCCtoPT.value = True
   End Select

'INITIALIZE DELTA TEXTBOX AND CALCED LABEL
   LoadDirEntry DeltaTextBox, SECTION_CURVE_SOLVER, KEY_DELTA
   DeltaTextBox.MaxLength = MAX_LEN_DIR_STRING
   SaveDeltaEntry DeltaTextBox, SECTION_CURVE_SOLVER, KEY_DELTA, angleStyleGlobal, AngPrec()
   InitCalcedLabel DeltaCalcedLabel

'INITIALIZE P.T. STATION FOR CURVE TEXTBOX AND CALCED LABEL
   LoadStaEntry PTStaTextBox, SECTION_CURVE_SOLVER, KEY_PT_STA_CURVE, stationStyleGlobal, PRECISION_LINEAR
   PTStaTextBox.MaxLength = MAX_LEN_STA_STRING
   SaveStationEntry PTStaTextBox, SECTION_CURVE_SOLVER, KEY_PT_STA_CURVE, stationStyleGlobal, PRECISION_LINEAR
   PTStaTextBox.ControlTipText = TOOL_TIP_ENTER_STATION
   InitCalcedLabel PtStaCalcedLabel

'INITIALIZE TANGENT OUT TEXTBOX AND CALCED LABEL
   LoadDirEntry TangentOutTextBox, SECTION_CURVE_SOLVER, KEY_TANGENT_OUT
   TangentOutTextBox.MaxLength = MAX_LEN_DIR_STRING
   TangentOutTextBox.ControlTipText = TOOL_TIP_ENTER_DIRECTION
   SaveDirEntry TangentOutTextBox, SECTION_CURVE_SOLVER, KEY_TANGENT_OUT, angleStyleGlobal, AngPrec()
   InitCalcedLabel TanOutCalcedLabel

'INITIALIZE C.C. TO P.T. TEXTBOX AND CALCED LABEL
   LoadDirEntry CCtoPTTextBox, SECTION_CURVE_SOLVER, KEY_CC2PT
   CCtoPTTextBox.MaxLength = MAX_LEN_DIR_STRING
   CCtoPTTextBox.ControlTipText = TOOL_TIP_ENTER_DIRECTION
   SaveDirEntry CCtoPTTextBox, SECTION_CURVE_SOLVER, KEY_CC2PT, angleStyleGlobal, AngPrec()
   InitCalcedLabel CcToPtCalcedLabel

'INITIALIZE DRAW IT FROM OPTION
   myOption = GetSetting(APP_NAME, SECTION_CURVE_SOLVER, KEY_DRAW_FROM, OPTION_PC)
   If myOption = OPTION_PC Then
      OptionPC.value = True
   Else
      OptionPI.value = True
   End If

'INITIALIZE DRAW RADIAL LINES CHECK BOX
   InitializeCheckBox RadialCheckbox, SECTION_CURVE_SOLVER, KEY_DRAW_RADIALS

'INITIALIZE R= LABEL ON PC CHECK BOX
   InitializeCheckBox RequalsPCCheckBox, SECTION_CURVE_SOLVER, KEY_DRAW_RAD_ON_PC

'INITIALIZE R= LABEL ON PT CHECK BOX
   InitializeCheckBox RequalsPTCheckBox, SECTION_CURVE_SOLVER, KEY_DRAW_RAD_ON_PT

'INITIALIZE DRAW TANGENTS CHECK BOX
   InitializeCheckBox TangentLinesCheckBox, SECTION_CURVE_SOLVER, KEY_DRAW_TANGENTS

'INITIALIZE LABEL PC STATION CHECK BOX
   InitializeCheckBox PCStationCheckBox, SECTION_CURVE_SOLVER, KEY_LABEL_PC, False

'INITIALIZE CURVE PC PREFIX OPTION
   myOption = GetSetting(APP_NAME, SECTION_CURVE_SOLVER, KEY_LABEL_PC_OTHER, OPTION_TRUE)
   If myOption = OPTION_TRUE Then
      OptionOtherPCPrefix.value = True
   Else
      OptionPCPrefix.value = True
   End If

'INITIALIZE P.C. TEXTBOX
   PCprefixTextBox.text = GetSetting(APP_NAME, SECTION_CURVE_SOLVER, KEY_LABEL_PC_OTHER_TEXT, "")
   PCprefixTextBox.MaxLength = MAX_LEN_PREFIX

'INITIALIZE LABEL PT STATION CHECK BOX
   InitializeCheckBox PTStationCheckBox, SECTION_CURVE_SOLVER, KEY_LABEL_PT, False

'INITIALIZE CURVE P.T. PREFIX OPTION
   myOption = GetSetting(APP_NAME, SECTION_CURVE_SOLVER, KEY_LABEL_PT_OTHER, OPTION_TRUE)
   If myOption = OPTION_TRUE Then
      OptionOtherPTPrefix.value = True
   Else
      OptionPTPrefix.value = True
   End If

'INITIALIZE P.T. PREFIX TEXTBOX
   PTprefixTextBox.text = GetSetting(APP_NAME, SECTION_CURVE_SOLVER, KEY_LABEL_PT_OTHER_TEXT, "")
   PTprefixTextBox.MaxLength = MAX_LEN_PREFIX
   
'INITIALIZE DRAW SYMBOL ON PC CHECKBOX
   InitializeCheckBox PCSymbolCheckBox, SECTION_CURVE_SOLVER, KEY_DRAW_PC_SYMBOL, False

'INITIALIZE DRAW SYMBOL ON PT CHECKBOX
   InitializeCheckBox PTSymbolCheckBox, SECTION_CURVE_SOLVER, KEY_DRAW_PT_SYMBOL, False

'INITIALIZE DRAW CURVE DATA CHECKBOX
   InitializeCheckBox CurveDataCheckBox, SECTION_CURVE_SOLVER, KEY_CURVE_DATA, False
   
'INITIALIZE CURVE DATA PREFIX TEXTBOX
   CurveDataPrefixTextBox.text = GetSetting(APP_NAME, SECTION_CURVE_SOLVER, KEY_PREFIX, "{ ")
   CurveDataPrefixTextBox.MaxLength = MAX_LEN_PREFIX
   
'INITIALIZE HEADING TEXTBOX
   HeadingTextBox.text = GetSetting(APP_NAME, SECTION_CURVE_SOLVER, KEY_HEADING, DEFAULT_CURVE_DATA_HEADING)
   HeadingTextBox.MaxLength = MAX_LEN_HEADING
   
'INITIALIZE TEXT ALIGNMENT STATES
   myOption = GetSetting(APP_NAME, SECTION_CURVE_SOLVER, KEY_ALIGNED, OPTION_LEFT)
   If myOption = OPTION_LEFT Then
      AlignLeftOption.value = True
   Else
      AlignRightOption.value = True
   End If

'INITIALIZE LABEL PC STATION CHECKBOX
   InitializeCheckBox SpiralCheckBox, SECTION_CURVE_SOLVER, KEY_SPIRAL_MODE, False



'POPULATE BASELINE SETTINGS COMBO BOXES
   PopulateLevelBox BaselineLevelComboBox, SECTION_CURVE_SOLVER, KEY_BASELINE_LEVEL
   PopulateColorBox BaselineColorComboBox, SECTION_CURVE_SOLVER, KEY_BASELINE_COLOR
   PopulateLinestyleBox BaselineStyleComboBox, SECTION_CURVE_SOLVER, KEY_BASELINE_STYLE
   PopulateWeightBox BaselineWeightComboBox, SECTION_CURVE_SOLVER, KEY_BASELINE_WEIGHT

'POPULATE RADIAL LINES SETTINGS COMBO BOXES
   PopulateLevelBox RadialLinesLevelComboBox, SECTION_CURVE_SOLVER, KEY_RADIALS_LEVEL
   PopulateColorBox RadialLinesColorComboBox, SECTION_CURVE_SOLVER, KEY_RADIALS_COLOR
   PopulateLinestyleBox RadialLinesStyleComboBox, SECTION_CURVE_SOLVER, KEY_RADIALS_STYLE
   PopulateWeightBox RadialLinesWeightComboBox, SECTION_CURVE_SOLVER, KEY_RADIALS_WEIGHT

'POPULATE OTHER TEXT SETTINGS COMBO BOXES
   PopulateLevelBox OtherTextLevelComboBox, SECTION_CURVE_SOLVER, KEY_TEXT_LEVEL
   PopulateColorBox OtherTextColorComboBox, SECTION_CURVE_SOLVER, KEY_TEXT_COLOR
   PopulateLinestyleBox OtherTextStyleComboBox, SECTION_CURVE_SOLVER, KEY_TEXT_STYLE
   PopulateWeightBox OtherTextWeightComboBox, SECTION_CURVE_SOLVER, KEY_TEXT_WEIGHT
   PopulateFontBox OtherTextFontComboBox, SECTION_CURVE_SOLVER, KEY_TEXT_FONT






'POPULATE CURVE DATA SETTINGS COMBO BOXES
   PopulateLevelBox CurveDataLevelComboBox, SECTION_CURVE_SOLVER, KEY_CURVE_DATA_LEVEL
   PopulateColorBox CurveDataColorComboBox, SECTION_CURVE_SOLVER, KEY_CURVE_DATA_COLOR
   PopulateLinestyleBox CurveDataStyleComboBox, SECTION_CURVE_SOLVER, KEY_CURVE_DATA_STYLE
   PopulateWeightBox CurveDataWeightComboBox, SECTION_CURVE_SOLVER, KEY_CURVE_DATA_WEIGHT
   PopulateFontBox CurveDataFontComboBox, SECTION_CURVE_SOLVER, KEY_CURVE_DATA_FONT
   
'POPULATE SYMBOLS SETTINGS COMBO BOXES
   PopulateLevelBox SymbolsLevelComboBox, SECTION_CURVE_SOLVER, KEY_SYMBOL_LEVEL
   PopulateColorBox SymbolsColorComboBox, SECTION_CURVE_SOLVER, KEY_SYMBOL_COLOR
   PopulateLinestyleBox SymbolsStyleComboBox, SECTION_CURVE_SOLVER, KEY_SYMBOL_STYLE
   PopulateWeightBox SymbolsWeightComboBox, SECTION_CURVE_SOLVER, KEY_SYMBOL_WEIGHT




'INITIALIZE LINE P.T. STATION TEXTBOX
   LoadStaEntry LinePTStaTextBox, SECTION_CURVE_SOLVER, KEY_PT_STA_LINE, stationStyleGlobal, PRECISION_LINEAR
   LinePTStaTextBox.MaxLength = MAX_LEN_STA_STRING
   LinePTStaTextBox.ControlTipText = TOOL_TIP_ENTER_STATION

'INITIALIZE LINE DIRECTION TEXTBOX
   LoadDirEntry LineDirectionTextBox, SECTION_CURVE_SOLVER, KEY_LINE_DIRECTION
   LineDirectionTextBox.MaxLength = MAX_LEN_DIR_STRING
   LineDirectionTextBox.ControlTipText = TOOL_TIP_ENTER_DIRECTION
   SaveDirEntry LineDirectionTextBox, SECTION_CURVE_SOLVER, KEY_LINE_DIRECTION, angleStyleGlobal, AngPrec()

'INITIALIZE LINE P.C. STATION TEXTBOX AND CALCED LABEL
   LoadStaEntry LinePCStationTextBox, SECTION_CURVE_SOLVER, KEY_PC_STA_LINE, stationStyleGlobal, PRECISION_LINEAR
   LinePCStationTextBox.MaxLength = MAX_LEN_STA_STRING
   LinePCStationTextBox.ControlTipText = TOOL_TIP_ENTER_STATION
   InitCalcedLabel PCStaCalcedLabel

'INITIALIZE LINE DISTANCE TEXTBOX AND CALCED LABEL
   LoadNonnegativeEntry LineDistanceTextBox, SECTION_CURVE_SOLVER, KEY_DISTANCE, 100#, PRECISION_LINEAR
   LineDistanceTextBox.MaxLength = MAX_LEN_DIST_STRING
   InitCalcedLabel DistCalcedLabel
      
'INITIALIZE LINE P.C. STATION/DISTANCE OPTION
   myOption = GetSetting(APP_NAME, SECTION_CURVE_SOLVER, KEY_LENGTH_BY, OPTION_STATION)
   If myOption = OPTION_STATION Then
      LinePCStaOption.value = True
   Else
      LineDistanceOption.value = True
   End If

'INITIALIZE LINE LABEL P.T. STATION CHECKBOX
   InitializeCheckBox LabelPTStationCheckBox, SECTION_CURVE_SOLVER, KEY_LABEL_PT_LINE

'INITIALIZE LINE PT LABEL OPTION
   myOption = GetSetting(APP_NAME, SECTION_CURVE_SOLVER, KEY_LABEL_PT_LINE_SIDE, OPTION_LEFT)
   If myOption = OPTION_LEFT Then
      LabelPTLeftOption.value = True
   Else
      LabelPTRightOption.value = True
   End If

'INITIALIZE LINE PT PREFIX OPTION
   myOption = GetSetting(APP_NAME, SECTION_CURVE_SOLVER, KEY_LABEL_PT_LN_PREFIX_OTHER, OPTION_FALSE)
   If myOption = OPTION_TRUE Then
      LabelPTOtherOption.value = True
   Else
      LabelPTOption.value = True
   End If

'INITIALIZE LINE LABEL PT PREFIX TEXTBOX
   LabelPTOtherTextBox.text = GetSetting(APP_NAME, SECTION_CURVE_SOLVER, KEY_LABEL_PT_LN_PREFIX_OTH_TXT, "")
   LabelPTOtherTextBox.MaxLength = MAX_LEN_PREFIX

'INITIALIZE LINE LABEL P.C. STATION CHECKBOX
   InitializeCheckBox LabelPCStationCheckBox, SECTION_CURVE_SOLVER, KEY_LABEL_PC_LINE

'INITIALIZE LINE LABEL P.C. SIDE OPTION
   myOption = GetSetting(APP_NAME, SECTION_CURVE_SOLVER, KEY_LABEL_PC_LINE_SIDE, OPTION_LEFT)
   If myOption = OPTION_LEFT Then
      LabelPCLeftOption.value = True
   Else
      LabelPCRightOption.value = True
   End If

'INITIALIZE LINE LABEL P.C. PREFIX OPTION
   myOption = GetSetting(APP_NAME, SECTION_CURVE_SOLVER, KEY_LABEL_PC_LN_PREFIX_OTHER, OPTION_FALSE)
   If myOption = OPTION_TRUE Then
      PCOtherOption.value = True
   Else
      PCLabelOption.value = True
   End If

'INITIALIZE LINE LABEL P.C. PREFIX TEXTBOX
   PCOtherTextBox.text = GetSetting(APP_NAME, SECTION_CURVE_SOLVER, KEY_LABEL_PC_LN_PREFIX_OTH_TXT, "")
   PCOtherTextBox.MaxLength = MAX_LEN_PREFIX
   
'INITIALIZE LABEL LINE CHECKBOX
   InitializeCheckBox LabelLineCheckBox, SECTION_CURVE_SOLVER, KEY_LABEL_LINE

'INITIALIZE INCLUDE "P.T. TO P.C." CHECKBOX
   InitializeCheckBox includePTtoPCCheckBox, SECTION_CURVE_SOLVER, KEY_INCLUDE_PT_TO_PC
   includePTtoPCCheckBox.Caption = "Include """ & TEXT_PT_TO_PC & """"
   includePTtoPCCheckBox.Width = 100.5

'INITIALIZE DRAW SYMBOL ON PT CHECK BOX
   InitializeCheckBox DrawSymbolPTCheckBox, SECTION_CURVE_SOLVER, KEY_DRAW_SYMBOL_PT
   
'INITIALIZE DRAW SYMBOL ON PC CHECK BOX
   InitializeCheckBox DrawSymbolPCCheckBox, SECTION_CURVE_SOLVER, KEY_DRAW_SYMBOL_PC



'INITIALIZE SPIRAL CURVE ORIENTATION OPTION
   myOption = GetSetting(APP_NAME, SECTION_CURVE_SOLVER, KEY_SPIRAL_ORIENT, OPTION_LEFT)
   If myOption = OPTION_LEFT Then
      LHSpiralOption.value = True
   Else
      RHSpiralOption.value = True
   End If

'INITIALIZE SPIRAL CURVE TYPE OPTION
   myOption = GetSetting(APP_NAME, SECTION_CURVE_SOLVER, KEY_SPIRAL_INGOING, OPTION_TRUE)
   If myOption = OPTION_TRUE Then
      InGoingOption.value = True
   Else
      OutgoingOption.value = True
   End If

'INITALIZE SPIRAL DEFINITION TYPE RADIO BUTTONS
   myOption = GetSetting(APP_NAME, SECTION_CURVE_SOLVER, KEY_SPIRAL_DEF_TYPE, OPTION_RADIUS)
   Select Case myOption
      Case OPTION_RADIUS
         RadiusButton.value = True
      Case OPTION_SPIRAL_ANGLE
         SpiralAngleButton.value = True
      Case Else
         RadiusButton.value = True
   End Select

'INITIALIZE PASS TO BUTTON
   SaveSpiralType

'INITIALIZE SPIRAL TANGENT IN DIRECTION TEXTBOX
   LoadDirEntry SpiralTanInTextBox, SECTION_CURVE_SOLVER, KEY_SPIRAL_TANGENT_IN
   SpiralTanInTextBox.MaxLength = MAX_LEN_DIR_STRING
   SpiralTanInTextBox.ControlTipText = TOOL_TIP_ENTER_DIRECTION
   SaveDirEntry SpiralTanInTextBox, SECTION_CURVE_SOLVER, KEY_SPIRAL_TANGENT_IN, angleStyleGlobal, AngPrec()

'INITIALIZE SPIRAL START STATION TEXTBOX AND CALCED LABEL
   LoadStaEntry StartStationTextBox, SECTION_CURVE_SOLVER, KEY_STATION_START, stationStyleGlobal, PRECISION_LINEAR
   StartStationTextBox.MaxLength = MAX_LEN_STA_STRING
   SaveStationEntry StartStationTextBox, SECTION_CURVE_SOLVER, KEY_STATION_START, stationStyleGlobal, PRECISION_LINEAR
   StartStationTextBox.ControlTipText = TOOL_TIP_ENTER_STATION

'INITIALIZE SPIRAL RADIUS TEXTBOX AND CALCED LABEL
   LoadRadiusEntry RadTextBox, SECTION_CURVE_SOLVER, KEY_SPIRAL_RADIUS, PRECISION_LINEAR
   RadTextBox.MaxLength = MAX_LEN_RADIUS_STRING
   InitCalcedLabel RadiusCalcedLabel

'INITIALIZE SPIRAL ANGLE TEXTBOX AND CALCED LABEL
   LoadDirEntry SpiralAngleTextBox, SECTION_CURVE_SOLVER, KEY_SPIRAL_ANGLE
   SpiralAngleTextBox.MaxLength = MAX_LEN_DIR_STRING
   SpiralAngleTextBox.ControlTipText = "Enter Spiral Angle (theta)"
   SaveDirEntry SpiralAngleTextBox, SECTION_CURVE_SOLVER, KEY_SPIRAL_ANGLE, angleStyleGlobal, AngPrec()
   InitCalcedLabel SpiralAngleCalcedLabel

'INITIALIZE SPIRAL LENGTH TEXTBOX
   LoadNonnegativeEntry LengthTextBox, SECTION_CURVE_SOLVER, KEY_SPIRAL_LEGNTH, 200#, PRECISION_LINEAR
   LengthTextBox.MaxLength = MAX_LEN_DIST_STRING

'INITIALIZE LABEL START STATION CHECKBOX
   InitializeCheckBox StartStaCheckBox, SECTION_CURVE_SOLVER, KEY_LABEL_START

'INITIALIZE START STATION PREFIX OPTION
   myOption = GetSetting(APP_NAME, SECTION_CURVE_SOLVER, KEY_START_PREFIX_OPTION, OPTION_DEFAULT)
   If myOption = OPTION_DEFAULT Then
      StartDefPrefixOption.value = True
   Else
      StartOtherOption.value = True
   End If

'INITIALIZE START STATION PREFIX TEXTBOX
   StartPrefixTextBox.text = GetSetting(APP_NAME, SECTION_CURVE_SOLVER, KEY_START_PREFIX, "")
   StartPrefixTextBox.MaxLength = MAX_LEN_PREFIX

'INITIALIZE LABEL END STATION CHECKBOX
   InitializeCheckBox EndStationCheckBox, SECTION_CURVE_SOLVER, KEY_LABEL_END

'INITIALIZE END STATION PREFIX RADIO BUTTON
   myOption = GetSetting(APP_NAME, SECTION_CURVE_SOLVER, KEY_END_PREFIX_OPTION, OPTION_DEFAULT)
   If myOption = OPTION_DEFAULT Then
      EndDefPrefixOption.value = True
   Else
      EndOtherOption.value = True
   End If

'INITIALIZE END STATION PREFIX TEXTBOX
   EndPrefixTextBox.text = GetSetting(APP_NAME, SECTION_CURVE_SOLVER, KEY_END_PREFIX, "")
   EndPrefixTextBox.MaxLength = MAX_LEN_PREFIX

'INITIALIZE SPIRAL DRAW TANGENTS CHECKBOX
   InitializeCheckBox SpiralTangentsCheckBox, SECTION_CURVE_SOLVER, KEY_SPIRAL_DRAW_TANGENTS

'INITIALIZE SPIRAL DRAW SYMBOL ON START POINT CHECKBOX
   InitializeCheckBox BeginSymCheckBox, SECTION_CURVE_SOLVER, KEY_SPIRAL_DRAW_START_SYM, False

'INITIALIZE SPIRAL DRAW SYMBOL ON END POINT CHECKBOX
   InitializeCheckBox EndSymCheckBox, SECTION_CURVE_SOLVER, KEY_SPIRAL_DRAW_END_SYM, False

'INITIALIZE SPIRAL DRAW SPIRAL DATA CHECKBOX
   InitializeCheckBox SpiralDataCheckBox, SECTION_CURVE_SOLVER, KEY_SPIRAL_DRAW_SPIRAL_DATA, False

'INITIALIZE SPIRAL DATA PREFIX TEXTBOX
   SpiralPrefixTextBox.text = GetSetting(APP_NAME, SECTION_CURVE_SOLVER, KEY_SPIRAL_DATA_PREFIX, "")
   SpiralPrefixTextBox.MaxLength = MAX_LEN_PREFIX

'INITIALIZE SPIRAL DATA HEADING TEXTBOX
   SpiralHeadingTextBox.text = GetSetting(APP_NAME, SECTION_CURVE_SOLVER, KEY_SPIRAL_DATA_HEADING, DEFAULT_SPIRAL_DATA_HEADING)
   SpiralHeadingTextBox.MaxLength = MAX_LEN_PREFIX



'SET COLOR OF MESSAGE LABELS
   LineErrorLabel.ForeColor = RGB(0, 0, 255)   'BLUE FOR NOW
   CurveErrorLabel.ForeColor = RGB(0, 0, 255)  'BLUE FOR NOW
   SpiralErrorLabel.ForeColor = RGB(0, 0, 255)  'BLUE FOR NOW
   
'SET CONTROL STATES
   ControlsStatesCurve
   ControlsStatesCurveOptions
   ControlsStatesLine
   ControlsStatesSpiral
   
'CALC LABELS
   CalcCurve
   CalcTangent
   CalcSpiral

'MOVE INTO LAST POSITION
   If GetSetting(APP_NAME, SECTION_CURVE_SOLVER, KEY_START_TOP, "") = "" Then
      Me.StartUpPosition = 1
   Else
      Me.StartUpPosition = 0
      Me.Top = CDbl(GetSetting(APP_NAME, SECTION_CURVE_SOLVER, KEY_START_TOP, WINDOW_DEFAULT_TOP))
      Me.Left = CDbl(GetSetting(APP_NAME, SECTION_CURVE_SOLVER, KEY_START_LEFT, WINDOW_DEFAULT_LEFT))
   End If
  
'SET MODE OF USER FORM
   SetSpiralStates

'BRING CURVE ENTRY PAGE TO FOREGROUND
   Me.MainMultiPage.value = 0



'SET FLAG
   finishedLoadingGlobal = True
End Sub



Private Sub UserForm_QueryClose(Cancel As Integer, CloseMode As Integer)
'SAVE USERFORM POSITION
   SaveSetting APP_NAME, SECTION_CURVE_SOLVER, KEY_START_TOP, FormatNumber(Me.Top, 2)
   SaveSetting APP_NAME, SECTION_CURVE_SOLVER, KEY_START_LEFT, FormatNumber(Me.Left, 2)
End Sub



Private Sub UserForm_Terminate()
   CommandState.StartDefaultCommand
End Sub



'*************************************************************************************************************
'********************************************OTHER STUFF******************************************************
Private Sub UpdateAngleTextPrecision()
   If Not finishedLoadingGlobal Then
      Exit Sub
   End If
   SaveDirEntry TangentInTextBox, SECTION_CURVE_SOLVER, KEY_TANGENT_IN, angleStyleGlobal, AngPrec()
   SaveDeltaEntry DeltaTextBox, SECTION_CURVE_SOLVER, KEY_DELTA, angleStyleGlobal, AngPrec()
   SaveDirEntry PCtoCCTextBox, SECTION_CURVE_SOLVER, KEY_PC2CC, angleStyleGlobal, AngPrec()
   SaveDirEntry TangentOutTextBox, SECTION_CURVE_SOLVER, KEY_TANGENT_OUT, angleStyleGlobal, AngPrec()
   SaveDirEntry PCtoCCTextBox, SECTION_CURVE_SOLVER, KEY_CC2PC, angleStyleGlobal, AngPrec()
   SaveDirEntry LineDirectionTextBox, SECTION_CURVE_SOLVER, KEY_LINE_DIRECTION, angleStyleGlobal, AngPrec()
   CalcCurve
   SaveDirEntry SpiralTanInTextBox, SECTION_CURVE_SOLVER, KEY_SPIRAL_TANGENT_IN, angleStyleGlobal, AngPrec()
   SaveDeltaEntry SpiralAngleTextBox, SECTION_CURVE_SOLVER, KEY_SPIRAL_ANGLE, angleStyleGlobal, AngPrec()
   CalcSpiral
End Sub



Private Function AngPrec() As Long
   If OptionSecond.value Then
      AngPrec = PRECISION_ANG_SEC
   Else
      AngPrec = PRECISION_ANG_TENTH_SEC
   End If
End Function



Private Sub InitCalcedLabel(theCalcedLabel As label)
   theCalcedLabel.ForeColor = RGB(0, 0, 255)  'BLUE FOR NOW
   theCalcedLabel.BackColor = &H8000000F      'BUTTON FACE
   theCalcedLabel.WordWrap = False
   theCalcedLabel.BorderStyle = fmBorderStyleSingle
   theCalcedLabel.SpecialEffect = fmSpecialEffectSunken
   theCalcedLabel.TextAlign = fmTextAlignCenter
   theCalcedLabel.ControlTipText = "Calculated value"
End Sub



Private Function errorString(ByVal TheError As Integer) As String
   Select Case TheError
      Case ERROR_ENTRY_BAD_FORMAT
         errorString = "Entry not understood."
      Case ERROR_DELTA_TOO_SMALL
         errorString = "Delta too small"
      Case ERROR_PC_STATION_TOO_SMALL
         errorString = "PC station too small."
      Case ERROR_DISTANCE_TOO_SMALL
         errorString = "Distance/length too small."
      Case ERROR_DISTANCE_TOO_BIG
         errorString = "Distance/length too big."
      Case ERROR_RADIUS_TOO_SMALL
         errorString = "Radius too small."
      Case ERROR_RADIUS_TOO_BIG
         errorString = "Radius too big."
      Case ERROR_PT_STATION_TOO_SMALL
         errorString = "PT station too small."
      Case ERROR_CURVE_TOO_LARGE
         errorString = "Curve too large."
      Case ERROR_PROGRAM_ISSUE
         errorString = "Program blundered."
      Case ERROR_STATION_MISMATCH
         errorString = "Unsolveable at this precision."
      Case ERROR_BAD_SPIRAL_ANGLE
         errorString = "Problem with spiral angle."
      Case ERROR_BAD_SPIRAL_LENGTH
         errorString = "Unusable Spiral Length"
      Case ERROR_RESULT_TOO_BIG
         errorString = "Results too big."
      Case Else
         errorString = "Unknown Error"
   End Select
End Function



'*************************************************************************************************************
'**********************************************CONTROL STATES*************************************************
Private Sub ControlsStatesLine()
   LinePCStationTextBox.enabled = LinePCStaOption.value
   SetFieldState LinePCStationTextBox, PCStaCalcedLabel, LinePCStaOption.value
   LineDistanceTextBox.enabled = LineDistanceOption.value
   SetFieldState LineDistanceTextBox, DistCalcedLabel, LineDistanceOption.value
   LabelPTLeftOption.enabled = LabelPTStationCheckBox.value
   LabelPTRightOption.enabled = LabelPTStationCheckBox.value
   LinePTPrefixFrame.enabled = LabelPTStationCheckBox.value
   LabelPTOption.enabled = LabelPTStationCheckBox.value
   LabelPTOtherOption.enabled = LabelPTStationCheckBox.value
   LabelPTOtherTextBox.enabled = LabelPTOtherOption.enabled And LabelPTOtherOption.value
   EnabledColor LabelPTOtherTextBox
   LabelPCLeftOption.enabled = LabelPCStationCheckBox.value
   LabelPCRightOption.enabled = LabelPCStationCheckBox.value
   LinePCPrefixFrame.enabled = LabelPCStationCheckBox.value
   PCLabelOption.enabled = LabelPCStationCheckBox.value
   PCOtherOption.enabled = LabelPCStationCheckBox.value
   PCOtherTextBox.enabled = PCOtherOption.value And PCOtherOption.enabled
   EnabledColor PCOtherTextBox
   includePTtoPCCheckBox.enabled = LabelLineCheckBox.value
End Sub



Private Sub ControlsStatesCurveOptions()
   PCPrefixFrame.enabled = PCStationCheckBox.value
   OptionPCPrefix.enabled = PCStationCheckBox.value
   OptionOtherPCPrefix.enabled = PCStationCheckBox.value
   PCprefixTextBox.enabled = OptionOtherPCPrefix.enabled And OptionOtherPCPrefix.value
   EnabledColor PCprefixTextBox
   PTPrefixFrame.enabled = PTStationCheckBox.value
   OptionPTPrefix.enabled = PTStationCheckBox.value
   OptionOtherPTPrefix.enabled = PTStationCheckBox.value
   PTprefixTextBox.enabled = OptionOtherPTPrefix.enabled And OptionOtherPTPrefix.value
   EnabledColor PTprefixTextBox
   PrefixLabel.enabled = CurveDataCheckBox.value
   HeadingLabel.enabled = CurveDataCheckBox.value
   CurveDataPrefixTextBox.enabled = CurveDataCheckBox.value
   EnabledColor CurveDataPrefixTextBox
   HeadingTextBox.enabled = CurveDataCheckBox.value
   EnabledColor HeadingTextBox
   AlignLeftOption.enabled = CurveDataCheckBox.value
   AlignRightOption.enabled = CurveDataCheckBox.value
End Sub



Private Sub ControlsStatesCurve()
   SetFieldState TangentInTextBox, TanInCalcLabel, OptionTangentIn.value
   SetFieldState PCtoCCTextBox, PcToCcCalcedLabel, OptionPCtoCC.value
   Plus180Button.enabled = OptionPCtoCC.value
   SetFieldState DeltaTextBox, DeltaCalcedLabel, OptionDelta.value
   SetFieldState PTStaTextBox, PtStaCalcedLabel, OptionPTSta.value
   SetFieldState TangentOutTextBox, TanOutCalcedLabel, OptionTangentOut.value
   SetFieldState CCtoPTTextBox, CcToPtCalcedLabel, OptionAzCCtoPT.value
End Sub



Private Sub ControlsStatesSpiral()
   SetFieldState RadTextBox, RadiusCalcedLabel, RadiusButton.value
   SetFieldState SpiralAngleTextBox, SpiralAngleCalcedLabel, SpiralAngleButton.value
   
   Dim startStaCheckValue As Boolean
   startStaCheckValue = StartStaCheckBox.value
   StartPrefixFrame.enabled = StartStaCheckBox.value
   StartDefPrefixOption.enabled = StartStaCheckBox.value
   StartOtherOption.enabled = StartStaCheckBox.value
   StartPrefixTextBox.enabled = StartOtherOption.value And StartStaCheckBox.value
   EnabledColor StartPrefixTextBox
   
   Dim endStaCheckValue As Boolean
   endStaCheckValue = EndStationCheckBox.value
   EndStationFrame.enabled = endStaCheckValue
   EndDefPrefixOption.enabled = endStaCheckValue
   EndOtherOption.enabled = endStaCheckValue
   EndPrefixTextBox.enabled = EndOtherOption.value And EndStationCheckBox.value
   EnabledColor EndPrefixTextBox
   
   Dim spiralDataCheckValue As Boolean
   spiralDataCheckValue = SpiralDataCheckBox.value
   SpiralPrefixLabel.enabled = spiralDataCheckValue
   SpiralPrefixTextBox.enabled = spiralDataCheckValue
   EnabledColor SpiralPrefixTextBox
   SpiralHeadingLabel.enabled = spiralDataCheckValue
   SpiralHeadingTextBox.enabled = spiralDataCheckValue
   EnabledColor SpiralHeadingTextBox
End Sub



Private Sub SetFieldState(theEntryTextbox As TextBox, theCalcedLabel As label, theState As Boolean)
   If theState Then
      theEntryTextbox.Visible = True
      theEntryTextbox.enabled = True
      theCalcedLabel.Visible = False
      theCalcedLabel.enabled = False
   Else
      theEntryTextbox.Visible = False
      theEntryTextbox.enabled = False
      theCalcedLabel.Visible = True
      theCalcedLabel.enabled = True
   End If
End Sub



'SPIRAL MODE
Private Sub SetSpiralStates()
   Dim showSpiral As Boolean
   showSpiral = SpiralCheckBox.value

   Me.MainMultiPage.Pages(5).Visible = showSpiral
   CToSpButton.Visible = showSpiral
   LToSpButton.Visible = showSpiral
   If showSpiral Then
      Me.Width = 213
      Me.MainMultiPage.Width = 210
      CalcSpiral
   Else
      Me.Width = 183
      Me.MainMultiPage.Width = 179
   End If
End Sub



'*************************************************************************************************************
'************************************************CALCULATIONS*************************************************
Private Sub ClearCurveCalcLabels()
   TanInCalcLabel.Caption = ""
   PcToCcCalcedLabel.Caption = ""
   DeltaCalcedLabel.Caption = ""
   PtStaCalcedLabel.Caption = ""
   TanOutCalcedLabel.Caption = ""
   CcToPtCalcedLabel.Caption = ""
   CurveErrorLabel.Caption = ""
   SolveDeltaLabel.Caption = ""
   SolveHalfDeltaLabel.Caption = ""
   RadLabel.Caption = ""
   SolveTangentLabel.Caption = ""
   SolveLongChordLabel.Caption = ""
   CurveLengthLabel.Caption = ""
   SolvedCDLabel.Caption = ""
End Sub



Private Sub ClearLineCalcLabels()
   PCStaCalcedLabel.Caption = ""
   DistCalcedLabel.Caption = ""
   LineErrorLabel.Caption = ""
End Sub



Private Sub ClearSpiralCalcLabels()
   RadiusCalcedLabel.Caption = ""
   SpiralAngleCalcedLabel.Caption = ""
   SolvedEndStationLabel.Caption = ""
   SolvedTanOutLabel.Caption = ""
   LongTanSolvedLabel.Caption = ""
   SolvedSTLabel.Caption = ""
   SpiralErrorLabel.Caption = ""
End Sub



Private Sub CalcTangent()
   Dim TheError As Integer
   If TangentCalc(TheError) Then
      PassToCurveButton.enabled = True
      DrawLineButton.enabled = True
      LToSpButton.enabled = True
   Else
      ClearLineCalcLabels
      LineErrorLabel.Caption = "Msg: " & errorString(TheError)
      PassToCurveButton.enabled = False
      DrawLineButton.enabled = False
      LToSpButton.enabled = False
   End If
End Sub



Private Function TangentCalc(ByRef TheError As Integer) As Boolean
'RETURNS TRUE IF OKAY, FALSE IF NO GOOD
   TangentCalc = False

'CLEAR OUT PREVIOUS CALCS
   ClearLineCalcLabels

'GET P.T. STATION
   Dim PTStation As Double
   Dim origPrec As Long
   If Not IsStationString(LinePTStaTextBox.text, PTStation, origPrec, stationStyleGlobal) Then
      TheError = ERROR_ENTRY_BAD_FORMAT
      Exit Function
   End If

   
'HOLDING P.C. STATION
   If LinePCStaOption.value = True Then
'GET P.C. STATION
      Dim PCStation As Double
      If Not IsStationString(LinePCStationTextBox.text, PCStation, origPrec, stationStyleGlobal) Then
         TheError = ERROR_ENTRY_BAD_FORMAT
         Exit Function
      End If
'MAKE SURE PC STATION IS GREATER THAN PT STATION
      If PTStation >= PCStation Then
         TheError = ERROR_PC_STATION_TOO_SMALL
         Exit Function
      End If
      Dim calcedDistance As Double
      calcedDistance = Round(PCStation - PTStation, PRECISION_LINEAR)
      DistCalcedLabel.Caption = FormatNumber(calcedDistance, PRECISION_LINEAR, vbTrue, vbFalse, vbTrue)
      TangentCalc = True
   End If

   
'HOLDING DISTANCE
   If LineDistanceOption.value Then
'GET DISTANCE
      Dim distance As Double
      If Not IsNonnegativeString(LineDistanceTextBox.text, False, distance, origPrec) Then
         TheError = ERROR_ENTRY_BAD_FORMAT
         Exit Function
      End If
'MAKE SURE IT'S BIG ENOUGH
      If distance <= 0 Then
         TheError = ERROR_DISTANCE_TOO_SMALL
         Exit Function
      End If
'MAKE SURE IT'S NOT TOO BIG
      If distance > MAX_DISTANCE Then
         TheError = ERROR_DISTANCE_TOO_BIG
         Exit Function
      End If
      
      
'CALC PC STATION
      Dim calcedPcStation As Double
      calcedPcStation = PTStation + distance
      PCStaCalcedLabel.Caption = StationToString(calcedPcStation, PRECISION_LINEAR, stationStyleGlobal)
      TangentCalc = True
   End If
End Function



Private Sub CalcCurve()
   Dim TheError As Integer
   If CurvCalc(TheError) Then
      PassToLineButton.enabled = True
      CToSpButton.enabled = True
      DrawItButton.enabled = tangentSolvedGlobal Or OptionPC.value
   Else
      ClearCurveCalcLabels
      PassToLineButton.enabled = False
      DrawItButton.enabled = False
      CToSpButton.enabled = False
      CurveErrorLabel.Caption = "Msg: " & errorString(TheError)
   End If
End Sub



Private Function CurvCalc(ByRef TheError As Integer) As Boolean
'RETURNS TRUE IF OKAY, FALSE IF NO GOOD

'INITIALIZE FLAG
   CurvCalc = False
   tangentSolvedGlobal = False

'CLEAR CALCULATED LABELS
   ClearCurveCalcLabels

'SOLVE FOR SOUTH AZIMUTH PC TO PI AND PC TO CC
'TANGENT IN GIVEN
   If OptionTangentIn.value Then
'GET TANEGENT IN IN SOUTH AZIMUTH
      Dim tangentInSA As Double
      Dim tangentInDirType As Integer
      Dim origPrec As Long
      Dim quad As Integer
      If Not DirStringToSAz(TangentInTextBox.text, tangentInSA, origPrec, tangentInDirType, quad) Then
         TheError = ERROR_ENTRY_BAD_FORMAT
         Exit Function
      End If
      Dim outgoingDirType As Integer
      outgoingDirType = tangentInDirType
'FOR LEFT HAND CURVE
      If OptionLeft.value Then
         Dim pcToCcInSA As Double
         pcToCcInSA = tangentInSA - 90#
         MakeSure360 pcToCcInSA
'FOR RIGHT HAND CURVE
      Else
         pcToCcInSA = tangentInSA + 90#
         MakeSure360 pcToCcInSA
      End If
      PcToCcCalcedLabel.Caption = SAzToDirectionStr(pcToCcInSA, AngPrec(), tangentInDirType, angleStyleGlobal)
   End If
      
      
'RADIAL LINE PC TO CC GIVEN, SOLVE FOR TANGENT IN
   If OptionPCtoCC.value Then
'GET PC TO CC IN SOUTH AZIMUTH
      Dim pcToccDirType As Integer
      If Not DirStringToSAz(PCtoCCTextBox.text, pcToCcInSA, origPrec, pcToccDirType, quad) Then
         TheError = ERROR_ENTRY_BAD_FORMAT
         Exit Function
      End If
      outgoingDirType = pcToccDirType
'FOR LEFT HAND CURVE
      If OptionLeft.value Then
         tangentInSA = pcToCcInSA + 90#
         MakeSure360 tangentInSA
'FOR RIGHT HAND CURVE
      Else
         tangentInSA = pcToCcInSA - 90#
         MakeSure360 tangentInSA
      End If
      TanInCalcLabel.Caption = SAzToDirectionStr(tangentInSA, AngPrec(), pcToccDirType, angleStyleGlobal)
   End If

'GET RADIUS
   Dim radius As Double
   If Not IsNonnegativeString(RadiusTextBox.text, False, radius, origPrec) Then
      TheError = ERROR_ENTRY_BAD_FORMAT
      Exit Function
   End If
'MAKE SURE NOT TOO SMALL
   If radius <= 0 Then
      TheError = ERROR_RADIUS_TOO_SMALL
      Exit Function
   End If
'MAKE SURE NOT TOO BIG
   If radius > MAX_RADIUS Then
      TheError = ERROR_RADIUS_TOO_SMALL
      Exit Function
   End If
   RadLabel.Caption = RadiusTextBox.text

'GET P.C. STATION
   Dim PCStation As Double
   If Not IsStationString(PCStaTextBox.text, PCStation, origPrec, stationStyleGlobal) Then
      TheError = ERROR_ENTRY_BAD_FORMAT
      Exit Function
   End If


'SOLVE FOR DELTA
'DELTA IS GIVEN
   If OptionDelta.value Then
'GET DELTA IN DOUBLE
      Dim degPart As Long
      Dim minPart As Long
      Dim secPart As Double
      If Not IsDeltaString(DeltaTextBox.text, origPrec, degPart, minPart, secPart) Then
         TheError = ERROR_ENTRY_BAD_FORMAT
         Exit Function
      End If
      Dim deltaDecimal As Double
      deltaDecimal = DmsToDec(degPart, minPart, secPart)
      If deltaDecimal <= 0 Then
         TheError = ERROR_DELTA_TOO_SMALL
         Exit Function
      End If
      SolveDeltaLabel.Caption = DeltaTextBox.text
   End If

   
'P.T. STATION IS GIVEN
   If OptionPTSta.value Then
'GET P.T. STATION PTStaTextBox
      Dim PTStation As Double
      If Not IsStationString(PTStaTextBox.text, PTStation, origPrec, stationStyleGlobal) Then
         TheError = ERROR_ENTRY_BAD_FORMAT
         Exit Function
      End If
'MAKE SURE P.T. IS BIGGER THAN P.C.
      If PTStation <= PCStation Then
         TheError = ERROR_PT_STATION_TOO_SMALL
         Exit Function
      End If
'CALC DELTA FROM P.T. STATION
      Dim CurveLength As Double
      CurveLength = Round(PTStation - PCStation, PRECISION_LINEAR)
      Dim deltaInRadians As Double
      deltaInRadians = CurveLength / radius
      Dim deltaFromStation As Double
      deltaFromStation = Degrees(deltaInRadians)
'MAKE SURE LENGTH OF CURVE IS NOT TOO LONG
      If deltaFromStation >= 360 Then
         TheError = ERROR_CURVE_TOO_LARGE
         Exit Function
      End If

'FILL IN CALCED DELTA LABEL
      DeltaCalcedLabel.Caption = DegreesToAngleString(deltaFromStation, AngPrec(), angleStyleGlobal)
      SolveDeltaLabel.Caption = DeltaCalcedLabel.Caption
      If Not AngleStringToDegree(DeltaCalcedLabel.Caption, deltaDecimal) Then
         TheError = ERROR_PROGRAM_ISSUE
      End If
      If deltaDecimal <= 0 Then
         TheError = ERROR_DELTA_TOO_SMALL
         Exit Function
      End If
   End If

   
'TANGENT OUT IS GIVEN
   If OptionTangentOut.value Then
'GET TANGENT OUT IN SOUTH AZIMUTH
      Dim tangentOutSA As Double
      Dim tangentOutDirType As Integer
      If Not DirStringToSAz(TangentOutTextBox.text, tangentOutSA, origPrec, tangentOutDirType, quad) Then
         TheError = ERROR_ENTRY_BAD_FORMAT
         Exit Function
      End If
      outgoingDirType = tangentOutDirType
'FOR LEFT HAND CURVE
      If OptionLeft.value = True Then
         deltaDecimal = tangentInSA - tangentOutSA
'FOR RIGHT HAND CURVE
      Else
         deltaDecimal = tangentOutSA - tangentInSA
      End If
      MakeSure360 deltaDecimal
      DeltaCalcedLabel.Caption = DegreesToAngleString(deltaDecimal, AngPrec(), angleStyleGlobal)
      SolveDeltaLabel.Caption = DeltaCalcedLabel.Caption
      If Not AngleStringToDegree(DeltaCalcedLabel.Caption, deltaDecimal) Then
         TheError = ERROR_PROGRAM_ISSUE
         Exit Function
      End If
      If deltaDecimal <= 0 Then
         TheError = ERROR_DELTA_TOO_SMALL
         Exit Function
      End If
   End If
      
   
'RADIAL LINE C.C. TO P.T. OUT IS GIVEN
   If OptionAzCCtoPT.value Then
'GET C.C. TO P.T. OUT IN SOUTH AZIMUTH
      Dim ccToPtInSA As Double
      Dim ccToPtDirType As Integer
      If Not DirStringToSAz(CCtoPTTextBox.text, ccToPtInSA, origPrec, ccToPtDirType, quad) Then
         TheError = ERROR_ENTRY_BAD_FORMAT
         Exit Function
      End If
      outgoingDirType = ccToPtDirType
      Dim ccToPcInSA As Double
      ccToPcInSA = pcToCcInSA + 180#
      MakeSure360 ccToPcInSA
'FOR LEFT HAND CURVE
      If OptionLeft.value Then
         deltaDecimal = ccToPcInSA - ccToPtInSA
'FOR RIGHT HAND CURVE
      Else
         deltaDecimal = ccToPtInSA - ccToPcInSA
      End If
      MakeSure360 deltaDecimal
      DeltaCalcedLabel.Caption = DegreesToAngleString(deltaDecimal, AngPrec(), angleStyleGlobal)
      SolveDeltaLabel.Caption = DeltaCalcedLabel.Caption
      If Not AngleStringToDegree(DeltaCalcedLabel.Caption, deltaDecimal) Then
         TheError = ERROR_PROGRAM_ISSUE
         Exit Function
      End If
      If deltaDecimal <= 0 Then
         TheError = ERROR_DELTA_TOO_SMALL
         Exit Function
      End If
   End If

   
'SOLVE FOR REST OF VARIABLES
'SOLVE LENGTH OF CURVE
   Dim lengthOfCurve As Double
   lengthOfCurve = Round(Radians(deltaDecimal) * radius, PRECISION_LINEAR)
   CurveLengthLabel.Caption = FormatNumber(lengthOfCurve, PRECISION_LINEAR, vbTrue, vbFalse, vbTrue)

'SOLVE P.T. STATION
   Dim solvedPtStation
   solvedPtStation = PCStation + lengthOfCurve
'CHECK IT AGAINST ENTERED VALUE
   If OptionPTSta.value And Round(solvedPtStation, PRECISION_LINEAR) <> Round(PTStation, PRECISION_LINEAR) Then
      TheError = ERROR_STATION_MISMATCH
      Exit Function
   End If
   PtStaCalcedLabel.Caption = StationToString(solvedPtStation, PRECISION_LINEAR, stationStyleGlobal)

'SOLVE HALF DELTA
   Dim deltaOver2 As Double
   Dim suggestedPrec As Long
   If halfDelta(SolveDeltaLabel.Caption, degPart, minPart, secPart, suggestedPrec, deltaOver2) Then
      SolveHalfDeltaLabel.Caption = DirString(degPart, minPart, secPart, suggestedPrec, DIR_TYPE_AZIMUTH, angleStyleGlobal)
   End If

'SOLVE LONG CHORD
   Dim longChord As Double
   longChord = radius * Sin(Radians(deltaOver2)) * 2
   SolveLongChordLabel.Caption = FormatNumber(longChord, PRECISION_LINEAR, vbTrue, vbFalse, vbTrue)

'SOLVE TANGENT OUT AND RADIAL LINE OUT
   If OptionLeft.value Then
      tangentOutSA = tangentInSA - deltaDecimal
      ccToPcInSA = tangentOutSA + 90#
   Else
      tangentOutSA = tangentInSA + deltaDecimal
      ccToPcInSA = tangentOutSA - 90#
   End If
   MakeSure360 tangentOutSA
   MakeSure360 ccToPcInSA
   If Not OptionTangentOut.value Then
      TanOutCalcedLabel.Caption = SAzToDirectionStr(tangentOutSA, AngPrec(), outgoingDirType, angleStyleGlobal)
   End If
   If Not OptionAzCCtoPT.value Then
      CcToPtCalcedLabel.Caption = SAzToDirectionStr(ccToPcInSA, AngPrec(), outgoingDirType, angleStyleGlobal)
   End If

'SOLVE FOR CHORD DIRECTION
   If OptionLeft.value Then
      Dim chordSA As Double
      chordSA = tangentInSA - deltaOver2
   Else
      chordSA = tangentInSA + deltaOver2
   End If
   MakeSure360 chordSA
   Dim chordDirType As Integer
   If OptionTangentIn.value Then
      chordDirType = tangentInDirType
   Else
      chordDirType = pcToccDirType
   End If
   SolvedCDLabel.Caption = SAzToDirectionStr(chordSA, suggestedPrec, chordDirType, angleStyleGlobal)

'SOLVE FOR TANGENT LENGTH IF CAN
   Dim maxDeltaForTangentDeg As Double
   maxDeltaForTangentDeg = Degrees(Atn(MAX_DISTANCE / radius) * 2#)
   If deltaDecimal <= maxDeltaForTangentDeg Then
      Dim tangentLen As Double
      tangentLen = Tan(Radians(deltaOver2)) * radius
      SolveTangentLabel.Caption = FormatNumber(tangentLen, PRECISION_LINEAR, vbTrue, vbFalse, vbTrue)
'MARK IT SOLVED IF TANGENT LEGNTH IS SOLVEABLE
      tangentSolvedGlobal = True
   End If

'RECHECK CURVE LENGTH HERE

   
   
'EXIT NICELY
   CurvCalc = True
End Function



Private Sub CalcSpiral()
   Dim TheError As Integer
   If SpiralCalc(TheError) Then
      SpiralPassButton.enabled = True
      DrawSpiralButton.enabled = True
   Else
      ClearSpiralCalcLabels
      SpiralPassButton.enabled = False
      DrawSpiralButton.enabled = False
      SpiralErrorLabel.Caption = "Msg: " & errorString(TheError)
   End If
End Sub



Private Function SpiralCalc(ByRef TheError As Integer) As Boolean
'RETURNS TRUE IF OKAY, FALSE IF NO GOOD

'INITIALIZE FLAG
   SpiralCalc = False

'MAKE SURE TAB IS VISIBILE
   If Not Me.MainMultiPage(5).Visible Then
      Exit Function
   End If

'CLEAR CALCULATED LABELS
   ClearSpiralCalcLabels

'CHECK IF LEGNTH IS OK
   If Not IsNumeric(LengthTextBox.text) Then
      TheError = ERROR_BAD_SPIRAL_LENGTH
      Exit Function
   End If
   Dim spiralLength As Double
   spiralLength = CDbl(LengthTextBox.text)
   If spiralLength <= 0 Or spiralLength > MAX_DISTANCE Then
      TheError = ERROR_BAD_SPIRAL_LENGTH
      Exit Function
   End If

'CALCULATE END STATION
   Dim startStation As Double
   Dim origPrec As Long
   If Not IsStationString(StartStationTextBox.text, startStation, origPrec, stationStyleGlobal) Then
      TheError = ERROR_ENTRY_BAD_FORMAT
      Exit Function
   End If
   Dim endStation As Double
   endStation = startStation + spiralLength
   If endStation > MAX_DISTANCE Then
      TheError = ERROR_RESULT_TOO_BIG
      Exit Function
   End If
   SolvedEndStationLabel.Caption = StationToString(endStation, PRECISION_LINEAR, stationStyleGlobal)

'CALCULATE SPIRAL ANGLE
   If SpiralAngleButton.value Then
'SPIRAL ANGLE IS GIVEN
      Dim degPart As Long
      Dim minPart As Long
      Dim secPart As Double
      If Not IsDeltaString(SpiralAngleTextBox.text, origPrec, degPart, minPart, secPart) Then
         TheError = ERROR_ENTRY_BAD_FORMAT
         Exit Function
      End If
      Dim spiralAngleDecimal As Double
      spiralAngleDecimal = DmsToDec(degPart, minPart, secPart)
      If spiralAngleDecimal >= 90# Or spiralAngleDecimal <= 0 Then
         TheError = ERROR_BAD_SPIRAL_ANGLE
         Exit Function
      End If
'SOLVE FOR RADIUS
      Dim radius As Double
      radius = (spiralLength * 90#) / (spiralAngleDecimal * Pi)
      RadiusCalcedLabel.Caption = FormatNumber(radius, PRECISION_LINEAR, vbTrue, vbFalse, vbTrue)
      radius = CDbl(RadiusCalcedLabel.Caption)
   Else
'RADIUS IS GIVEN
      If Not IsNumeric(RadTextBox.text) Then
          TheError = ERROR_ENTRY_BAD_FORMAT
         Exit Function
      End If
      radius = CDbl(RadTextBox.text)
      If radius <= 0 Then
         TheError = ERROR_RADIUS_TOO_SMALL
         Exit Function
      End If
      Dim degreeOfCurve As Double
      degreeOfCurve = 18000# / (Pi * radius)
      spiralAngleDecimal = (spiralLength * degreeOfCurve) / 200#
      If spiralAngleDecimal >= 90# Or spiralAngleDecimal <= 0# Then
         TheError = ERROR_BAD_SPIRAL_ANGLE
         Exit Function
      End If
      SpiralAngleCalcedLabel.Caption = DegreesToAngleString(spiralAngleDecimal, AngPrec(), angleStyleGlobal)
      If Not AngleStringToDegree(SpiralAngleCalcedLabel.Caption, spiralAngleDecimal) Then
'SHOULD NEVER GET HERE, CREATE ERROR IF IT DOES
         Err.Raise ERROR_NUM_562
         Exit Function
      End If
   End If

'CALCULATE TANGENT OUT
'GET TANEGENT IN IN SOUTH AZIMUTH
   Dim tangentInSA As Double
   Dim tangentInDirType As Integer
   Dim quad As Integer
   If Not DirStringToSAz(SpiralTanInTextBox.text, tangentInSA, origPrec, tangentInDirType, quad) Then
      TheError = ERROR_ENTRY_BAD_FORMAT
      Exit Function
   End If
   Dim outgoingDirType As Integer
   outgoingDirType = tangentInDirType
   If LHSpiralOption.value Then
      Dim tangentOutSA As Double
      tangentOutSA = tangentInSA - spiralAngleDecimal
   Else
      tangentOutSA = tangentInSA + spiralAngleDecimal
   End If
   MakeSure360 tangentOutSA
   SolvedTanOutLabel.Caption = SAzToDirectionStr(tangentOutSA, AngPrec(), tangentInDirType, angleStyleGlobal)

'CALCULATE LONG AND SHORT TANGENT
   Dim shortTangent As Double
   Dim longTangent As Double
   calcShortLongTanget spiralAngleDecimal, spiralLength, longTangent, shortTangent
   SolvedSTLabel.Caption = FormatNumber(shortTangent, PRECISION_LINEAR, vbTrue, vbFalse, vbTrue)
   LongTanSolvedLabel.Caption = FormatNumber(longTangent, PRECISION_LINEAR, vbTrue, vbFalse, vbTrue)

'RETURN GOOD
   SpiralCalc = True
End Function



'*************************************************************************************************************
'****************************************DRAWING THE GRAPHIC ELEMENTS*****************************************
Private Function CreateTempCurve(CurrentPosition As Point3d, template As Element) As CellElement
'CREATE ARC AS IF CURRENT POSITION IS THE PC
   Dim theArc As ArcElement
   Set theArc = CreateArcPartFromPC(CurrentPosition, template)

'CALCULATE PI FOR THIS ARC
   If TangentInTextBox.enabled Then
      Dim tanInText As String
      tanInText = TangentInTextBox.text
   Else
      tanInText = TanInCalcLabel.Caption
   End If
   Dim origPrec As Long
   Dim dirType As Integer
   Dim quad As Integer
   Dim sAzIn As Double
   If Not DirStringToSAz(tanInText, sAzIn, origPrec, dirType, quad) Then
'SHOULD NEVER GET HERE, CREATE ERROR IF IT DOES
      Err.Raise ERROR_NUM_514
   End If

   If TangentOutTextBox.enabled Then
      Dim tanOutText As String
      tanOutText = TangentOutTextBox.text
   Else
      tanOutText = TanOutCalcedLabel.Caption
   End If
   Dim sAzOut As Double
   If Not DirStringToSAz(tanOutText, sAzOut, origPrec, dirType, quad) Then
'SHOULD NEVER GET HERE, CREATE ERROR IF IT DOES
      Err.Raise ERROR_NUM_515
   End If

'CREATE THE CELL
   Dim cellArray() As Element
   ReDim cellArray(0 To 2)

'CREATE TANGENT LINES IF POSSIBLE
   If OptionPI.enabled Then
      Dim thePI As Point3d
      If CalculatePI(theArc, sAzIn, sAzOut, thePI) Then
'IF DRAWING FROM PI, CALCULATE THE ACTUAL PC
         If OptionPI.value Then
            Dim actualPC As Point3d
            actualPC.X = CurrentPosition.X - (thePI.X - CurrentPosition.X)
            actualPC.Y = CurrentPosition.Y - (thePI.Y - CurrentPosition.Y)
            actualPC.z = CurrentPosition.z
            Set theArc = CreateArcPartFromPC(actualPC, template)
            thePI = CurrentPosition
         End If
         Dim tanLineIn As LineElement
         Set tanLineIn = CreateLineElement2(template, theArc.startPoint, thePI)
         Dim tanLineOut As LineElement
         Set tanLineOut = CreateLineElement2(template, thePI, theArc.endPoint)
         ReDim Preserve cellArray(5)
         Set cellArray(3) = tanLineIn
         Set cellArray(4) = tanLineOut
      Else
'SHOULD NEVER GET HERE, CREATE ERROR IF IT DOES
         Err.Raise ERROR_NUM_516
      End If
   End If

'CREATE THE RADIAL LINES
   Dim pcRadialLine As LineElement
   Set pcRadialLine = CreateLineElement2(template, theArc.startPoint, theArc.CenterPoint)
   Dim ptRadialLine As LineElement
   Set ptRadialLine = CreateLineElement2(template, theArc.CenterPoint, theArc.endPoint)
   Set cellArray(0) = theArc
   Set cellArray(1) = pcRadialLine
   Set cellArray(2) = ptRadialLine
   Set CreateTempCurve = CreateCellElement1(vbNullString, cellArray, CurrentPosition)
End Function



Private Sub DrawPermBaseCurve(CurrentPosition As Point3d, TheView As view)
'CREATE TEMPLATES
   Dim baselineTemplate As Element
   Set baselineTemplate = CreateBaselineTemplate()
   Dim textTemplate As TextElement
   Set textTemplate = CreateBaseTextTemplate()
'CREATE ARC AS IF CURRENT POSITION IS THE PC
   Dim theArc As ArcElement
   Set theArc = CreateArcPartFromPC(CurrentPosition, baselineTemplate)

'CALCULATE PI FOR THIS ARC
   If TangentInTextBox.enabled Then
      Dim tanInText As String
      tanInText = TangentInTextBox.text
   Else
      tanInText = TanInCalcLabel.Caption
   End If
   Dim origPrec As Long
   Dim dirType As Integer
   Dim quad As Integer
   Dim sAzIn As Double
   If Not DirStringToSAz(tanInText, sAzIn, origPrec, dirType, quad) Then
'SHOULD NEVER GET HERE, CREATE ERROR IF IT DOES
      Err.Raise ERROR_NUM_517
   End If

   If TangentOutTextBox.enabled Then
      Dim tanOutText As String
      tanOutText = TangentOutTextBox.text
   Else
      tanOutText = TanOutCalcedLabel.Caption
   End If
   Dim sAzOut As Double
   If Not DirStringToSAz(tanOutText, sAzOut, origPrec, dirType, quad) Then
'SHOULD NEVER GET HERE, CREATE ERROR IF IT DOES
      Err.Raise ERROR_NUM_518
   End If
   
'CREATE TANGENT LINES IF POSSIBLE
   If OptionPI.enabled Then
      Dim thePI As Point3d
      If CalculatePI(theArc, sAzIn, sAzOut, thePI) Then
'IF DRAWING FROM PI, CALCULATE THE ACTUAL PC
         If OptionPI.value Then
            Dim actualPC As Point3d
            actualPC.X = CurrentPosition.X - (thePI.X - CurrentPosition.X)
            actualPC.Y = CurrentPosition.Y - (thePI.Y - CurrentPosition.Y)
            actualPC.z = CurrentPosition.z
            Set theArc = CreateArcPartFromPC(actualPC, baselineTemplate)
            thePI = CurrentPosition
         End If
         Dim tanLineTemplate As LineElement
         Set tanLineTemplate = CreateRadialLineTemplate()
         Dim tanLineIn As LineElement
         Set tanLineIn = CreateLineElement2(tanLineTemplate, theArc.startPoint, thePI)
         Dim tanLineOut As LineElement
         Set tanLineOut = CreateLineElement2(tanLineTemplate, thePI, theArc.endPoint)
      Else
'SHOULD NEVER GET HERE, CREATE ERROR IF IT DOES
         Err.Raise ERROR_NUM_519
      End If
   End If
   
'ADD THE BASELINE ARC TO THE DRAWING
   ActiveModelReference.AddElement theArc
   theArc.Redraw
 
'TAG IT WITH THE BEGINNING STATION
   TagMyElement theArc, TAG_NAME_BEGIN_STATION, PCStaTextBox.text
   
'TAG IT WITH THE LENGTH
   TagMyElement theArc, TAG_NAME_LENGTH, FormatNumber(theArc.length, LINEAR_PRECISION_BASELINE)
   theArc.Rewrite


'DRAW THE SYMBOLS ON PC AND PT
   Dim charSize As Double
   charSize = GetCharSize()
   Dim symbolRadius As Double
   symbolRadius = charSize / 3#
   Dim symbolsTemplate As LineElement
   Set symbolsTemplate = CreateSymbolTemplate
   
'DRAW CIRCLE ON THE PC
   If PCSymbolCheckBox.value Then
      Dim PCsymbol As EllipseElement
      Set PCsymbol = CreateEllipseElement2(symbolsTemplate, theArc.startPoint, symbolRadius, symbolRadius, Matrix3dIdentity)
      ActiveModelReference.AddElement PCsymbol
      PCsymbol.Redraw
   End If
   
'DRAW CIRCLE ON THE PT
   If PTSymbolCheckBox = True Then
      Dim PTsymbol As EllipseElement
      Set PTsymbol = CreateEllipseElement2(symbolsTemplate, theArc.endPoint, symbolRadius, symbolRadius, Matrix3dIdentity)
      ActiveModelReference.AddElement PTsymbol
      PTsymbol.Redraw
   End If

'DRAW TANGENT LINES
   If TangentLinesCheckBox.value Then
      ActiveModelReference.AddElement tanLineIn
      tanLineIn.Redraw
      ActiveModelReference.AddElement tanLineOut
      tanLineOut.Redraw
   End If

'DRAW RADIAL LINES
   If RadialCheckbox.value Then
      Dim radLineTemplate As LineElement
      Set radLineTemplate = CreateRadialLineTemplate()
      Dim pcRadialLine As LineElement
      Set pcRadialLine = CreateLineElement2(radLineTemplate, theArc.startPoint, theArc.CenterPoint)
      ActiveModelReference.AddElement pcRadialLine
      pcRadialLine.Redraw
      Dim ptRadialLine As LineElement
      Set ptRadialLine = CreateLineElement2(radLineTemplate, theArc.CenterPoint, theArc.endPoint)
      ActiveModelReference.AddElement ptRadialLine
      ptRadialLine.Redraw
   End If

'DRAW R =
   Dim pcExtLineLength As Double
   pcExtLineLength = 0
   Dim ptExtLineLength As Double
   ptExtLineLength = 0
   Dim rEqualsText As String
   rEqualsText = "R = " & RadiusTextBox.text
'DRAW "R = " ON PC
   If RequalsPCCheckBox.value Then
      Dim pcREqualsElement As TextElement
      Set pcREqualsElement = CreateTextElement1(textTemplate, rEqualsText, theArc.startPoint, Matrix3dIdentity)
      Dim texMet As Point2d
      pcREqualsElement.GetTotalTextSize texMet.X, texMet.Y
      pcExtLineLength = Max(pcExtLineLength, texMet.X)
      TextTheRadial theArc.startPoint, sAzIn, sAzToCC(sAzIn), charSize, pcREqualsElement, True
   End If
   
'DRAW "R = " ON PT
   If RequalsPTCheckBox.value Then
      Dim ptREqualsElement As TextElement
      Set ptREqualsElement = CreateTextElement1(textTemplate, rEqualsText, theArc.endPoint, Matrix3dIdentity)
      ptREqualsElement.GetTotalTextSize texMet.X, texMet.Y
      ptExtLineLength = Max(ptExtLineLength, texMet.X)
      TextTheRadial theArc.endPoint, sAzOut, sAzToCC(sAzOut), charSize, ptREqualsElement, False
   End If

'DRAW STATION ON PC
   If PCStationCheckBox.value Then
'GET THE STATION STRING
      Dim pcStationString As String
      pcStationString = TEXT_PREFIX_STATION & PCStaTextBox.text
      If OptionPCPrefix.value Then
         pcStationString = TEXT_PREFIX_PC & pcStationString
      Else
         pcStationString = PCprefixTextBox.text & pcStationString
      End If
      Dim pcStationElement As TextElement
      Set pcStationElement = CreateTextElement1(textTemplate, pcStationString, theArc.startPoint, Matrix3dIdentity)
      pcStationElement.GetTotalTextSize texMet.X, texMet.Y
      pcExtLineLength = Max(pcExtLineLength, texMet.X)
      TextTheRadial theArc.startPoint, sAzIn, sAzToCC(sAzIn), charSize, pcStationElement, False
   End If

'DRAW PC EXTENSION LINE
   If (Not RadialCheckbox.value) And (RequalsPCCheckBox.value Or PCStationCheckBox.value) Then
      pcExtLineLength = pcExtLineLength + 2 * charSize
      Dim pcExtLineEndPoint As Point3d
      pcExtLineEndPoint = CoordFwdSAz(theArc.startPoint, sAzToCC(sAzIn), pcExtLineLength)
      Dim pcExtLine As LineElement
      Set pcExtLine = CreateLineElement2(textTemplate, theArc.startPoint, pcExtLineEndPoint)
      ActiveModelReference.AddElement pcExtLine
      pcExtLine.Redraw
   End If

'DRAW STATION ON PT
   If PTStationCheckBox.value Then
      If PTStaTextBox.enabled Then
         Dim ptStationString As String
         ptStationString = PTStaTextBox.text
      Else
         ptStationString = PtStaCalcedLabel.Caption
      End If
      ptStationString = TEXT_PREFIX_STATION & ptStationString
      If OptionPTPrefix.value Then
         ptStationString = TEXT_PREFIX_PT & ptStationString
      Else
         ptStationString = PTprefixTextBox.text & ptStationString
      End If
      Dim ptStationElement As TextElement
      Set ptStationElement = CreateTextElement1(textTemplate, ptStationString, theArc.endPoint, Matrix3dIdentity)
      ptStationElement.GetTotalTextSize texMet.X, texMet.Y
      ptExtLineLength = Max(ptExtLineLength, texMet.X)
      TextTheRadial theArc.endPoint, sAzOut, sAzToCC(sAzOut), charSize, ptStationElement, True
   End If

'DRAW PT EXTENSION LINE
   If (Not RadialCheckbox.value) And (RequalsPTCheckBox.value Or PTStationCheckBox.value) Then
      ptExtLineLength = ptExtLineLength + 2 * charSize
      Dim ptExtLineEndPoint As Point3d
      ptExtLineEndPoint = CoordFwdSAz(theArc.endPoint, sAzToCC(sAzOut), ptExtLineLength)
      Dim ptExtLine As LineElement
      Set ptExtLine = CreateLineElement2(textTemplate, theArc.endPoint, ptExtLineEndPoint)
      ActiveModelReference.AddElement ptExtLine
      ptExtLine.Redraw
   End If


'DRAW CURVE DATA
   If CurveDataCheckBox.value Then
      If DeltaTextBox.enabled Then
         Dim deltaString As String
         deltaString = DeltaTextBox.text
      Else
         deltaString = DeltaCalcedLabel.Caption
      End If
      Dim degPart As Long
      Dim minPart As Long
      Dim secPart As Double
      Dim sugPrec As Long
      Dim deltaOver2 As Double
      If Not halfDelta(deltaString, degPart, minPart, secPart, sugPrec, deltaOver2) Then
         deltaOver2 = 0
      End If
      Dim sAzPcRadial As Double
      Dim radius As Double
      Inverse theArc.CenterPoint, theArc.startPoint, sAzPcRadial, radius
      If OptionLeft.value Then
         Dim midSAz As Double
         midSAz = sAzPcRadial - deltaOver2
      Else
         midSAz = sAzPcRadial + deltaOver2
      End If
      MakeSure360 midSAz
      anchorPointGlobal = CoordFwdSAz(theArc.CenterPoint, midSAz, radius)
      ElementTypeGlobal = ELEMENT_TYPE_DATA
      doAdditional = True
   End If
End Sub



Private Sub DrawPermBaseSpiral(CurrentPosition As Point3d, TheView As view)
'CREATE TEMPLATES
   Dim baselineTemplate As Element
   Set baselineTemplate = CreateBaselineTemplate()
   Dim textTemplate As TextElement
   Set textTemplate = CreateBaseTextTemplate()

'CREATE SPIRAL LINESTRING CURRENT POSITION IS THE BEGINING
   Dim theSpiral As LineElement
   Set theSpiral = CreateSpiralPart(CurrentPosition, baselineTemplate)
   ActiveModelReference.AddElement theSpiral
   theSpiral.Redraw

'TAG IT WITH THE BEGINNING STATION
   TagMyElement theSpiral, TAG_NAME_BEGIN_STATION, StartStationTextBox.text
   
'TAG IT WITH THE LENGTH
   TagMyElement theSpiral, TAG_NAME_LENGTH, LengthTextBox.text

'TAG IT WITH THE SPIRAL ANGLE IN DMS
   If SpiralAngleTextBox.enabled Then
      TagMyElement theSpiral, TAG_NAME_SPIRAL_ANGLE, SpiralAngleTextBox.text
   Else
      TagMyElement theSpiral, TAG_NAME_SPIRAL_ANGLE, SpiralAngleCalcedLabel.Caption
   End If
   
'TAG IT WITH THE LEFT-RIGHT ORIENTATION
   If LHSpiralOption.value Then
      TagMyElement theSpiral, TAG_NAME_CURVES_LEFT, OPTION_TRUE
   Else
      TagMyElement theSpiral, TAG_NAME_CURVES_LEFT, OPTION_FALSE
   End If

'TAG IT WITH INGOING-OUTGOING
   If InGoingOption.value Then
      TagMyElement theSpiral, TAG_NAME_INGOING, OPTION_TRUE
   Else
      TagMyElement theSpiral, TAG_NAME_INGOING, OPTION_FALSE
   End If

'UPDATE THE ELEMENT
   theSpiral.Rewrite

'GET SPIRAL VALUES
   Dim spiralAngleDegrees As Double
   Dim tangentInSA As Double
   Dim spiralLength As Double
   Dim startStation As Double
   getsSpiralEntries spiralAngleDegrees, tangentInSA, spiralLength, startStation
   Dim origPrec As Long
   Dim dirType As Integer
   Dim quad As Integer
   Dim tangentOutSA As Double
   If Not DirStringToSAz(SolvedTanOutLabel.Caption, tangentOutSA, origPrec, dirType, quad) Then
      Err.Raise ERROR_NUM_568
   End If
   
'DRAW THE SYMBOLS ON START AND END
   Dim charSize As Double
   charSize = GetCharSize()
   Dim symbolRadius As Double
   symbolRadius = charSize / 3#
   Dim symbolsTemplate As LineElement
   Set symbolsTemplate = CreateSymbolTemplate

'DRAW CIRCLE ON THE START OF THE SPIRAL
   If BeginSymCheckBox.value Then
      Dim startSymbol As EllipseElement
      Set startSymbol = CreateEllipseElement2(symbolsTemplate, theSpiral.startPoint, symbolRadius, symbolRadius, Matrix3dIdentity)
      ActiveModelReference.AddElement startSymbol
      startSymbol.Redraw
   End If

'DRAW CIRCLE ON THE END OF THE SPIRAL
   If EndSymCheckBox.value Then
      Dim endSymbol As EllipseElement
      Set endSymbol = CreateEllipseElement2(symbolsTemplate, theSpiral.endPoint, symbolRadius, symbolRadius, Matrix3dIdentity)
      ActiveModelReference.AddElement endSymbol
      endSymbol.Redraw
   End If

'DRAW THE TANGENT LINES
   If SpiralTangentsCheckBox.value Then
      Dim thePI As Point3d
      If Not calcPI(theSpiral.startPoint, theSpiral.endPoint, tangentInSA, tangentOutSA, thePI) Then
'SHOULD NEVER GET HERE, CREATE ERROR IF IT DOES
         Err.Raise ERROR_NUM_567
      End If
      Dim tanLineTemplate As LineElement
      Set tanLineTemplate = CreateRadialLineTemplate()
      Dim tanLineIn As LineElement
      Set tanLineIn = CreateLineElement2(tanLineTemplate, theSpiral.startPoint, thePI)
      ActiveModelReference.AddElement tanLineIn
      tanLineIn.Redraw
      Dim tanLineOut As LineElement
      Set tanLineOut = CreateLineElement2(tanLineTemplate, thePI, theSpiral.endPoint)
      ActiveModelReference.AddElement tanLineOut
      tanLineOut.Redraw
   End If

'DRAW THE START SPIRAL STATION
   If StartStaCheckBox.value Then
'DRAW THE TEXT
      If StartDefPrefixOption.value Then
         If InGoingOption.value Then
            Dim prefix As String
            prefix = TEXT_PREFIX_TS
         Else
            prefix = TEXT_PREFIX_CS
         End If
      Else
         prefix = StartPrefixTextBox.text
      End If
      Dim label As String
      label = prefix & TEXT_PREFIX_STATION & StartStationTextBox.text
      Dim labelElement As TextElement
      Set labelElement = CreateTextElement1(textTemplate, label, theSpiral.startPoint, Matrix3dIdentity)
      Dim texMet As Point2d
      labelElement.GetTotalTextSize texMet.X, texMet.Y
      Dim radialAz As Double
      radialAz = tanInToRadialIn(tangentInSA, LHSpiralOption)
      TextTheRadial theSpiral.startPoint, tangentInSA, radialAz, charSize, labelElement, True
      Dim extLineLength As Double
      extLineLength = texMet.X + (charSize * 2)
      
'DRAW THE EXTENSION LINE
      Dim ExtLineEndPoint As Point3d
      ExtLineEndPoint = CoordFwdSAz(theSpiral.startPoint, radialAz, extLineLength)
      Dim extLine As LineElement
      Set extLine = CreateLineElement2(textTemplate, theSpiral.startPoint, ExtLineEndPoint)
      ActiveModelReference.AddElement extLine
      extLine.Redraw
   End If
   
'DRAW THE END SPIRAL STATION
   If EndStationCheckBox.value Then
'DRAW THE TEXT
      If EndDefPrefixOption.value Then
         If InGoingOption.value Then
            prefix = TEXT_PREFIX_SC
         Else
            prefix = TEXT_PREFIX_ST
         End If
      Else
         prefix = EndPrefixTextBox.text
      End If
      label = prefix & TEXT_PREFIX_STATION & SolvedEndStationLabel.Caption
      Set labelElement = CreateTextElement1(textTemplate, label, theSpiral.endPoint, Matrix3dIdentity)
      labelElement.GetTotalTextSize texMet.X, texMet.Y
      radialAz = tanInToRadialIn(tangentOutSA, LHSpiralOption)
      TextTheRadial theSpiral.endPoint, tangentOutSA, radialAz, charSize, labelElement, False
      extLineLength = texMet.X + (charSize * 2)
      
'DRAW THE EXTENSION LINE
      ExtLineEndPoint = CoordFwdSAz(theSpiral.endPoint, radialAz, extLineLength)
      Set extLine = CreateLineElement2(textTemplate, theSpiral.endPoint, ExtLineEndPoint)
      ActiveModelReference.AddElement extLine
      extLine.Redraw
   End If

'DRAW SPIRAL DATA
   If SpiralDataCheckBox.value Then
      If SpiralAngleTextBox.enabled Then
         Dim thetaString As String
         thetaString = SpiralAngleTextBox.text
      Else
         thetaString = SpiralAngleCalcedLabel.Caption
      End If
      anchorPointGlobal = theSpiral.Vertex(5)
      ElementTypeGlobal = ELEMENT_TYPE_SPIRAL_DATA
      doAdditional = True
   End If
End Sub



Private Sub getsSpiralEntries(ByRef spiralAngleDegrees As Double, _
                              ByRef tangentInSA As Double, _
                              ByRef spiralLength As Double, _
                              ByRef startStation As Double)
'GET SPIRAL ANGLE
   If SpiralAngleButton.value Then
      Dim angleText As String
      angleText = SpiralAngleTextBox.text
   Else
      angleText = SpiralAngleCalcedLabel.Caption
   End If
   If Not AngleStringToDegree(angleText, spiralAngleDegrees) Then
      Err.Raise ERROR_NUM_563
   End If

'GET TANGENT IN
   Dim origPrec As Long
   Dim dirType As Integer
   Dim quad As Integer
   If Not DirStringToSAz(SpiralTanInTextBox.text, tangentInSA, origPrec, dirType, quad) Then
      Err.Raise ERROR_NUM_564
   End If

'GET SPIRAL LENGTH
   spiralLength = CDbl(LengthTextBox.text)
   
'GET START STATION
   If Not IsStationString(StartStationTextBox.text, startStation, origPrec, stationStyleGlobal) Then
      Err.Raise ERROR_NUM_565
   End If
End Sub



Function CreateSpiralPart(CurrentPosition As Point3d, baselineTemplate As Element) As LineElement
   Dim spiralAngleDegrees As Double
   Dim tangentInSA As Double
   Dim spiralLength As Double
   Dim startStation As Double
   getsSpiralEntries spiralAngleDegrees, tangentInSA, spiralLength, startStation

'CALCULATE NEXT +00 STATION
   Dim nextBallsStation As Double
   nextBallsStation = (Int(startStation / 100) + 1) * 100#

'INITIALIZE ARRAY
   Dim linePoints() As Point3d
   ReDim linePoints(0)

'MAKE MINIMUM 8 SEGMENTS
   Dim interval As Double
   interval = spiralLength / 8


'GENERATE POINTS ON SPIRAL
   If InGoingOption.value Then
'INGOING SPIRAL
'TANGENT-SPIRAL
      linePoints(0) = CurrentPosition
      
      Dim nextBallsLength As Double
      nextBallsLength = nextBallsStation - startStation
   
      Dim length As Double
      length = interval
      
      While length < spiralLength
         Dim xSpiral As Double
         Dim ySpiral As Double
         Dim thetaAtSta As Double
         If length = nextBallsLength Then
            incrementBalls nextBallsLength
         ElseIf nextBallsLength < length Then
'BALLS STATION
            SpiralXYTheta nextBallsLength, _
                          spiralLength, _
                          spiralAngleDegrees, _
                          xSpiral, _
                          ySpiral, _
                          thetaAtSta
            ReDim Preserve linePoints(UBound(linePoints) + 1)
            linePoints(UBound(linePoints)) = SpiralXYToPoint(CurrentPosition, tangentInSA, LHSpiralOption.value, xSpiral, ySpiral)
            incrementBalls nextBallsLength
         End If
         SpiralXYTheta length, _
                       spiralLength, _
                       spiralAngleDegrees, _
                       xSpiral, _
                       ySpiral, _
                       thetaAtSta
         ReDim Preserve linePoints(UBound(linePoints) + 1)
         linePoints(UBound(linePoints)) = SpiralXYToPoint(CurrentPosition, tangentInSA, LHSpiralOption.value, xSpiral, ySpiral)
         length = length + interval
      Wend
'SPIRAL-CURVE
      SpiralXYTheta spiralLength, _
                    spiralLength, _
                    spiralAngleDegrees, _
                    xSpiral, _
                    ySpiral, _
                    thetaAtSta
      ReDim Preserve linePoints(UBound(linePoints) + 1)
      linePoints(UBound(linePoints)) = SpiralXYToPoint(CurrentPosition, tangentInSA, LHSpiralOption.value, xSpiral, ySpiral)
   Else
'OUTGOING SPIRAL
'CURVE-SPIRAL
'CALCULATE SPIRAL-TANGENT POINT
      If RHSpiralOption.value Then
         Dim tangentOutSA As Double
         Dim ySA As Double
         tangentOutSA = tangentInSA + spiralAngleDegrees
         ySA = tangentOutSA - 90#
      Else
         tangentOutSA = tangentInSA - spiralAngleDegrees
         ySA = tangentOutSA + 90#
      End If
      Dim xSA As Double
      xSA = tangentOutSA + 180#
      SpiralXYTheta spiralLength, _
                    spiralLength, _
                    spiralAngleDegrees, _
                    xSpiral, _
                    ySpiral, _
                    thetaAtSta
      Dim xyIntersect As Point3d
      xyIntersect = CoordFwdSAz(CurrentPosition, ySA, ySpiral)
      Dim STPoint As Point3d
      STPoint = CoordFwdSAz(xyIntersect, tangentOutSA, xSpiral)

'START LINESTRING
      linePoints(0) = CurrentPosition
'FILL IN LINE SEGMENTS
      Dim atStation As Double
      atStation = startStation + interval
      Dim endStation As Double
      endStation = startStation + spiralLength
      While atStation < endStation
         If atStation = nextBallsStation Then
            incrementBalls nextBallsStation
         ElseIf nextBallsStation < atStation Then
'BALLS STATION
            StationToSpiralXYTheta nextBallsStation, _
                          startStation, _
                          spiralLength, _
                          spiralAngleDegrees, _
                          False, _
                          xSpiral, _
                          ySpiral, _
                          thetaAtSta
            ReDim Preserve linePoints(UBound(linePoints) + 1)
            linePoints(UBound(linePoints)) = SpiralXYToPoint(STPoint, xSA, RHSpiralOption.value, xSpiral, ySpiral)
            incrementBalls nextBallsStation
         End If
         StationToSpiralXYTheta atStation, _
                       startStation, _
                       spiralLength, _
                       spiralAngleDegrees, _
                       False, _
                       xSpiral, _
                       ySpiral, _
                       thetaAtSta
         ReDim Preserve linePoints(UBound(linePoints) + 1)
         linePoints(UBound(linePoints)) = SpiralXYToPoint(STPoint, xSA, RHSpiralOption.value, xSpiral, ySpiral)
         atStation = atStation + interval
      Wend
'SPIRAL-TANGENT
      ReDim Preserve linePoints(UBound(linePoints) + 1)
      linePoints(UBound(linePoints)) = STPoint
   End If
'RETURN LINESTRING
   Set CreateSpiralPart = CreateLineElement1(baselineTemplate, linePoints)
End Function



Private Sub incrementBalls(ByRef balls As Double)
   balls = balls + 100
End Sub



Private Function CreateTempSpiral(CurrentPosition As Point3d, template As Element) As CellElement
'CREATE ARC AS IF CURRENT POSITION IS THE PC
   Dim theSpiral As LineElement
   Set theSpiral = CreateSpiralPart(CurrentPosition, template)

'CALCULATE PI
'GET TANGENT IN
   Dim tangentInSA As Double
   Dim origPrec As Long
   Dim dirType As Integer
   Dim quad As Integer
   If Not DirStringToSAz(SpiralTanInTextBox.text, tangentInSA, origPrec, dirType, quad) Then
      Err.Raise ERROR_NUM_566
   End If

'GET DISTANCE TO PI
   If InGoingOption.value Then
'USE LONG TANGENT IF INGOING SPIRAL
      Dim distToPI As Double
      distToPI = CDbl(LongTanSolvedLabel.Caption)
   Else
'USE SHORT TANGENT IF OUT GOING SPIRAL
      distToPI = CDbl(SolvedSTLabel.Caption)
   End If

'CALCULATE PI
   Dim piPoint As Point3d
   piPoint = CoordFwdSAz(CurrentPosition, tangentInSA, distToPI)

'CREATE THE CELL
   Dim cellArray(0 To 1) As Element
   Set cellArray(0) = theSpiral
   Set cellArray(1) = CreateLineElement2(template, CurrentPosition, piPoint)
   Set CreateTempSpiral = CreateCellElement1(vbNullString, cellArray, CurrentPosition)
End Function



Private Function sAzToCC(fwdSAz As Double) As Double
   sAzToCC = tanInToRadialIn(fwdSAz, OptionLeft)
End Function



Private Function tanInToRadialIn(fwdSAz As Double, optionButton As optionButton) As Double
   If optionButton.value Then
      tanInToRadialIn = fwdSAz - 90#
      MakeSure360 tanInToRadialIn
   Else
      tanInToRadialIn = fwdSAz + 90#
      MakeSure360 tanInToRadialIn
   End If
End Function


Private Function CalculatePI(theArc As ArcElement, tangentInSAz As Double, tangentOutSAz As Double, ByRef thePI As Point3d) As Boolean
   CalculatePI = calcPI(theArc.startPoint, theArc.endPoint, tangentInSAz, tangentOutSAz, thePI)
End Function



Private Function CreateArcPartFromPC(thePC As Point3d, template As Element) As ArcElement
'GET RADIUS
   Dim radius As Double
   radius = CDbl(RadiusTextBox.text)

'GET PC TO CC SOUTH AZIMUTH
   If PCtoCCTextBox.enabled Then
      Dim pcToCCText As String
      pcToCCText = PCtoCCTextBox.text
   Else
      pcToCCText = PcToCcCalcedLabel.Caption
   End If
   Dim origPrec As Long
   Dim dirType As Integer
   Dim quad As Integer
   Dim sAzOfPcToCc As Double
   If Not DirStringToSAz(pcToCCText, sAzOfPcToCc, origPrec, dirType, quad) Then
'SHOULD NEVER GET HERE, CREATE ERROR IF IT DOES
      Err.Raise ERROR_NUM_520
   End If

'CALCULATE THE CENTER CIRCLE
   Dim centerCircle As Point3d
   centerCircle = CoordFwdSAz(thePC, sAzOfPcToCc, radius)

'GET DELTA
   If DeltaTextBox.enabled Then
      Dim DeltaText As String
      DeltaText = DeltaTextBox.text
   Else
      DeltaText = DeltaCalcedLabel.Caption
   End If
   Dim degPart As Long
   Dim minPart As Long
   Dim secPart As Double
   If Not IsDeltaString(DeltaText, origPrec, degPart, minPart, secPart) Then
'SHOULD NEVER GET HERE, CREATE ERROR IF IT DOES
      Err.Raise ERROR_NUM_521
   End If
   Dim deltaDegrees As Double
   deltaDegrees = DmsToDec(degPart, minPart, secPart)

'CALCULATE START ANGLE
   Dim radialSAz As Double
   radialSAz = sAzOfPcToCc + 180#
   MakeSure360 radialSAz
   Dim startAngleRadians As Double
   startAngleRadians = Radians(270 - radialSAz)

'CALCULATE SWEEP ANGLE
   Dim sweepAngleRadians As Double
   sweepAngleRadians = Radians(deltaDegrees)
   If OptionRight.value Then
      sweepAngleRadians = -sweepAngleRadians
   End If

'CREATE THE ARC
   Dim baselineCurve As ArcElement
   Set CreateArcPartFromPC = CreateArcElement2(template, _
                                               centerCircle, _
                                               radius, _
                                               radius, _
                                               Matrix3dIdentity, _
                                               startAngleRadians, _
                                               sweepAngleRadians)
End Function



Private Function CreateLeaderText(CurrentPosition As Point3d, _
                                  TheView As view, _
                                  textTemplate As TextElement, _
                                  ByRef leaderCell As CellElement, _
                                  ByRef leadLengthChars As Double) As CellElement
'CREATE LEADER CELL
   Dim charSize As Double
   charSize = GetCharSize()
   Dim isLeft As Boolean
   Dim labelPoint As Point3d
   Set leaderCell = CreateArrowLeader(anchorPointGlobal, _
                                      CurrentPosition, _
                                      charSize, _
                                      textTemplate, _
                                      TheViewRotRadians(TheView), _
                                      1, _
                                      1.5, _
                                      isLeft, _
                                      labelPoint, _
                                      leadLengthChars)

'CREATE DIRECTION TEXT ELEMENT
   Dim sAzLine As Double
   Dim origPrec As Long
   Dim dirType As Integer
   Dim quad As Integer
   Dim directionString As String
   directionString = LineDirectionTextBox.text
   If DirStringToSAz(directionString, sAzLine, origPrec, dirType, quad) Then
'CHANGE DIRECTION STYLE
      directionString = SAzToDirectionStr(sAzLine, origPrec, dirType, angleStyleGlobal Or STYLE_ANGLE_NO_00_SEC Or STYLE_ANGLE_CARET)
   End If
   Dim dirTextInPt As Point3d
   dirTextInPt = labelPoint
   Dim dirTextElement As TextElement
   Set dirTextElement = CreateTextElement1(textTemplate, directionString, labelPoint, Matrix3dIdentity)
   dirTextInPt.Y = dirTextInPt.Y + charSize * 0.75
'IF ON THE LEFT, MOVE THE TEXT OVER
   If isLeft Then
      Dim texMet As Point2d
      dirTextElement.GetTotalTextSize texMet.X, texMet.Y
      dirTextInPt.X = dirTextInPt.X - texMet.X
   End If
   dirTextElement.origin = dirTextInPt
   Dim rotAngleRadians As Double
   rotAngleRadians = TheViewRotRadians(TheView)
   dirTextElement.RotateAboutZ labelPoint, rotAngleRadians
'ADD DIRECTION TEXT TO ARRAY
   Dim cellArray() As Element
   ReDim cellArray(2)
   Set cellArray(0) = dirTextElement

'ADD DISTANCE TEXT ELEMENT
   If LineDistanceTextBox.enabled Then
      Dim DistanceText As String
      DistanceText = LineDistanceTextBox.text
   Else
       DistanceText = DistCalcedLabel.Caption
   End If
   Dim disTextInPt As Point3d
   disTextInPt = labelPoint
   Dim disTextElement As TextElement
   Set disTextElement = CreateTextElement1(textTemplate, DistanceText, labelPoint, Matrix3dIdentity)
   disTextInPt.Y = disTextInPt.Y - charSize * 0.75
   If isLeft Then
      disTextElement.GetTotalTextSize texMet.X, texMet.Y
      disTextInPt.X = disTextInPt.X - texMet.X
   End If
   disTextElement.origin = disTextInPt
   disTextElement.RotateAboutZ labelPoint, rotAngleRadians
   Set cellArray(1) = disTextElement

'ADD "(P.T. TO P.C.)" TEXT ELEMENT IF NEEDED
   If includePTtoPCCheckBox.value Then
      Dim ptToPcTextElement As TextElement
      Set ptToPcTextElement = CreateTextElement1(textTemplate, TEXT_PT_TO_PC, labelPoint, Matrix3dIdentity)
      Dim ptToPcTextInPt As Point3d
      ptToPcTextInPt = labelPoint
      ptToPcTextInPt.Y = ptToPcTextInPt.Y - charSize * 2.25
      If isLeft Then
         ptToPcTextElement.GetTotalTextSize texMet.X, texMet.Y
         ptToPcTextInPt.X = ptToPcTextInPt.X - texMet.X
      End If
      ptToPcTextElement.origin = ptToPcTextInPt
      ptToPcTextElement.RotateAboutZ labelPoint, rotAngleRadians
      AddItToArray cellArray, ptToPcTextElement
   End If

'CREATE THE TEXT CELL
   Set CreateLeaderText = CreateCellElement1(vbNullString, cellArray, CurrentPosition)
End Function



Private Sub DrawSolvedLine(thePoint As Point3d, TheView As view)
'CALCULATE METRICS
   Dim charSize As Double
   charSize = GetCharSize()
   Dim ViewAngle As Double
   ViewAngle = TheViewRotRadians(TheView)
   DrawLineAndStuff thePoint, charSize

'DRAW THE AZIMUTH AND DISTANCE LINE LABEL PART
   If LabelLineCheckBox.value Then
'CREATE DIRECTION TEXT ELEMENT
      Dim directionString As String
      directionString = LineDirectionTextBox.text
'GET SOUTH AZ OF THE LINE
      Dim sAzLine As Double
      Dim origPrec As Long
      Dim dirType As Integer
      Dim quad As Integer
      If DirStringToSAz(directionString, sAzLine, origPrec, dirType, quad) Then
'CHANGE DIRECTION STYLE
         directionString = SAzToDirectionStr(sAzLine, origPrec, dirType, angleStyleGlobal Or STYLE_ANGLE_NO_00_SEC Or STYLE_ANGLE_CARET)
      End If
      Dim textTemplate As TextElement
      Set textTemplate = CreateBaseTextTemplate()
      Dim directionTextElement As TextElement
      Set directionTextElement = CreateTextElement1(textTemplate, directionString, thePoint, Matrix3dIdentity)
'CREATE DISTANCE TEXT ELEMENT
      Dim DistanceString As String
      If LineDistanceTextBox.enabled Then
         DistanceString = LineDistanceTextBox.text
      Else
         DistanceString = DistCalcedLabel.Caption
      End If
      Dim distanceTextElement As TextElement
      Set distanceTextElement = CreateTextElement1(textTemplate, DistanceString, thePoint, Matrix3dIdentity)
                  
'DETERMINE IF LINE IS POINTING LEFT OR RIGHT OF VIEW
      Dim isLeft As Boolean
      isLeft = linePointsLeft(sAzLine, ViewAngle)
         
'LABEL THE LINE
      LabelTheLine thePoint, sAzLine, CDbl(DistanceString), directionTextElement, distanceTextElement, isLeft, charSize
   End If
End Sub



Private Sub LabelTheLine(ThePT As Point3d, _
                         lineSAz As Double, _
                         lineDistance As Double, _
                         directionTextElement As TextElement, _
                         distanceTextElement As TextElement, _
                         theLinePointsLeft As Boolean, _
                         charSize As Double)
'LABELS LINE WITH DIRECTION, DISTANCE, AND MAYBE "(P.T. to P.C.)"

'CREATE TEXT
   Dim ptToPcTextElement As TextElement
   Set ptToPcTextElement = CreateTextElement1(directionTextElement, TEXT_PT_TO_PC, ThePT, Matrix3dIdentity)

'CALCULATE METRICS
   Dim dirTextMetrics As Point2d
   directionTextElement.GetTotalTextSize dirTextMetrics.X, dirTextMetrics.Y
   Dim disTextMetrics As Point2d
   distanceTextElement.GetTotalTextSize disTextMetrics.X, disTextMetrics.Y
   Dim ptToPCTextMetrics As Point2d
   ptToPcTextElement.GetTotalTextSize ptToPCTextMetrics.X, ptToPCTextMetrics.Y
   Dim arrowLength As Double
   arrowLength = ARROW_LENGTH * charSize

'CALCULATE MINIMAL LENGTHS
'SPACE DIRECTION TEXT + SPACE + ARROW + SPACE +DISTANCE TEXT + SPACE + PT TO PC TEXT + SPACE
   Dim allOnOneSideMin As Double
   allOnOneSideMin = dirTextMetrics.X + disTextMetrics.X + arrowLength + 4 * charSize
'IF USING "(P.T. to P.C.)"
   If includePTtoPCCheckBox.value Then
      allOnOneSideMin = allOnOneSideMin + ptToPCTextMetrics.X + charSize
   End If

'CALCULATE HOW MUCH TO MOVE OFF THE LINE, BASED ON LEFT/CENTER JUSTIFIED
      Dim lineSpace As Double
      lineSpace = charSize / 3#
      Dim TextOffset As Double
      TextOffset = lineSpace + charSize / 2#

'FITS ALL ABOVE LINE
   If (allOnOneSideMin) <= lineDistance Then
'SPACE IT EVENLY
      If includePTtoPCCheckBox.value Then
         Dim spaceBetween As Double
         spaceBetween = (lineDistance - (ptToPCTextMetrics.X + dirTextMetrics.X + disTextMetrics.X + arrowLength)) / 5#
'MAX SPACE BETWEEN SHOULD BE SOMETHING LIKE 40 CHARACTERS
         spaceBetween = Min(spaceBetween, (40# * charSize))
         Dim endSpace As Double
         endSpace = (lineDistance - (ptToPCTextMetrics.X + dirTextMetrics.X + disTextMetrics.X + 3# * spaceBetween + arrowLength)) / 2#
      Else
         spaceBetween = (lineDistance - (dirTextMetrics.X + disTextMetrics.X + arrowLength)) / 4#
'MAX SPACE BETWEEN SHOULD BE SOMETHING LIKE 40 CHARACTERS
         spaceBetween = Min(spaceBetween, (40# * charSize))
         endSpace = (lineDistance - (dirTextMetrics.X + disTextMetrics.X + 2# * spaceBetween + arrowLength)) / 2#
      End If

'CALCULATE INSERTION POINTS
      Dim cellInsertionPoint As Point3d
      cellInsertionPoint = ThePT
      cellInsertionPoint.Y = cellInsertionPoint.Y + TextOffset
      If theLinePointsLeft Then
         cellInsertionPoint.X = cellInsertionPoint.X + endSpace - lineDistance
      Else
         cellInsertionPoint.X = cellInsertionPoint.X + endSpace
      End If

'MOVE DIRECTION TEXT INTO POSITION
      Dim newDirTextElement As TextElement
      Set newDirTextElement = CreateTextElement1(directionTextElement, directionTextElement.text, cellInsertionPoint, Matrix3dIdentity)

'CALCULATE TAIL OF ARROW
      Dim arrowInPt As Point3d
      arrowInPt = cellInsertionPoint
      arrowInPt.X = arrowInPt.X + dirTextMetrics.X + spaceBetween

'CREATE ARROW IN POSITION
      Dim ArrowCell As CellElement
      Set ArrowCell = MyCreateArrowCell(arrowInPt, charSize, theLinePointsLeft, directionTextElement)
      
'MOVE THE DISTANCE TEXT INTO POSITION
      Dim distTextInPt As Point3d
      distTextInPt = cellInsertionPoint
      distTextInPt.X = distTextInPt.X + dirTextMetrics.X + spaceBetween + arrowLength + spaceBetween
      distanceTextElement.origin = distTextInPt

'CREATE THE CELL ARRAY
      Dim arrayForCell() As Element
      ReDim arrayForCell(3)
      Set arrayForCell(0) = newDirTextElement
      Set arrayForCell(1) = ArrowCell
      Set arrayForCell(2) = distanceTextElement

'ADD PT TO PC TEXT IF NEEDED
      If includePTtoPCCheckBox.value Then
         Dim ptToPcTextInPt As Point3d
         ptToPcTextInPt = distTextInPt
         ptToPcTextInPt.X = ptToPcTextInPt.X + disTextMetrics.X + spaceBetween
         ptToPcTextElement.origin = ptToPcTextInPt
         AddItToArray arrayForCell, ptToPcTextElement
      End If
      
'CREATE THE CELL AND ROTATE IT APPROPRIATELY
      Dim rotateToAzim As Double
      If theLinePointsLeft Then
         rotateToAzim = -Radians(lineSAz - 90#)
      Else
         rotateToAzim = -Radians(lineSAz - 270#)
      End If
      Dim AboveLineCell As CellElement
      Set AboveLineCell = CreateCellElement1(vbNullString, arrayForCell, cellInsertionPoint)
      AboveLineCell.RotateAboutZ ThePT, rotateToAzim
   
'ADD THE CELL TO THE FILE
      ActiveModelReference.AddElement AboveLineCell
      AboveLineCell.Redraw
      Exit Sub
   End If
   

'DOES NOT FIT ABOVE LINE, TRY ABOVE AND BELOW
   If (dirTextMetrics.X + arrowLength + charSize * 3#) > lineDistance Then
'LABEL WITH LEADER
      doAdditional = True
      ElementTypeGlobal = ELEMENT_TYPE_LEADER
      Exit Sub
   End If
   
   If (disTextMetrics.X + charSize * 2#) > lineDistance Then
'LABEL WITH LEADER
      doAdditional = True
      ElementTypeGlobal = ELEMENT_TYPE_LEADER
      Exit Sub
   End If

   If (ptToPCTextMetrics.X + charSize * 2#) > lineDistance Then
'LABEL WITH LEADER
      doAdditional = True
      ElementTypeGlobal = ELEMENT_TYPE_LEADER
      Exit Sub
   End If

'PLACE THE DIRECTION ON TOP OF THE LINE, PLACE DISTANCE ON THE BOTTOM
   Dim topCellInsertionPoint As Point3d
   topCellInsertionPoint = ThePT
   topCellInsertionPoint.Y = topCellInsertionPoint.Y + TextOffset
   Dim topSpacing As Double
   topSpacing = (lineDistance - (dirTextMetrics.X + arrowLength)) / 3#
   If theLinePointsLeft Then
      topCellInsertionPoint.X = topCellInsertionPoint.X - lineDistance + topSpacing
   Else
      topCellInsertionPoint.X = topCellInsertionPoint.X + topSpacing
   End If
'MOVE DIRECTION TEXT INTO POSITION
   Set newDirTextElement = CreateTextElement1(directionTextElement, directionTextElement.text, topCellInsertionPoint, Matrix3dIdentity)

'CREATE THE ARROW
   arrowInPt = topCellInsertionPoint
   arrowInPt.X = arrowInPt.X + dirTextMetrics.X + topSpacing
   Set ArrowCell = MyCreateArrowCell(arrowInPt, charSize, theLinePointsLeft, directionTextElement)

'CREATE THE TOP OF LINE CELL
   Dim topCellArray() As Element
   ReDim topCellArray(2)
   Set topCellArray(0) = newDirTextElement
   Set topCellArray(1) = ArrowCell
   If theLinePointsLeft Then
      rotateToAzim = -Radians(lineSAz - 90#)
   Else
      rotateToAzim = -Radians(lineSAz - 270#)
   End If
   Set AboveLineCell = CreateCellElement1(vbNullString, topCellArray, topCellInsertionPoint)
   AboveLineCell.RotateAboutZ ThePT, rotateToAzim
   
'ADD THE CELL TO THE FILE
   ActiveModelReference.AddElement AboveLineCell
   AboveLineCell.Redraw

'DO THE TEXT BELOW THE LINE
   Dim disInsertPoint As Point3d
   disInsertPoint = ThePT
   disInsertPoint.Y = disInsertPoint.Y - TextOffset
   Dim ptToPcInsPt As Point3d
   ptToPcInsPt = disInsertPoint

'BOTH TEXT FIT ON LINE
   If (ptToPCTextMetrics.X + disTextMetrics.X + charSize * 3#) < lineDistance Then
      Dim disSpacing As Double
      disSpacing = (lineDistance - (ptToPCTextMetrics.X + disTextMetrics.X)) / 3#
      Dim ptToPcSpacing As Double
      ptToPcSpacing = disSpacing + disTextMetrics.X + disSpacing
'BOTH DO NOT FIT, STACK THEM
   Else
      disSpacing = (lineDistance - disTextMetrics.X) / 2#
      ptToPcSpacing = (lineDistance - ptToPCTextMetrics.X) / 2#
      ptToPcInsPt.Y = ptToPcInsPt.Y - charSize - lineSpace
   End If

'CALCULATE THE INSERTION POINTS
   If theLinePointsLeft Then
      disInsertPoint.X = disInsertPoint.X - lineDistance + disSpacing
      ptToPcInsPt.X = ptToPcInsPt.X - lineDistance + ptToPcSpacing
   Else
      disInsertPoint.X = disInsertPoint.X + disSpacing
      ptToPcInsPt.X = ptToPcInsPt.X + ptToPcSpacing
   End If

'MOVE THE TEXT
   distanceTextElement.origin = disInsertPoint
   distanceTextElement.RotateAboutZ ThePT, rotateToAzim
   ptToPcTextElement.origin = ptToPcInsPt
   ptToPcTextElement.RotateAboutZ ThePT, rotateToAzim

'ADD THE TEXT TO THE FILE
   ActiveModelReference.AddElement distanceTextElement
   distanceTextElement.Redraw
   If includePTtoPCCheckBox.value Then
      ActiveModelReference.AddElement ptToPcTextElement
      ptToPcTextElement.Redraw
   End If
End Sub



Private Sub DrawLineAndStuff(point As Point3d, ByVal charSize As Double)
'CREATE TEMPLATES
   Dim baselineTemplate As LineElement
   Set baselineTemplate = CreateBaselineTemplate()
   Dim symbolsTemplate As LineElement
   Set symbolsTemplate = CreateSymbolTemplate()
   Dim OtherTextTemplate As TextElement
   Set OtherTextTemplate = CreateBaseTextTemplate()

'DRAW THE LINE
'CREATE THE LINE ELEMENT
   Dim baselineSegment As LineElement
   Dim lineAzimuth As Double
   Set baselineSegment = CreateLinePart(point, baselineTemplate, lineAzimuth)
   
'SAVE MID POINT COORDINATE
   anchorPointGlobal = CalcMidPoint(baselineSegment.startPoint, baselineSegment.endPoint)
   
'ADD IT TO THE FILE
   ActiveModelReference.AddElement baselineSegment
   Dim BeginStationString As String
   
'TAG IT WITH THE BEGINNING STATION
   TagMyElement baselineSegment, TAG_NAME_BEGIN_STATION, LinePTStaTextBox.text
   
'TAG IT WITH THE LENGTH
   TagMyElement baselineSegment, TAG_NAME_LENGTH, FormatNumber(baselineSegment.length, LINEAR_PRECISION_BASELINE)
   baselineSegment.Rewrite
         

'DRAW THE PC STATION LABEL
   If LabelPCStationCheckBox.value Then
'CREATE THE STRING FOR THE P.C. STATION LABEL
      If LinePCStationTextBox.enabled Then
      Dim pcStationString As String
         pcStationString = LinePCStationTextBox.text
      Else
         pcStationString = PCStaCalcedLabel.Caption
      End If
      pcStationString = TEXT_PREFIX_STATION & pcStationString
      If PCOtherOption.value Then
         pcStationString = PCOtherTextBox.text & pcStationString
      Else
         pcStationString = TEXT_PREFIX_PC & pcStationString
      End If
   
'CREATE THE TEXT ELEMENT FOR THE P.C. STATION
      Dim pCTextElement As TextElement
      Set pCTextElement = CreateTextElement1(OtherTextTemplate, pcStationString, baselineSegment.endPoint, Matrix3dIdentity)
   
'GET THE LENGTH OF THE TEXT ELEMENT
      Dim pCTextMetrics As Point2d
      pCTextElement.GetTotalTextSize pCTextMetrics.X, pCTextMetrics.Y
      
'DRAW IT ON THE LEFT OR RIGHT OF THE BASELINE, CALCULATE THE RADIAL AZIMUTH FOR SUBROUTINE TO DRAW IT
      If LabelPCLeftOption.value Then
         Dim AzToCC As Double
         AzToCC = lineAzimuth + 270#
      Else
         AzToCC = lineAzimuth + 90#
      End If
      
'DRAW IT
      TextTheRadial baselineSegment.endPoint, lineAzimuth, AzToCC, charSize, pCTextElement, False
      
'DRAW EXTENSION LINE
      Dim extensionBeginPC As Point3d
      extensionBeginPC = baselineSegment.endPoint 'might want to change this later
      Dim extensionEndPC As Point3d
      extensionEndPC = CoordFwdSAz(baselineSegment.endPoint, AzToCC, pCTextMetrics.X + charSize + charSize)
      Dim extensionLinePC As LineElement
      Set extensionLinePC = CreateLineElement2(OtherTextTemplate, extensionBeginPC, extensionEndPC)
      
'ADD EXTENSION LINE TO FILE
      ActiveModelReference.AddElement extensionLinePC
      extensionLinePC.Redraw
   End If

'DRAW THE PT STATION LABEL
   If LabelPTStationCheckBox.value Then
'CREATE THE STRING FOR THE P.T. STATION LABEL
      Dim ptStationString As String
      ptStationString = TEXT_PREFIX_STATION & LinePTStaTextBox.text
      If LabelPTOtherOption.value Then
         ptStationString = LabelPTOtherTextBox.text & ptStationString
      Else
         ptStationString = TEXT_PREFIX_PT & ptStationString
      End If
      
'CREATE THE TEXT ELEMENT FOR THE P.T. STATION
      Dim PTTextElement As TextElement
      Set PTTextElement = CreateTextElement1(OtherTextTemplate, ptStationString, baselineSegment.startPoint, Matrix3dIdentity)
      
'GET THE LENGTH OF THE TEXT ELEMENT
      Dim PTTextMetrics As Point2d
      PTTextElement.GetTotalTextSize PTTextMetrics.X, PTTextMetrics.Y
      
'DRAW IT ON THE LEFT OR RIGHT OF THE BASELINE, CALCULATE THE RADIAL AZIMUTH FOR SUBROUTINE TO DRAW IT
      If LabelPTLeftOption.value Then
         AzToCC = lineAzimuth + 270#
      Else
         AzToCC = lineAzimuth + 90#
      End If
      
'DRAW IT
      TextTheRadial baselineSegment.startPoint, lineAzimuth, AzToCC, charSize, PTTextElement, True
      
'DRAW EXTENSION LINE
      Dim extensionBeginPT As Point3d
      extensionBeginPT = baselineSegment.startPoint
      Dim extensionEndPT As Point3d
      extensionEndPT = CoordFwdSAz(baselineSegment.startPoint, AzToCC, PTTextMetrics.X + charSize + charSize)
      Dim extensionLinePT As LineElement
      Set extensionLinePT = CreateLineElement2(OtherTextTemplate, extensionBeginPT, extensionEndPT)
      
'ADD EXTENSION LINE TO FILE
      ActiveModelReference.AddElement extensionLinePT
      extensionLinePT.Redraw
   End If

'DRAW THE SYMBOLS ON PC AND PT
   Dim symbolRadius As Double
   symbolRadius = charSize / 3#
   
'DRAW CIRCLE ON THE PC
   If DrawSymbolPCCheckBox.value Then
      Dim PCsymbol As EllipseElement
      Set PCsymbol = CreateEllipseElement2(symbolsTemplate, baselineSegment.endPoint, symbolRadius, symbolRadius, Matrix3dIdentity)
      
'ADD IT TO THE FILE
      ActiveModelReference.AddElement PCsymbol
      PCsymbol.Redraw
   End If
   
'DRAW CIRCLE ON THE PT
   If DrawSymbolPTCheckBox = True Then
      Dim PTsymbol As EllipseElement
      Set PTsymbol = CreateEllipseElement2(symbolsTemplate, baselineSegment.startPoint, symbolRadius, symbolRadius, Matrix3dIdentity)
      
'ADD IT TO THE FILE
      ActiveModelReference.AddElement PTsymbol
      PTsymbol.Redraw
   End If
End Sub



Private Sub TextTheRadial(PCorPT As Point3d, _
                          TangentAz As Double, _
                          AzToCC As Double, _
                          charSize As Double, _
                          theText As TextElement, _
                          isFwd As Boolean)
'DRAW TEXT ON THE RADIAL LINE, LEFT OR RIGHT, FORWARD OR BACK

'CALCULATE METRICS
   Dim lineSpace As Double
   lineSpace = charSize / 3#
   Dim textWidth As Double
   Dim textHeight As Double
   theText.GetTotalTextSize textWidth, textHeight

'HAVE TEXT ALWAYS TOP GOING UPSTATION
'CALCULATE CHANGE FORWARD OR BACK
   Dim dY As Double
   dY = charSize / 2# + lineSpace
   If Not isFwd Then
      dY = -dY
   End If
   
'SEE IF RADIAL ON LEFT OR RIGHT OF BASELINE
'BASED ON TEXT ELEMENT LEFT/CENTER JUSTIIFIED
   If To360(TangentAz, AzToCC) < 180# Then
'TEXT GOES ON LEFT SIDE OF LINE
      Dim dX As Double
      dX = -charSize - textWidth
   Else
'TEXT GOES ON RIGHT SIDE
      dX = charSize
   End If

   Dim InsertionPoint As Point3d
   InsertionPoint.X = PCorPT.X + dX
   InsertionPoint.Y = PCorPT.Y + dY
   InsertionPoint.z = PCorPT.z

'CREATE NEW TEXT AT INSERTION POINT INSTEAD OF MOVING ORIGINAL TEXT ELEMENT
   Dim newTextElement As TextElement
   Set newTextElement = CreateTextElement1(theText, theText.text, InsertionPoint, Matrix3dIdentity)

'FIGURE OUT THE ROTATION
   Dim rotationDegrees As Double
   rotationDegrees = TangentAz - 180#

'ROTATE IT INTO PLACE
   newTextElement.RotateAboutZ PCorPT, -Radians(rotationDegrees)

'ADD IT TO THE FILE
   ActiveModelReference.AddElement newTextElement
   newTextElement.Redraw
End Sub



Private Function CreateLinePart(startPoint As Point3d, template As Element, ByRef sAzOfLine As Double) As LineElement
'CREATE THE LINE PART OF BASELINE
   Dim origPrec As Long
   Dim dirType As Integer
   Dim quad As Integer
   If Not DirStringToSAz(LineDirectionTextBox.text, sAzOfLine, origPrec, dirType, quad) Then
'SHOULD NEVER GET HERE, CREATE ERROR IF IT DOES
      Err.Raise ERROR_NUM_522
   End If
   If LineDistanceTextBox.enabled Then
      Dim DistText As String
      DistText = LineDistanceTextBox.text
   Else
      DistText = DistCalcedLabel.Caption
   End If
   Dim distance As Double
   distance = CDbl(DistText)
   Dim endPoint As Point3d
   endPoint = CoordFwdSAz(startPoint, sAzOfLine, distance)
   Set CreateLinePart = CreateLineElement2(template, startPoint, endPoint)
End Function


'*************************************************************************************************************
'**************************************************TEMPLATES**************************************************
Private Function CreateBaselineTemplate() As LineElement
   Set CreateBaselineTemplate = CreateLineTemplate(SECTION_CURVE_SOLVER, _
                                                   BaselineLevelComboBox, _
                                                   KEY_BASELINE_LEVEL, _
                                                   BaselineWeightComboBox, _
                                                   BaselineColorComboBox, _
                                                   BaselineStyleComboBox, _
                                                   KEY_BASELINE_STYLE)
End Function

Private Function CreateSymbolTemplate() As LineElement
   Set CreateSymbolTemplate = CreateLineTemplate(SECTION_CURVE_SOLVER, _
                                                 SymbolsLevelComboBox, _
                                                 KEY_SYMBOL_LEVEL, _
                                                 SymbolsWeightComboBox, _
                                                 SymbolsColorComboBox, _
                                                 SymbolsStyleComboBox, _
                                                 KEY_SYMBOL_STYLE)
End Function

Private Function CreateBaseTextTemplate() As TextElement
   Set CreateBaseTextTemplate = CreateTextTemplate(SECTION_CURVE_SOLVER, _
                                                   OtherTextFontComboBox, _
                                                   KEY_TEXT_FONT, _
                                                   OtherTextLevelComboBox, _
                                                   KEY_TEXT_LEVEL, _
                                                   OtherTextWeightComboBox, _
                                                   OtherTextColorComboBox, _
                                                   OtherTextStyleComboBox, _
                                                   KEY_TEXT_STYLE)
   
End Function

Private Function CreateRadialLineTemplate() As LineElement
   Set CreateRadialLineTemplate = CreateLineTemplate(SECTION_CURVE_SOLVER, _
                                                     RadialLinesLevelComboBox, _
                                                     KEY_RADIALS_LEVEL, _
                                                     RadialLinesWeightComboBox, _
                                                     RadialLinesColorComboBox, _
                                                     RadialLinesStyleComboBox, _
                                                     KEY_RADIALS_STYLE)
End Function



Private Function CreateCurveDataTextTemplate() As TextElement
   Set CreateCurveDataTextTemplate = CreateTextTemplate(SECTION_CURVE_SOLVER, _
                                                        CurveDataFontComboBox, _
                                                        KEY_CURVE_DATA_FONT, _
                                                        CurveDataLevelComboBox, _
                                                        KEY_CURVE_DATA_LEVEL, _
                                                        CurveDataWeightComboBox, _
                                                        CurveDataColorComboBox, _
                                                        CurveDataStyleComboBox, _
                                                        KEY_CURVE_DATA_STYLE)
   
End Function

Attribute VB_Name = "FrmDropDiagram"
Attribute VB_Base = "0{554AF0DF-6357-49EF-98BC-1E8092C4C8F2}{4C23B276-6CC5-4490-A3B9-A8D04E205CD2}"
Attribute VB_GlobalNameSpace = False
Attribute VB_Creatable = False
Attribute VB_PredeclaredId = True
Attribute VB_Exposed = False
Attribute VB_TemplateDerived = False
Attribute VB_Customizable = False
















'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit

Private recordPoint                    As Point3d
Private groundPoint                    As Point3d

Private textBoxNumber                  As Integer

Private Const TEXTBOX_DESC1            As Integer = 1
Private Const TEXTBOX_DESC2            As Integer = 2
Private Const TEXTBOX_DIRECTION        As Integer = 3



'*************************************************************************************************************
'**********************************INTERFACE FOR PICKING TEXT ROUTINE*****************************************
Public Sub EnterText(ByVal Entry As String)
   Select Case textBoxNumber
      Case TEXTBOX_DESC1
         DescriptionTextBox.text = Left(Entry, MAX_LEN_POINT_DESC)
         DescriptionTextBox_AfterUpdate
      Case TEXTBOX_DESC2
         Desc2TextBox.text = Left(Entry, MAX_LEN_POINT_DESC)
         Desc2TextBox_AfterUpdate
      Case TEXTBOX_DIRECTION
         AzimuthTextBox.text = Entry
         AzimuthTextBox_AfterUpdate
   End Select
End Sub



Private Sub PickSubToo(boxNumber As Integer)
   textBoxNumber = boxNumber
   Dim pickTool As New DropDiagramILocateText
   Set pickTool.hostForm = Me
   CommandState.StartLocate pickTool
   Me.Hide
End Sub



'*************************************************************************************************************
'**************************************INTERFACE WITH DRAWING ROUTINES****************************************
Public Function RecPoint() As Point3d
   RecPoint = recordPoint
End Function



Public Function grndPoint() As Point3d
   grndPoint = groundPoint
End Function



Public Function GetTextTemp() As TextElement
   Set GetTextTemp = CreateTextTemplate(SECTION_DROP_DIAGRAM, _
                                        FontComboBox, _
                                        KEY_FONT, _
                                        LevelComboBox, _
                                        KEY_LEVEL, _
                                        WeightComboBox, _
                                        ColorComboBox, _
                                        StyleComboBox, _
                                        KEY_STYLE, , _
                                        msdTextJustificationLeftCenter)
End Function



Public Function GetLineTemp() As LineElement
'TO INTERFACE WITH LINE PLACING ROUTINE
   Set GetLineTemp = CreateLineTemplate(SECTION_DROP_DIAGRAM, _
                                        LevelComboBox2, _
                                        KEY_LEVEL2, _
                                        WeightComboBox, _
                                        ColorComboBox, _
                                        StyleComboBox, _
                                        KEY_STYLE)
End Function
'*************************************************************************************************************
'*******************************************UPDATE DISPLAY****************************************************
Private Sub FillRecTextBoxes()
   RecordEastLabel.Caption = DoubleToEastingString(recordPoint.X, 2)
   RecordNorthLabel.Caption = DoubleToNorthingString(recordPoint.Y, 2)
End Sub



Private Sub FillGrndTextBoxes()
   GrndEastLabel.Caption = DoubleToEastingString(groundPoint.X, 2)
   GrndNorthLabel.Caption = DoubleToNorthingString(groundPoint.Y, 2)
End Sub



'*************************************************************************************************************
'******************************************SAVING THE POINTS**************************************************
Private Sub SaveRecordPoint()
   SaveSetting APP_NAME, SECTION_DROP_DIAGRAM, KEY_REC_EAST, FormatNumber(recordPoint.X, MAX_PRECISION_COORDINATE)
   SaveSetting APP_NAME, SECTION_DROP_DIAGRAM, KEY_REC_NORTH, FormatNumber(recordPoint.Y, MAX_PRECISION_COORDINATE)
   SaveSetting APP_NAME, SECTION_DROP_DIAGRAM, KEY_REC_ELEVATION, FormatNumber(recordPoint.z, MAX_PRECISION_COORDINATE)
End Sub



Private Sub SaveGroundPoint()
   SaveSetting APP_NAME, SECTION_DROP_DIAGRAM, KEY_GRND_EAST, FormatNumber(groundPoint.X, MAX_PRECISION_COORDINATE)
   SaveSetting APP_NAME, SECTION_DROP_DIAGRAM, KEY_GRND_NORTH, FormatNumber(groundPoint.Y, MAX_PRECISION_COORDINATE)
   SaveSetting APP_NAME, SECTION_DROP_DIAGRAM, KEY_GRND_ELEVATION, FormatNumber(groundPoint.z, MAX_PRECISION_COORDINATE)
End Sub



'*************************************************************************************************************
'*************************************************MAIN TAB****************************************************
'DIRECTION TEXT PICK BUTTON
Private Sub PickDirButton_Click()
   PickSubToo TEXTBOX_DIRECTION
End Sub



'REFERENCE DIRECTION TEXTBOX
Private Sub AzimuthTextBox_AfterUpdate()
   SaveDirEntry AzimuthTextBox, SECTION_DROP_DIAGRAM, KEY_REF_AZ, STYLE_ANGLE_SPACE Or STYLE_ANGLE_LEAD, 4
End Sub

Private Sub AzimuthTextBox_Enter()
   SelectAllText AzimuthTextBox
End Sub



'+180 BUTTON
Private Sub Plus180Button_Click()
   Plus180 AzimuthTextBox
   AzimuthTextBox_AfterUpdate
End Sub



'DESCRIPTION 1 CHECKBOX
Private Sub DescriptionCheckBox_AfterUpdate()
   SaveCheckBoxSetting DescriptionCheckBox, SECTION_DROP_DIAGRAM, KEY_CHECKBOX1
   ControlStates
End Sub



'DESCRIPTION1 TEXTBOX
Private Sub DescriptionTextBox_AfterUpdate()
   SaveSetting APP_NAME, SECTION_DROP_DIAGRAM, KEY_DESCRIPTION, DescriptionTextBox.text
End Sub

Private Sub DescriptionTextBox_Enter()
   SelectAllText DescriptionTextBox
End Sub



'DESCRIPTION1 PICK BUTTON
Private Sub PickDescriptionButton_Click()
   PickSubToo TEXTBOX_DESC1
End Sub



'DESCRIPTION2 CHECKBOX
Private Sub Desc2CheckBox_Click()
   SaveCheckBoxSetting Desc2CheckBox, SECTION_DROP_DIAGRAM, KEY_OPTION_DESC2
   ControlStates
End Sub



'DESCRIPTION2 TEXTBOX
Private Sub Desc2TextBox_AfterUpdate()
   SaveSetting APP_NAME, SECTION_DROP_DIAGRAM, KEY_DESCRIPTION2, Desc2TextBox.text
End Sub

Private Sub Desc2TextBox_Enter()
   SelectAllText Desc2TextBox
End Sub



'DESCRIPTION2 PICK BUTTON
Private Sub PickDesc2Button_Click()
   PickSubToo TEXTBOX_DESC2
End Sub



'RECORD COORDINATE PICK BUTTON
Private Sub PickRecButton_Click()
   FrmDropDiagram.Hide

   Dim ThePickedPoint As Point3d
   If PickSub(COMMAND_NAME_DROP_DIAGRAM, "Pick Record Point.", ThePickedPoint) Then
      recordPoint = ThePickedPoint
      SaveRecordPoint
      FillRecTextBoxes
   End If

   FrmDropDiagram.Show
   GrndPickButton.SetFocus
End Sub



'GROUND COORDINATE PICK BUTTON
Private Sub GrndPickButton_Click()
   FrmDropDiagram.Hide

   Dim ThePickedPoint As Point3d
   If PickSub(COMMAND_NAME_DROP_DIAGRAM, "Pick Ground Point.", ThePickedPoint) Then
      groundPoint = ThePickedPoint
      SaveGroundPoint
      FillGrndTextBoxes
   End If

   FrmDropDiagram.Show
   DrawItButton.SetFocus
End Sub



'REVISE DIAGRAM BUTTON
Private Sub UpdateButton_Click()
   CommandState.StartLocate New DropDiagramLocateUpdate
End Sub



'DRAW IT BUTTON
Private Sub DrawItButton_Click()
    CommandState.StartPrimitive New DropDiagramPrimitive
End Sub



'*************************************************************************************************************
'***********************************************SETTINGS TAB**************************************************
'COLOR COMBOBOX
Private Sub ColorComboBox_AfterUpdate()
   ColorBoxOnUpdate ColorComboBox, SECTION_DROP_DIAGRAM, KEY_COLOR
End Sub

'COLOR PICKER
Private Sub ChooseColorButton_Click()
   Dim MyColor As String
   If ChooseMyTableColor(MyColor) Then
      ColorComboBox.text = MyColor
      ColorComboBox_AfterUpdate
   End If
End Sub



'LEVEL COMBOBOX
Private Sub LevelComboBox_AfterUpdate()
   If Not LevelBoxOnUpdate(LevelComboBox, SECTION_DROP_DIAGRAM, KEY_LEVEL) Then
      PopulateLevelBox LevelComboBox, SECTION_DROP_DIAGRAM, KEY_LEVEL
      Beep
   End If
End Sub

'STYLE COMBOBOX
Private Sub StyleComboBox_AfterUpdate()
   If Not LineStyleBoxOnUpdate(StyleComboBox, SECTION_DROP_DIAGRAM, KEY_STYLE) Then
      PopulateLinestyleBox StyleComboBox, SECTION_DROP_DIAGRAM, KEY_STYLE
      Beep
   End If
End Sub

'WEIGHT COMBOBOX
Private Sub WeightComboBox_AfterUpdate()
   WeightBoxOnUpdate WeightComboBox, SECTION_DROP_DIAGRAM, KEY_WEIGHT
End Sub

'FONT COMBOBOX
Private Sub FontComboBox_AfterUpdate()
   If Not FontBoxOnUpdate(FontComboBox, SECTION_DROP_DIAGRAM, KEY_FONT) Then
      PopulateFontBox FontComboBox, SECTION_DROP_DIAGRAM, KEY_FONT
      Beep
   End If
End Sub



'USE LEADER CHECKBOX
Private Sub LeaderCheckBox_Click()
   SaveCheckBoxSetting LeaderCheckBox, SECTION_DROP_DIAGRAM, KEY_OPTION_LEADER
   LeaderLabel.enabled = LeaderCheckBox.value
   RadialsLevelLabel.enabled = LeaderCheckBox.value
   LevelComboBox2.enabled = LeaderCheckBox.value
End Sub



'LEADER LINE LEVEL COMBOBOX
Private Sub LevelComboBox2_AfterUpdate()
   If Not LevelBoxOnUpdate(LevelComboBox2, SECTION_DROP_DIAGRAM, KEY_LEVEL2) Then
      PopulateLevelBox LevelComboBox2, SECTION_DROP_DIAGRAM, KEY_LEVEL2
      Beep
   End If
End Sub



'SET REVISED COLOR CHECKBOX
Private Sub ReviseColorCheckBox_Click()
   SaveCheckBoxSetting ReviseColorCheckBox, SECTION_DROP_DIAGRAM, KEY_SET_REVISION_COLOR
   ControlStates
End Sub



'REVISION COLOR COMBOBOX
Private Sub RevisonColorComboBox_AfterUpdate()
   ColorBoxOnUpdate RevisonColorComboBox, SECTION_DROP_DIAGRAM, KEY_REVISION_COLOR
End Sub



'COLOR CHOOSER BUTTON
Private Sub ColorChooserButton_Click()
   Dim MyColor As String
   If ChooseMyTableColor(MyColor) Then
      RevisonColorComboBox.text = MyColor
      RevisonColorComboBox_AfterUpdate
   End If
End Sub



'SETTINGS BUTTON
Private Sub SettingsButton_Click()
   Setting
End Sub



'*************************************************************************************************************
'**********************************************CONTROL STATES*************************************************
Private Sub ControlStates()
   RevisonColorComboBox.enabled = ReviseColorCheckBox.value
   RevisonColorComboBox.BackColor = BackOLE_COLOR(ReviseColorCheckBox.value)
   RevisionColorLabel.enabled = ReviseColorCheckBox.value
   ColorChooserButton.enabled = ReviseColorCheckBox.value
   DescriptionTextBox.enabled = DescriptionCheckBox.value
   PickDescriptionButton.enabled = DescriptionCheckBox.value
   DescriptionTextBox.BackColor = BackOLE_COLOR(DescriptionCheckBox.value)
   Desc2TextBox.enabled = Desc2CheckBox.value
   PickDesc2Button.enabled = Desc2CheckBox.value
   Desc2TextBox.BackColor = BackOLE_COLOR(Desc2CheckBox.value)
End Sub




'*************************************************************************************************************
'**********************************************USERFORM EVENTS************************************************
Private Sub UserForm_Initialize()
   Dim IsChecked As String
      
   AzimuthTextBox.MaxLength = MAX_LEN_DIR_STRING
   AzimuthTextBox.text = GetSetting(APP_NAME, SECTION_DROP_DIAGRAM, KEY_REF_AZ, "0")
   AzimuthTextBox_AfterUpdate
   
   recordPoint.X = CDbl(GetSetting(APP_NAME, SECTION_DROP_DIAGRAM, KEY_REC_EAST, "0"))
   recordPoint.Y = CDbl(GetSetting(APP_NAME, SECTION_DROP_DIAGRAM, KEY_REC_NORTH, "0"))
   recordPoint.z = CDbl(GetSetting(APP_NAME, SECTION_DROP_DIAGRAM, KEY_REC_ELEVATION, "0"))
   FillRecTextBoxes
   
   groundPoint.X = CDbl(GetSetting(APP_NAME, SECTION_DROP_DIAGRAM, KEY_GRND_EAST, "0"))
   groundPoint.Y = CDbl(GetSetting(APP_NAME, SECTION_DROP_DIAGRAM, KEY_GRND_NORTH, "0"))
   groundPoint.z = CDbl(GetSetting(APP_NAME, SECTION_DROP_DIAGRAM, KEY_GRND_ELEVATION, "0"))
   FillGrndTextBoxes

'INITIALIZE DESCRIPTION TEXTBOXES
   DescriptionTextBox.MaxLength = MAX_LEN_POINT_DESC
   DescriptionTextBox.text = GetSetting(APP_NAME, SECTION_DROP_DIAGRAM, KEY_DESCRIPTION, "227")
   Desc2TextBox.MaxLength = MAX_LEN_POINT_DESC
   Desc2TextBox.text = GetSetting(APP_NAME, SECTION_DROP_DIAGRAM, KEY_DESCRIPTION2, "Iron Pin")

'INITIALIZE DESCRIPTION CHECKBOXES
   InitializeCheckBox DescriptionCheckBox, SECTION_DROP_DIAGRAM, KEY_CHECKBOX1
   InitializeCheckBox Desc2CheckBox, SECTION_DROP_DIAGRAM, KEY_OPTION_DESC2

'INITIALIZE LEADER LINE CHECKBOX
   InitializeCheckBox LeaderCheckBox, SECTION_DROP_DIAGRAM, KEY_OPTION_LEADER

'POPULATE REVISION COLOR COMBOBOX
   PopulateColorBox RevisonColorComboBox, SECTION_DROP_DIAGRAM, KEY_REVISION_COLOR
   
'INITIALIZE REVISION COLOR CHECKBOX
   InitializeCheckBox ReviseColorCheckBox, SECTION_DROP_DIAGRAM, KEY_SET_REVISION_COLOR

'LEVEL COMBOBOX
   PopulateLevelBox LevelComboBox, SECTION_DROP_DIAGRAM, KEY_LEVEL
   
'COLOR COMBOBOX
   PopulateColorBox ColorComboBox, SECTION_DROP_DIAGRAM, KEY_COLOR
   
'STYLE COMBOBOX
   PopulateLinestyleBox StyleComboBox, SECTION_DROP_DIAGRAM, KEY_STYLE
   
'WEIGHT COMBOBOX
   PopulateWeightBox WeightComboBox, SECTION_DROP_DIAGRAM, KEY_WEIGHT
   
'FONT COMBOBOX
   PopulateFontBox FontComboBox, SECTION_DROP_DIAGRAM, KEY_FONT

'LEADER LINELEVEL COMBOBOX
   PopulateLevelBox LevelComboBox2, SECTION_DROP_DIAGRAM, KEY_LEVEL2

'UPDATE STATES
   ControlStates
   
'MOVE INTO LAST POSITION
   If GetSetting(APP_NAME, SECTION_DROP_DIAGRAM, KEY_START_TOP, "") = "" Then
      Me.StartUpPosition = 1
   Else
      Me.StartUpPosition = 0
      Me.Top = CDbl(GetSetting(APP_NAME, SECTION_DROP_DIAGRAM, KEY_START_TOP, WINDOW_DEFAULT_TOP))
      Me.Left = CDbl(GetSetting(APP_NAME, SECTION_DROP_DIAGRAM, KEY_START_LEFT, WINDOW_DEFAULT_LEFT))
   End If

'SET CAPTION
   Me.Caption = COMMAND_NAME_DROP_DIAGRAM

'START ON MAIN PAGE
   Me.MultiPage1.value = 0
End Sub




Private Sub UserForm_QueryClose(Cancel As Integer, CloseMode As Integer)
'SAVE USERFORM POSITION
   SaveSetting APP_NAME, SECTION_DROP_DIAGRAM, KEY_START_TOP, FormatNumber(Me.Top, 2)
   SaveSetting APP_NAME, SECTION_DROP_DIAGRAM, KEY_START_LEFT, FormatNumber(Me.Left, 2)
End Sub

Attribute VB_Name = "FrmDupFinder"
Attribute VB_Base = "0{352C4927-5A3F-4904-A3E8-6D5A7BDD8482}{BBA83BC6-45E3-4C1E-BAC0-75C84450D5BB}"
Attribute VB_GlobalNameSpace = False
Attribute VB_Creatable = False
Attribute VB_PredeclaredId = True
Attribute VB_Exposed = False
Attribute VB_TemplateDerived = False
Attribute VB_Customizable = False



















'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.



'GENERAL NOTES:
'PROGRAM ASSUMES MASTER UNIT IS FOOT OR SURVEY FOOT, SOME KIND OF FOOT

Option Explicit

Private Const BACK_HIGHLIGHT = &H8000000D
Private Const BUTTON_TEXT = &H80000012
Private Const NUM_OF_ROWS_MINUS_1 As Long = 7
Private Const NUM_OF_ROWS         As Long = 8


Dim tecNormal As TransientElementContainer         'CONTAINER FOR TEMPORARY UNHIGHLIGHTED GRAPHICS
Dim tecHilite As TransientElementContainer         'CONTAINER FOR TEMPORARY HIGHLIGHTED GRAPHICS
Dim sqHilite  As TransientElementContainer         'CONTAINER FOR TEMPORARY HIGHLIGHTED SQUARES GRAPHICS


Dim points()        As Point3d
Dim selIndex()      As Boolean
Dim dispText()      As String
Dim dispTextD()     As String
Dim markOverlap()   As Boolean


Private openCloseHandler    As ClsOpenCloseDupFind 'MAKE SURE DOESN'T CRASH ON FILE CLOSE
Private viewChangeHandler   As ClsViewChange       'REDRAW SQUARES


Private Function LoadCoordinateFile(filename As String, ByRef CoordinateListBox As ListBox) As Boolean
'LOAD LOT FILE INTO USERFORM, RETURNS TRUE IF SUCCESSFUL

'INITIALIZE RETURN VALUE
   LoadCoordinateFile = False

'JUMP ON ERROR
   On Error GoTo errhnd

'OPEN FILE
   Dim FFILE As Long
   FFILE = FreeFile
   Open filename For Input As #FFILE

'READ FILE ONE LINE AT A TIME
   Dim LineNum As Long
   LineNum = 0
   Dim plotZ As Double
   plotZ = getZ()
   Dim OpenFileErrors As Long
   OpenFileErrors = 0
   Do While EOF(FFILE) = False
      Dim TextLine As String
      Line Input #FFILE, TextLine
      LineNum = LineNum + 1
      Dim pointName As String
      Dim northing As String
      Dim easting As String
      Dim elevation As String
      Dim description As String
      If ParsePointString(TextLine, pointName, northing, easting, elevation, description) Then
         LoadCoordinateFile = True
         CoordinateListBox.AddItem TextLine
         Dim topIndex As Long
         topIndex = CoordinateListBox.ListCount - 1
'ADD SELECTED INDICATOR
         ReDim Preserve selIndex(topIndex)
         selIndex(topIndex) = False
'ADD DISPLAY TEXT
         ReDim Preserve dispText(topIndex)
         dispText(topIndex) = pointName
         ReDim Preserve dispTextD(topIndex)
         dispTextD(topIndex) = description
'ADD POINT
         ReDim Preserve points(topIndex)
         points(topIndex).X = CDbl(easting)
         points(topIndex).Y = CDbl(northing)
         points(topIndex).z = plotZ
'RESIZE MARKER ARRAY
      Else
         Close #FFILE
         GoTo errhnd
      End If
   Loop
   If CoordinateListBox.ListCount < 1 Then
      GoTo errhnd
   End If

'CLOSE FILE
   Close #FFILE
   
'RESIZE OVERLAP ARRAY
   ReDim markOverlap(topIndex)

'SET SCROLL BAR
   ListScrollBar.Max = topIndex
   ListScrollBar.value = MaxLong(topIndex - NUM_OF_ROWS_MINUS_1, 0)
   ScrollBarState
'JUMP PAST ERROR CODE
   Exit Function

'ERROR HANDLING
errhnd:
   ReDim markOverlap(UBound(points))
   ListScrollBar.Max = UBound(points)
   LoadCoordinateFile = False
   ErrorMess Err.Number
   Err.Clear
End Function



Private Sub ScrollBarState()
   If CoordinateListBox.ListCount > 1 Then
      ListScrollBar.enabled = True
      ListScrollBar.Visible = True
   Else
      ListScrollBar.enabled = False
      ListScrollBar.Visible = False
   End If
End Sub


Private Sub PickButtonState()
   If CoordinateListBox.ListCount > 1 Then
      PickLegButton.enabled = True
   Else
      PickLegButton.enabled = False
   End If
End Sub


Private Sub DispList()
   If CoordinateListBox.ListCount > 1 Then
      ListScrollBar.Visible = True
      DisplayArray ListScrollBar.value
   ElseIf CoordinateListBox.ListCount > 0 Then
      DisplayArray 0
      ListScrollBar.Visible = False
   Else
      clearListDisp
      ListScrollBar.Visible = False
   End If
End Sub


Private Sub DisplayArray(beginIndex As Long)
   If CoordinateListBox.ListCount < 1 Then
      Exit Sub
   End If

   Dim maxIndex As Long
   maxIndex = UBound(dispText)
   Dim nextIndex As Long
   nextIndex = beginIndex
   DispArrySub maxIndex, nextIndex, ListLabel1, ListLabel1D
   DispArrySub maxIndex, nextIndex, ListLabel2, ListLabel2D
   DispArrySub maxIndex, nextIndex, ListLabel3, ListLabel3D
   DispArrySub maxIndex, nextIndex, ListLabel4, ListLabel4D
   DispArrySub maxIndex, nextIndex, ListLabel5, ListLabel5D
   DispArrySub maxIndex, nextIndex, ListLabel6, ListLabel6D
   DispArrySub maxIndex, nextIndex, ListLabel7, ListLabel7D
   DispArrySub maxIndex, nextIndex, ListLabel8, ListLabel8D
End Sub



Private Sub DispArrySub(maxIndex As Long, thisIndex As Long, listLabel As label, listLabelD)
   If thisIndex <= maxIndex Then
      listLabel.Caption = dispText(thisIndex)
      listLabelD.Caption = dispTextD(thisIndex)
      If selIndex(thisIndex) Then
         listLabel.BackColor = BACK_HIGHLIGHT
         listLabel.ForeColor = backgroundWhite
         listLabelD.BackColor = BACK_HIGHLIGHT
         listLabelD.ForeColor = backgroundWhite
      Else
         listLabel.BackColor = backgroundWhite
         listLabel.ForeColor = BUTTON_TEXT
         listLabelD.BackColor = backgroundWhite
         listLabelD.ForeColor = BUTTON_TEXT
      End If
   Else
      listLabel.Caption = ""
      listLabel.BackColor = backgroundWhite
      listLabel.ForeColor = BUTTON_TEXT
      listLabelD.Caption = ""
      listLabelD.BackColor = backgroundWhite
      listLabelD.ForeColor = BUTTON_TEXT
   End If
   thisIndex = thisIndex + 1
End Sub



Private Sub clearListDisp()
   clearSub ListLabel1
   clearSub ListLabel2
   clearSub ListLabel3
   clearSub ListLabel4
   clearSub ListLabel5
   clearSub ListLabel6
   clearSub ListLabel7
   clearSub ListLabel8
   
   clearSub ListLabel1D
   clearSub ListLabel2D
   clearSub ListLabel3D
   clearSub ListLabel4D
   clearSub ListLabel5D
   clearSub ListLabel6D
   clearSub ListLabel7D
   clearSub ListLabel8D
End Sub



Private Sub clearSub(listLabel As label)
   listLabel.Caption = ""
   listLabel.BackColor = backgroundWhite
   listLabel.ForeColor = BUTTON_TEXT
End Sub



Private Sub ToggleSelect(indexOffset As Long)
   If CoordinateListBox.ListCount < 1 Then
      Exit Sub
   End If
   Dim listIndex As Long
   listIndex = ListScrollBar.value + indexOffset
   If listIndex > UBound(selIndex) Then
      Exit Sub
   End If
   If ListScrollBar.enabled Then
      selIndex(listIndex) = Not selIndex(listIndex)
      DisplayArray ListScrollBar.value
   Else
      selIndex(indexOffset) = Not selIndex(indexOffset)
      DisplayArray 0
   End If
   DisplayCircles
End Sub



Private Sub ClearTransients()
'CLEAR OUT TEMPORARY GRAPHICS CONTAINERS
   Set tecNormal = Nothing
   Set tecHilite = Nothing
End Sub



Private Sub ClearSquares()
'CLEAR OUT TEMPORARY GRAPHICS CONTAINERS
   Set sqHilite = Nothing
End Sub



Private Sub CreateHiliteTransientContainer()
'CREATE TEMPORARY GRAPHICS CONTAINER FOR HIGHLIGHTED ELEMENTS
   Dim flags As MsdTransientFlags
   flags = msdTransientFlagsOverlay
   Set tecHilite = CreateTransientElementContainer1(Nothing, flags, msdViewAll, msdDrawingModeHilite)
End Sub



Private Sub CreateNormalTransientContainer()
'CREATE TEMPORARY GRAPHICS CONTAINER FOR REGULARLY DISPLAYED ELEMENTS
   Dim flags As MsdTransientFlags
   flags = msdTransientFlagsOverlay
   Set tecNormal = CreateTransientElementContainer1(Nothing, flags, msdViewAll, msdDrawingModeNormal)
End Sub



Private Sub CreateHiliteSquaresContainer()
'CREATE TEMPORARY GRAPHICS CONTAINER FOR HIGHLIGHTED ELEMENTS
   Dim flags As MsdTransientFlags
   flags = msdTransientFlagsOverlay
   Set sqHilite = CreateTransientElementContainer1(Nothing, flags, msdViewAll, msdDrawingModeHilite)
End Sub



Private Sub ResetMarkers(markerArray() As Boolean)
   Dim lowerIndex As Long
   lowerIndex = LBound(markerArray)
   If lowerIndex = -1 Then
      Exit Sub
   End If
   Dim i As Long
   For i = lowerIndex To UBound(markerArray)
      markerArray(i) = False
   Next i
End Sub



Private Sub TagOverlappers(scanMode As Boolean)
   ResetMarkers markOverlap
   Dim diameter As Double
   diameter = CDbl(DiameterTextBox.text)
   Dim lowerIndex As Long
   lowerIndex = LBound(markOverlap)
   If lowerIndex = -1 Then
      Exit Sub
   End If
   Dim i As Long
   For i = lowerIndex To UBound(markOverlap)
      If scanMode Then
         ScanUpperPart i, diameter
      Else
         SelectUpperPart i, diameter
      End If
   Next i
End Sub



Private Sub SelectUpperPart(indexAt As Long, diameter As Double)
   If selIndex(indexAt) Then
      Exit Sub
   End If
   Dim i As Long
   For i = indexAt + 1 To UBound(selIndex)
      If selIndex(i) Then
         GoTo NextEnd
      End If

      Dim dX As Double
      dX = points(indexAt).X - points(i).X
      If Abs(dX) >= diameter Then
         GoTo NextEnd
      End If
         
      Dim dY As Double
      dY = points(indexAt).Y - points(i).Y
      If Abs(dY) >= diameter Then
         GoTo NextEnd
      End If
         
      Dim dist As Double
      dist = InverseDistance(dY, dX)
      If dist < diameter Then
         selIndex(i) = True
      End If
      
NextEnd:
   Next i
End Sub



Private Sub ScanUpperPart(indexAt As Long, diameter As Double)
   If selIndex(indexAt) Then
      Exit Sub
   End If
   Dim i As Long
   For i = indexAt + 1 To UBound(markOverlap)
      If selIndex(i) Then
         GoTo NextEnd
      End If
      
      If markOverlap(i) Then
         GoTo NextEnd
      End If
      
      Dim dX As Double
      dX = points(indexAt).X - points(i).X
      If Abs(dX) >= diameter Then
         GoTo NextEnd
      End If
         
      Dim dY As Double
      dY = points(indexAt).Y - points(i).Y
      If Abs(dY) >= diameter Then
         GoTo NextEnd
      End If
         
      Dim dist As Double
      dist = InverseDistance(dY, dX)
      If dist < diameter Then
         markOverlap(indexAt) = True
         markOverlap(i) = True
      End If
      
NextEnd:
   Next i
End Sub



Public Sub DisplayCircles()
   ClearTransients
   CreateHiliteTransientContainer
   CreateNormalTransientContainer

   Dim lowerIndex As Long
   lowerIndex = LBound(selIndex)
   If lowerIndex = -1 Then
      Exit Sub
   End If
   
   TagOverlappers True
   
   Dim theRadius As Double
   theRadius = CDbl(DiameterTextBox.text) / 2#

   Dim template As EllipseElement
   Set template = CreateEllipseElement2(Nothing, Point3dFromXYZ(0, 0, 0), theRadius, theRadius, Matrix3dIdentity)
   template.color = GetTetherColor()
   
   Dim i As Long
   For i = lowerIndex To UBound(markOverlap)
      If Not selIndex(i) Then
         Dim theCircle As EllipseElement
         Set theCircle = CreateEllipseElement2(template, points(i), theRadius, theRadius, Matrix3dIdentity)
'CHECK IF IT IS TO BE HIGHLIGHTED OR NOT
         If markOverlap(i) Then
            tecHilite.AppendCopyOfElement theCircle
         Else
            tecNormal.AppendCopyOfElement theCircle
         End If
      End If
   Next i
   DisplaySquares
End Sub



Public Sub DisplaySquares()
   ClearSquares
   CreateHiliteSquaresContainer

   If Not SquaresCheckBox.value Then
      Exit Sub
   End If

   Dim lowerIndex As Long
   lowerIndex = LBound(selIndex)
   If lowerIndex = -1 Then
      Exit Sub
   End If
   
   Dim template As EllipseElement
   Set template = CreateEllipseElement2(Nothing, Point3dFromXYZ(0, 0, 0), 100, 100, Matrix3dIdentity)
   template.color = GetTetherColor()
   
   Dim currentView As view
   Set currentView = GetSelectedView()
   If currentView Is Nothing Then
      Exit Sub
   End If
   Dim rotAngle As Double
   rotAngle = TheViewRotRadians(currentView)
   
   Dim sqSize As Double
   sqSize = calcCharSize(currentView, CDbl(SqSizeComboBox.text) / 2#)

   Dim i As Long
   For i = lowerIndex To UBound(markOverlap)
      If Not selIndex(i) Then
         If markOverlap(i) Then
            Dim theSquare As ShapeElement
            Set theSquare = createSquare(template, points(i), sqSize)
            theSquare.RotateAboutZ points(i), rotAngle
            sqHilite.AppendCopyOfElement theSquare
         End If
      End If
   Next i
End Sub



Private Function createSquare(template As Element, center As Point3d, size As Double) As ShapeElement
   Dim SqPoints(0 To 4) As Point3d
   Dim i As Long
   For i = 0 To 3
      SqPoints(i).z = center.z
   Next i
   SqPoints(0).X = center.X + size
   SqPoints(0).Y = center.Y + size
   SqPoints(4) = SqPoints(0)
   
   SqPoints(1).X = center.X + size
   SqPoints(1).Y = center.Y - size
    
   SqPoints(2).X = center.X - size
   SqPoints(2).Y = center.Y - size
    
   SqPoints(3).X = center.X - size
   SqPoints(3).Y = center.Y + size

   Set createSquare = CreateShapeElement1(template, SqPoints)
End Function



Private Sub WriteCoordinatesToFile(OutputFilename As String)
On Error GoTo errhnd

'write to file here
   Dim FFILE As Long
   FFILE = FreeFile
   Open OutputFilename For Append As #FFILE
      
'FIND THE LIST UPPER BOUND
   Dim TheListUpperBound As Long
   TheListUpperBound = CoordinateListBox.ListCount - 1
   
'CYCLE THROUGH THE LIST FROM THE FIRST ELEMENT TO LAST ELEMENT
   Dim listIndex As Long
   For listIndex = 0 To TheListUpperBound
'IF NOT SELECTED, THEN PRINT TO FILE
      If Not selIndex(listIndex) Then
         Print #FFILE, CoordinateListBox.List(listIndex)
      End If
   Next listIndex
   Close #FFILE
   Exit Sub

errhnd:
   ErrorMess Err.Number
   Err.Clear
End Sub



Private Function getZ() As Double
   getZ = CDbl(ZTextbox.text)
End Function



'*************************************************************************************************************
'********************************************USERFORM CONTROLS************************************************
'LISTLABEL1
Private Sub ListLabel1_Click()
   ToggleSelect 0
End Sub



'LISTLABEL2
Private Sub ListLabel2_Click()
   ToggleSelect 1
End Sub



'LISTLABEL3
Private Sub ListLabel3_Click()
   ToggleSelect 2
End Sub



'LISTLABEL4
Private Sub ListLabel4_Click()
   ToggleSelect 3
End Sub



'LISTLABEL5
Private Sub ListLabel5_Click()
   ToggleSelect 4
End Sub



'LISTLABEL6
Private Sub ListLabel6_Click()
   ToggleSelect 5
End Sub



'LISTLABEL7
Private Sub ListLabel7_Click()
   ToggleSelect 6
End Sub



'LISTLABEL8
Private Sub ListLabel8_Click()
   ToggleSelect 7
End Sub



'LISTLABEL1D
Private Sub ListLabel1D_Click()
   ToggleSelect 0
End Sub



'LISTLABEL2D
Private Sub ListLabel2D_Click()
   ToggleSelect 1
End Sub



'LISTLABEL3D
Private Sub ListLabel3D_Click()
   ToggleSelect 2
End Sub



'LISTLABEL4D
Private Sub ListLabel4D_Click()
   ToggleSelect 3
End Sub



'LISTLABEL5D
Private Sub ListLabel5D_Click()
   ToggleSelect 4
End Sub



'LISTLABEL6D
Private Sub ListLabel6D_Click()
   ToggleSelect 5
End Sub



'LISTLABEL7D
Private Sub ListLabel7D_Click()
   ToggleSelect 6
End Sub



'LISTLABEL8D
Private Sub ListLabel8D_Click()
   ToggleSelect 7
End Sub



'LIST SCROLLBAR
Private Sub ListScrollBar_Change()
   DisplayArray ListScrollBar.value
End Sub



'CANCEL BUTTON
Private Sub CancelButton_Click()
   Unload Me
End Sub



'CLEAR BUTTON
Private Sub ClearButton_Click()
   CoordinateListBox.Clear
   ReDim points(0)
   ReDim markOverlap(0)
   ReDim selIndex(0)
   ReDim dispText(0)
   clearListDisp
   ListScrollBar.Max = 0
   ListScrollBar.value = 0
   PickButtonState
   ClearTransients
   CreateHiliteTransientContainer
   CreateNormalTransientContainer
   ClearSquares
   CreateHiliteSquaresContainer
End Sub



'LOAD BUTTON
Private Sub LoadButton_Click()
   Dim LastFullFileName As String
   LastFullFileName = GetSetting(APP_NAME, SECTION_DUP_FINDER, KEY_FILENAME_COORDINATE, "C:\Input.asc")
   Me.enabled = False
   Dim ToOpenFileName As String
   If OpenCoordFilename(LastFullFileName, ToOpenFileName) Then
      SaveSetting APP_NAME, SECTION_DUP_FINDER, KEY_FILENAME_COORDINATE, ToOpenFileName
      If LoadCoordinateFile(ToOpenFileName, CoordinateListBox) Then
         DispList
         DisplayCircles
      Else
         MsgBox "problem with file"
      End If
   End If
   PickButtonState
   Me.enabled = True
End Sub



'PICK BUTTON
Private Sub PickLegButton_Click()
   If CoordinateListBox.ListCount < 2 Then
      Exit Sub
   End If

'PICK THE POINT
   Me.Hide
   CadInputQueue.SendReset
   Dim myCIQ As CadInputQueue
   Set myCIQ = CadInputQueue
   CommandState.DisableAccuSnap
   ShowCommand COMMAND_NAME_DUP_FINDER
   ShowPrompt "Pick near desired point"
   Dim NoInput As Boolean
   NoInput = True
   Dim pointPicked As Boolean
   pointPicked = False
   Dim myCIM As CadInputMessage
   Set myCIQ = CadInputQueue
   Do While NoInput = True
      Set myCIM = myCIQ.GetInput
      Select Case myCIM.InputType
         Case msdCadInputTypeReset
             ShowPrompt ""
             ShowCommand COMMAND_NAME_DUP_FINDER
             ShowStatus CANCELLED_BY_RESET_STRING
             NoInput = False
          Case msdCadInputTypeDataPoint
             Dim pickedPoint As Point3d
             pickedPoint = myCIM.point
             pointPicked = True
             ClearCommandPromptArea
             NoInput = False
             CadInputQueue.SendReset
      End Select
   Loop
   Me.Show

   If Not pointPicked Then
      Exit Sub
   End If

'SCAN FOR CLOSEST AVAILABLE POINT
   Dim notStarted As Boolean
   notStarted = True
   Dim i As Long
   For i = LBound(points) To UBound(points)
      If Not selIndex(i) Then
         If notStarted Then
            Dim smallestDist As Double
            smallestDist = InverseHD(points(i), pickedPoint)
            Dim indexOfSmallest As Long
            indexOfSmallest = i
            notStarted = False
         Else
            Dim dist As Double
            dist = InverseHD(points(i), pickedPoint)
            If dist < smallestDist Then
               smallestDist = dist
               indexOfSmallest = i
            End If
         End If
      End If
   Next i

'SET LIST VIEW IF FOUND, LEAVE MESSAGE IF EVERYTHING IS SELECTED
   If notStarted Then
      MsgBox "nothing to compare"
   Else
      ListScrollBar.value = indexOfSmallest
   End If
End Sub



'SQUARES CHECKBOX
Private Sub SquaresCheckBox_Click()
   SaveCheckBoxSetting SquaresCheckBox, SECTION_DUP_FINDER, KEY_SQUARE
   DisplaySquares
   SqSizeState
End Sub



'SQUARE SIZE COMBOBOX
Private Sub SqSizeComboBox_Change()
   SaveSetting APP_NAME, SECTION_DUP_FINDER, KEY_SQUARE_SIZE, SqSizeComboBox.text
   DisplaySquares
End Sub

Private Sub SqSizeState()
   If SquaresCheckBox.value Then
      SqSizeLabel.enabled = True
      SqSizeComboBox.enabled = True
   Else
      SqSizeLabel.enabled = False
      SqSizeComboBox.enabled = False
   End If
End Sub



'UNSELECT ALL BUTTON
Private Sub UnselectAllButton_Click()
   ResetMarkers selIndex
   DispList
   DisplayCircles
End Sub



'SAVE UNSEL AS BUTTON
Private Sub SaveUnsButton_Click()
   Me.enabled = False
   Dim LastFullFileName As String
   LastFullFileName = GetSetting(APP_NAME, SECTION_DUP_FINDER, KEY_FILENAME_COORDINATE, "C:\Input.asc")
   Dim ToOpenFileName As String
   If GetNewCoordFilename(LastFullFileName, ToOpenFileName) Then
      CreateNewCoordinateFile (ToOpenFileName)
      WriteCoordinatesToFile (ToOpenFileName)
      MsgBox "Done."
   End If
   Me.enabled = True
End Sub



'SELECT OVERLAPPORS BUTTON
Private Sub OverlaporButton_Click()
   TagOverlappers False
   DispList
   DisplayCircles
   MsgBox "Done."
End Sub



Private Sub UserForm_Terminate()
   If Not viewChangeHandler Is Nothing Then
       RemoveViewUpdateEventsHandler viewChangeHandler
   End If
   Set viewChangeHandler = Nothing
End Sub

'Z TEXTBOX
Private Sub ZTextbox_AfterUpdate()
   SaveElevationEntry ZTextbox, SECTION_DUP_FINDER, KEY_ELEVATION

'UPDATE THE POINTS ARRAY
   Dim lowerIndex As Long
   lowerIndex = LBound(points)
   If lowerIndex < 0 Then
      Exit Sub
   End If
   Dim plotZ As Double
   plotZ = getZ()
   Dim i As Long
   For i = lowerIndex To UBound(points)
      points(i).z = plotZ
   Next i
   DisplayCircles
End Sub



'DIAMETER TEXTBOX
Private Sub DiameterTextBox_AfterUpdate()
   SaveNonnegativeEntry DiameterTextBox, SECTION_DUP_FINDER, KEY_RADIUS, 100#, MAX_PRECISION_RADIUS, False, 1#
   DisplayCircles
End Sub




'PLOT BUTTON
Private Sub PlotButton_Click()
   CommandState.CommandName = COMMAND_NAME_DUP_FINDER
   If ActiveModelReference.IsReadOnly Then
      Exit Sub
   End If
   Dim template As Element
   Set template = GetCircleTemp()
   Dim radius As Double
   radius = CDbl(DiameterTextBox.text) / 2#
   Dim i As Long
   For i = 0 To CoordinateListBox.ListCount - 1
      If Not selIndex(i) Then
         Dim circleCenter As Point3d
         Dim theCircle As EllipseElement
         Set theCircle = CreateEllipseElement2(template, points(i), radius, radius, Matrix3dIdentity)
         ActiveModelReference.AddElement theCircle
         theCircle.Redraw
      End If
   Next i
   MsgBox "Done."
   CommandState.StartDefaultCommand
End Sub



'*************************************************************************************************************
'**********************************************ATTRIBUTES TAB*************************************************
'COLOR COMBOBOX
Private Sub ColorComboBox2_AfterUpdate()
   ColorBoxOnUpdate ColorComboBox2, SECTION_DUP_FINDER, KEY_COLOR2
End Sub

'COLOR PICKER
Private Sub ChooseColorButton2_Click()
   Dim MyColor As String
   If ChooseMyTableColor(MyColor) Then
      ColorComboBox2.text = MyColor
      ColorComboBox2_AfterUpdate
   End If
End Sub

'LEVEL COMBOBOX
Private Sub LevelComboBox2_AfterUpdate()
   If Not LevelBoxOnUpdate(LevelComboBox2, SECTION_DUP_FINDER, KEY_LEVEL2) Then
      PopulateLevelBox LevelComboBox2, SECTION_DUP_FINDER, KEY_LEVEL2
      Beep
   End If
End Sub

'STYLE COMBOBOX
Private Sub StyleComboBox2_AfterUpdate()
   If Not LineStyleBoxOnUpdate(StyleComboBox2, SECTION_DUP_FINDER, KEY_STYLE2) Then
      PopulateLinestyleBox StyleComboBox2, SECTION_DUP_FINDER, KEY_STYLE2
      Beep
   End If
End Sub

'WEIGHT COMBOBOX
Private Sub WeightComboBox2_AfterUpdate()
   WeightBoxOnUpdate WeightComboBox2, SECTION_DUP_FINDER, KEY_WEIGHT2
End Sub



'CIRCLE TEMPLATE
Public Function GetCircleTemp() As LineElement
   Set GetCircleTemp = CreateLineTemplate(SECTION_DUP_FINDER, _
                                          LevelComboBox2, _
                                          KEY_LEVEL2, _
                                          WeightComboBox2, _
                                          ColorComboBox2, _
                                          StyleComboBox2, _
                                          KEY_STYLE2)
End Function



'SETTINGS BUTTON
Private Sub SettingsButton_Click()
   Setting
End Sub



'*************************************************************************************************************
'**********************************************USERFORM EVENTS************************************************
Private Sub UserForm_Initialize()
'WAIT FOR FILE OPEN AND CLOSE EVENTS
   Set openCloseHandler = New ClsOpenCloseDupFind

'REDRAW SQUARES

'MOVE INTO LAST POSITION
   If GetSetting(APP_NAME, SECTION_DUP_FINDER, KEY_START_TOP, "") = "" Then
      Me.StartUpPosition = 1
   Else
      Me.StartUpPosition = 0
      Me.Top = CDbl(GetSetting(APP_NAME, SECTION_DUP_FINDER, KEY_START_TOP, WINDOW_DEFAULT_TOP))
      Me.Left = CDbl(GetSetting(APP_NAME, SECTION_DUP_FINDER, KEY_START_LEFT, WINDOW_DEFAULT_LEFT))
   End If
   
'ELEVATION FIELD
   LoadElevationEntry ZTextbox, SECTION_DUP_FINDER, KEY_ELEVATION
   ZTextbox.MaxLength = MAX_LEN_ELEV_STRING

'RADIUS FIELD
   LoadRadiusEntry DiameterTextBox, SECTION_DUP_FINDER, KEY_RADIUS
   DiameterTextBox.MaxLength = MAX_LEN_RADIUS_STRING


'INITIALIZE ARRAYS
   ReDim points(0 To 0)
   ReDim selIndex(0 To 0)
   ReDim markOverlap(0 To 0)
   ReDim dispText(0 To 0)
   ReDim dispTextD(0 To 0)

'INITIALIZE SQUARE SIZE COMBOBOX
   SqSizeComboBox.AddItem "10"
   SqSizeComboBox.AddItem "20"
   SqSizeComboBox.AddItem "30"
   SqSizeComboBox.AddItem "40"
   SqSizeComboBox.AddItem "50"
   SqSizeComboBox.AddItem "100"
   Dim sqSize As String
   sqSize = GetSetting(APP_NAME, SECTION_DUP_FINDER, KEY_SQUARE_SIZE, "30")
   SqSizeComboBox.text = sqSize

'INITIALIZE SQUARES CHECKBOX
   InitializeCheckBox SquaresCheckBox, SECTION_DUP_FINDER, KEY_SQUARE
   SqSizeState

'CIRCLES ATTRIBUTES
'LEVEL COMBOBOX
   PopulateLevelBox LevelComboBox2, SECTION_DUP_FINDER, KEY_LEVEL2
'COLOR COMBOBOX
   PopulateColorBox ColorComboBox2, SECTION_DUP_FINDER, KEY_COLOR2
'STYLE COMBOBOX
   PopulateLinestyleBox StyleComboBox2, SECTION_DUP_FINDER, KEY_STYLE2
'WEIGHT COMBOBOX
   PopulateWeightBox WeightComboBox2, SECTION_DUP_FINDER, KEY_WEIGHT2


'HIDE SCROLLBAR
   ScrollBarState

'HIDE LISTBOX
   CoordinateListBox.Visible = False
   
'SET BACK GROUND COLOR OF LIST LABELS
   clearListDisp

'SET STATE OF PICK BUTTON
   PickButtonState

'SET TITLEBAR CAPTION
   Me.Caption = COMMAND_NAME_DUP_FINDER

'SET TO MAIN PAGE
   Me.MultiPage1.value = 0

'REDRAW SQUARES
   Set viewChangeHandler = New ClsViewChange
   AddViewUpdateEventsHandler viewChangeHandler
End Sub



Private Sub UserForm_QueryClose(Cancel As Integer, CloseMode As Integer)
'SAVE USERFORM POSITION
   SaveSetting APP_NAME, SECTION_DUP_FINDER, KEY_START_TOP, FormatNumber(Me.Top, 2)
   SaveSetting APP_NAME, SECTION_DUP_FINDER, KEY_START_LEFT, FormatNumber(Me.Left, 2)
End Sub

Attribute VB_Name = "FrmEnterCourse"
Attribute VB_Base = "0{777079AC-8584-4580-BC66-B6C91B30F1BF}{E4E493E6-5C24-4999-957C-0879F13BF21F}"
Attribute VB_GlobalNameSpace = False
Attribute VB_Creatable = False
Attribute VB_PredeclaredId = True
Attribute VB_Exposed = False
Attribute VB_TemplateDerived = False
Attribute VB_Customizable = False














'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.



'GENERAL NOTES:
'PROGRAM ASSUMES MASTER UNIT IS FOOT OR SURVEY FOOT, SOME KIND OF FOOT


Option Explicit

Private operatingMode     As Long
Private currentIndex      As Long
Private oldLineAzimuth    As String
Private oldLineDistance   As String
Private oldCurveRadius    As String
Private oldChordAzimuth   As String
Private oldChord          As String
Private oldRadialAzIn     As String
Private oldRadialAzOut    As String
Private oldTangentAzIn    As String
Private oldTangentAzOut   As String
Private oldChordDirTanOut As String
Private oldTanOutDirChord As String
Private oldChordDirTanIn  As String
Private oldTanInDirChord  As String



Private Sub LoadCourse(ByVal TheIndex As Long)
'LOADS COURSE INFO INTO USERFORM FOR EDITING
'ASSUMES VALID INDEX
   Dim CourseType As String
   CourseType = FrmPlotLot.CoursesListBox.List(TheIndex, 1)
   Select Case CourseType
      Case Lot_Closure_List_Type_Line
         Dim azString As String
         Dim DistString As String
         azString = FrmPlotLot.CoursesListBox.List(TheIndex, 2)
         DistString = FrmPlotLot.CoursesListBox.List(TheIndex, 3)
         DistString = Mid(DistString, Len(Lot_Closure_Data_Prefix_Distance) + 1)
         DistanceTextBox_Enter_Field DistString
         azString = Mid(azString, Len(Lot_Closure_Data_Prefix_Direction) + 1)
         AzimuthTextBox_Enter_Field azString
         OptionLine.value = True
         CourseEntryControls
      Case Lot_Closure_List_Type_Curve
         LoadCurve TheIndex
         OptionCurve.value = True
         CourseEntryControls
   End Select
End Sub



Private Sub LoadCurve(ByVal TheIndex As Long)
   Dim Data1 As String
   Data1 = FrmPlotLot.CoursesListBox.List(TheIndex, 2)
   Dim Data2 As String
   Data2 = FrmPlotLot.CoursesListBox.List(TheIndex, 3)
   Dim Data3 As String
   Data3 = FrmPlotLot.CoursesListBox.List(TheIndex, 4)
   Dim Data4 As String
   Data4 = FrmPlotLot.CoursesListBox.List(TheIndex, 5)
   
   Dim typeString As String
   Dim dataString As String
   
   SplitData Data1, typeString, dataString
   Select Case typeString
      Case Lot_Closure_Data_Prefix_Chord_Dr
         OptionChordDef.value = True
         ChordAzTextBox_Enter_Field dataString
         SplitData Data2, typeString, dataString
         ChordTextBox_Enter_Field dataString
         SplitData Data3, typeString, dataString
         RadiusTextBox_Enter_Field dataString
         SplitData Data4, typeString, dataString
         If dataString = Lot_Closure_Data_Rot_Left Then
            OptionLeft.value = True
         Else
            OptionRight.value = True
         End If
         Dim Data5 As String
         Data5 = FrmPlotLot.CoursesListBox.List(TheIndex, 6)
         SplitData Data5, typeString, dataString
         If dataString = Lot_Closure_Data_Size_Large Then
            CheckBoxBig.value = True
         Else
            CheckBoxBig.value = False
         End If
      
      Case Lot_Closure_Data_Prefix_RadialIn
         OptionRadials.value = True
         RadialInTextBox_Enter_Field dataString
         SplitData Data2, typeString, dataString
         RadiusTextBox_Enter_Field dataString
         SplitData Data3, typeString, dataString
         RadialOutTextBox_Enter_Field dataString
         SplitData Data4, typeString, dataString
         If dataString = Lot_Closure_Data_Size_Large Then
            CheckBoxBig.value = True
         Else
            CheckBoxBig.value = False
         End If
      
      Case Lot_Closure_Data_Prefix_TangentIn
         OptionTangents.value = True
         TangentInTextBox_Enter_Field dataString
         SplitData Data2, typeString, dataString
         RadiusTextBox_Enter_Field dataString
         SplitData Data3, typeString, dataString
         TangentOutTextBox_Enter_Field dataString
         SplitData Data4, typeString, dataString
         If dataString = Lot_Closure_Data_Size_Large Then
            CheckBoxBig.value = True
         Else
            CheckBoxBig.value = False
         End If
      
      Case Lot_Closure_Data_Prefix_TangentOut
         OptionTanOutChd.value = True
         TanOutChdTextBox_Enter_Field dataString
         SplitData Data2, typeString, dataString
         RadiusTextBox_Enter_Field dataString
         SplitData Data3, typeString, dataString
         ChdDirOutTextBox_Enter_Field dataString
         
      Case Lot_Closure_Data_Prefix_Radius
         OptionTanInChd.value = True
         RadiusTextBox_Enter_Field dataString
         SplitData Data2, typeString, dataString
         TanInChdTextBox_Enter_Field dataString
         SplitData Data3, typeString, dataString
         ChdTanInTextBox_Enter_Field dataString
   End Select
End Sub



Private Sub NewRow(ByVal TheIndex As Long, ByVal TheMode As Long)
'ADD THE ROW OR CLEAR IT OUT
   If TheMode = Mode_Insert Then
      Dim ListCount As Long
      ListCount = FrmPlotLot.CoursesListBox.ListCount
      FrmPlotLot.CoursesListBox.AddItem FormatNumber(TheIndex + 1, 0), TheIndex
      FrmPlotLot.RenumberCourses
   End If
   FrmPlotLot.CoursesListBox.List(TheIndex, 2) = ""
   FrmPlotLot.CoursesListBox.List(TheIndex, 3) = ""
   FrmPlotLot.CoursesListBox.List(TheIndex, 4) = ""
   FrmPlotLot.CoursesListBox.List(TheIndex, 5) = ""
   FrmPlotLot.CoursesListBox.List(TheIndex, 6) = ""
End Sub



Private Sub InsertCaption(ByVal TheIndex As Long)
   Me.Caption = "Insert Course " & FormatNumber(TheIndex + 1, 0)
End Sub



Private Sub EnterCourseInListBox(ByVal TheIndex As Long)
   If OptionLine = True Then
      FrmPlotLot.CoursesListBox.List(TheIndex, 1) = Lot_Closure_List_Type_Line
      FrmPlotLot.CoursesListBox.List(TheIndex, 2) = Lot_Closure_Data_Prefix_Direction & AzimuthTextBox.text
      FrmPlotLot.CoursesListBox.List(TheIndex, 3) = Lot_Closure_Data_Prefix_Distance & DistanceTextBox.text
   End If
   If OptionCurve = True Then
      EnterCurve TheIndex
   End If
End Sub



Private Sub EnterCurve(ByVal TheIndex As Long)
   Dim temp As String
   FrmPlotLot.CoursesListBox.List(TheIndex, 1) = Lot_Closure_List_Type_Curve
   If OptionChordDef.value = True Then
      temp = ChordAzTextBox.text
      temp = Lot_Closure_Data_Prefix_Chord_Dr & temp
      FrmPlotLot.CoursesListBox.List(TheIndex, 2) = temp
      temp = Lot_Closure_Data_Prefix_Chord & Trim(ChordTextBox.text)
      FrmPlotLot.CoursesListBox.List(TheIndex, 3) = temp
      temp = Lot_Closure_Data_Prefix_Radius & Trim(RadiusTextBox.text)
      FrmPlotLot.CoursesListBox.List(TheIndex, 4) = temp
      If OptionLeft.value = True Then
         FrmPlotLot.CoursesListBox.List(TheIndex, 5) = Lot_Closure_Data_Prefix_Rotation & Lot_Closure_Data_Rot_Left
      Else
         FrmPlotLot.CoursesListBox.List(TheIndex, 5) = Lot_Closure_Data_Prefix_Rotation & Lot_Closure_Data_Rot_Right
      End If
      If CheckBoxBig.value = True Then
         FrmPlotLot.CoursesListBox.List(TheIndex, 6) = Lot_Closure_Data_Prefix_Size & Lot_Closure_Data_Size_Large
      Else
         FrmPlotLot.CoursesListBox.List(TheIndex, 6) = Lot_Closure_Data_Prefix_Size & Lot_Closure_Data_Size_Small
      End If
   End If
   
   If OptionRadials.value = True Then
      temp = RadialInTextBox.text
      temp = Lot_Closure_Data_Prefix_RadialIn & temp
      FrmPlotLot.CoursesListBox.List(TheIndex, 2) = temp
      temp = Lot_Closure_Data_Prefix_Radius & Trim(RadiusTextBox.text)
      FrmPlotLot.CoursesListBox.List(TheIndex, 3) = temp
      temp = RadialOutTextBox.text
      temp = Lot_Closure_Data_Prefix_RadialOut & temp
      FrmPlotLot.CoursesListBox.List(TheIndex, 4) = temp
      If CheckBoxBig.value = True Then
         FrmPlotLot.CoursesListBox.List(TheIndex, 5) = Lot_Closure_Data_Prefix_Size & Lot_Closure_Data_Size_Large
      Else
         FrmPlotLot.CoursesListBox.List(TheIndex, 5) = Lot_Closure_Data_Prefix_Size & Lot_Closure_Data_Size_Small
      End If
   End If
   
   If OptionTangents.value = True Then
      temp = TangentInTextBox.text
      temp = Lot_Closure_Data_Prefix_TangentIn & temp
      FrmPlotLot.CoursesListBox.List(TheIndex, 2) = temp
      temp = Lot_Closure_Data_Prefix_Radius & Trim(RadiusTextBox.text)
      FrmPlotLot.CoursesListBox.List(TheIndex, 3) = temp
      temp = TangentOutTextBox.text
      temp = Lot_Closure_Data_Prefix_TangentOut & temp
      FrmPlotLot.CoursesListBox.List(TheIndex, 4) = temp
      If CheckBoxBig.value = True Then
         FrmPlotLot.CoursesListBox.List(TheIndex, 5) = Lot_Closure_Data_Prefix_Size & Lot_Closure_Data_Size_Large
      Else
         FrmPlotLot.CoursesListBox.List(TheIndex, 5) = Lot_Closure_Data_Prefix_Size & Lot_Closure_Data_Size_Small
      End If
   End If
   
   If OptionTanOutChd.value Then
      temp = Lot_Closure_Data_Prefix_TangentOut & TanOutChdTextBox.text
      FrmPlotLot.CoursesListBox.List(TheIndex, 2) = temp
      temp = Lot_Closure_Data_Prefix_Radius & Trim(RadiusTextBox.text)
      FrmPlotLot.CoursesListBox.List(TheIndex, 3) = temp
      temp = Lot_Closure_Data_Prefix_Chord_Dr & ChdDirOutTextBox.text
      FrmPlotLot.CoursesListBox.List(TheIndex, 4) = temp
   End If
   
   If OptionTanInChd.value Then
      temp = Lot_Closure_Data_Prefix_Radius & Trim(RadiusTextBox.text)
      FrmPlotLot.CoursesListBox.List(TheIndex, 2) = temp
      temp = Lot_Closure_Data_Prefix_TangentIn & TanInChdTextBox.text
      FrmPlotLot.CoursesListBox.List(TheIndex, 3) = temp
      temp = Lot_Closure_Data_Prefix_Chord_Dr & ChdTanInTextBox.text
      FrmPlotLot.CoursesListBox.List(TheIndex, 4) = temp
   End If

End Sub




'************************************************CONTROLS*****************************************************
'*************************************************************************************************************
'LINE OPTION RADIO BUTTON
Private Sub OptionLine_Click()
   CourseEntryControls
   If AzimuthTextBox.enabled = True Then
      AzimuthTextBox.SetFocus
   End If
End Sub



'LINE DIRECTION TEXTBOX
Private Sub AzimuthTextBox_AfterUpdate()
   DirectionOnUpdate AzimuthTextBox, oldLineAzimuth
End Sub

Private Sub AzimuthTextBox_Enter()
   SelectAllText AzimuthTextBox
End Sub

Public Sub AzimuthTextBox_Enter_Field(Entry As String)
   AzimuthTextBox.text = Entry
   AzimuthTextBox_AfterUpdate
End Sub



'LINE DIRECTION +180 BUTTON
Private Sub Plus180AzButton_Click()
   Plus180 AzimuthTextBox
   AzimuthTextBox_AfterUpdate
End Sub



'LINE DISTANCE TEXTBOX
Private Sub DistanceTextBox_AfterUpdate()
   DistanceOnUpdate DistanceTextBox, oldLineDistance, False
End Sub

Private Sub DistanceTextBox_Enter()
   SelectAllText DistanceTextBox
End Sub

Public Sub DistanceTextBox_Enter_Field(Entry As String)
   DistanceTextBox.text = Entry
   DistanceTextBox_AfterUpdate
End Sub



'CURVE OPTION RADIO BUTTON
Private Sub OptionCurve_Click()
   CourseEntryControls
   RadiusTextBox.SetFocus
End Sub



'RADIUS TEXTBOX
Private Sub RadiusTextBox_AfterUpdate()
   DistanceOnUpdate RadiusTextBox, oldCurveRadius, False
End Sub

Private Sub RadiusTextBox_Enter()
   SelectAllText RadiusTextBox
End Sub

Public Sub RadiusTextBox_Enter_Field(Entry As String)
   RadiusTextBox.text = Entry
   RadiusTextBox_AfterUpdate
End Sub



'LARGER ARC CHECKBOX
Private Sub CheckBoxBig_Click()
   SaveCheckBoxSetting CheckBoxBig, SECTION_LOT_CLOSURE_EDIT, KEY_TOGGLE_LARGER
End Sub



'CURVE CHORD DIRECTION RADIO BUTTON
Private Sub OptionChordDef_Click()
   CourseEntryControls
   If ChordAzTextBox.enabled Then
      ChordAzTextBox.SetFocus
   End If
End Sub



'CURVE CHORD DIRECTION TEXTBOX
Private Sub ChordAzTextBox_AfterUpdate()
   DirectionOnUpdate ChordAzTextBox, oldChordAzimuth
End Sub

Private Sub ChordAzTextBox_Enter()
   SelectAllText ChordAzTextBox
End Sub

Public Sub ChordAzTextBox_Enter_Field(Entry As String)
   ChordAzTextBox.text = Entry
   ChordAzTextBox_AfterUpdate
End Sub



'CURVE CHORD DIRECTION +180 BUTTON
Private Sub ChordPlus180Button_Click()
   Plus180 ChordAzTextBox
   ChordAzTextBox_AfterUpdate
End Sub




'CHORD DISTANCE TEXTBOX
Private Sub ChordTextBox_AfterUpdate()
   DistanceOnUpdate ChordTextBox, oldChord, False
End Sub

Private Sub ChordTextBox_Enter()
   SelectAllText ChordTextBox
End Sub

Public Sub ChordTextBox_Enter_Field(Entry As String)
   ChordTextBox.text = Entry
   ChordTextBox_AfterUpdate
End Sub



'CURVE P.C. TO C.C. CHECKBOX
Private Sub OptionRadials_Click()
   CourseEntryControls
   If RadialInTextBox.enabled Then
      RadialInTextBox.SetFocus
   End If
End Sub



'CURVE P.C. TO C.C TEXTBOX
Private Sub RadialInTextBox_AfterUpdate()
   DirectionOnUpdate RadialInTextBox, oldRadialAzIn
End Sub

Private Sub RadialInTextBox_Enter()
   SelectAllText RadialInTextBox
End Sub

Public Sub RadialInTextBox_Enter_Field(Entry As String)
   RadialInTextBox.text = Entry
   RadialInTextBox_AfterUpdate
End Sub



'CURVE P.C. TO C.C. +180 BUTTON
Private Sub RadialInPlus180Button_Click()
   Plus180 RadialInTextBox
   RadialInTextBox_AfterUpdate
End Sub



'CURVE C.C. TO P.T. TEXTBOX
Private Sub RadialOutTextBox_AfterUpdate()
   DirectionOnUpdate RadialOutTextBox, oldRadialAzOut
End Sub

Private Sub RadialOutTextBox_Enter()
   SelectAllText RadialOutTextBox
End Sub

Public Sub RadialOutTextBox_Enter_Field(Entry As String)
   RadialOutTextBox.text = Entry
   RadialOutTextBox_AfterUpdate
End Sub



'CURVE C.C. TO P.T. +180 BUTTON
Private Sub RadialOutPlus180Button_Click()
   Plus180 RadialOutTextBox
   RadialOutTextBox_AfterUpdate
End Sub



'CURVE TANGENT IN RADIO BUTTON
Private Sub OptionTangents_Click()
   CourseEntryControls
   If TangentInTextBox.enabled Then
      TangentInTextBox.SetFocus
   End If
End Sub



'CURVE TANGENT IN TEXTBOX
Private Sub TangentInTextBox_AfterUpdate()
   DirectionOnUpdate TangentInTextBox, oldTangentAzIn
End Sub

Private Sub TangentInTextBox_Enter()
   SelectAllText TangentInTextBox
End Sub

Public Sub TangentInTextBox_Enter_Field(Entry As String)
   TangentInTextBox.text = Entry
   TangentInTextBox_AfterUpdate
End Sub



'CURVE TANGENT IN +180 BUTTON
Private Sub TangentInPlus180Button_Click()
   Plus180 TangentInTextBox
   TangentInTextBox_AfterUpdate
End Sub



'CURVE TANGENT OUT TEXTBOX
Private Sub TangentOutTextBox_AfterUpdate()
   DirectionOnUpdate TangentOutTextBox, oldTangentAzOut
End Sub

Private Sub TangentOutTextBox_Enter()
   SelectAllText TangentOutTextBox
End Sub

Public Sub TangentOutTextBox_Enter_Field(Entry As String)
   TangentOutTextBox.text = Entry
   TangentOutTextBox_AfterUpdate
End Sub



'CURVE TANGENT OUT +180 BUTTON
Private Sub TangentOutPlus180Button_Click()
   Plus180 TangentOutTextBox
   TangentOutTextBox_AfterUpdate
End Sub



'CURVE CHORD DIRECTION TANGENT OUT RADIO BUTTON
Private Sub OptionTanOutChd_Click()
   CourseEntryControls
   If ChdDirOutTextBox.enabled Then
      ChdDirOutTextBox.SetFocus
   End If
End Sub



'CURVE CHORD DIRECTION TEXTBOX FOR TANGENT OUT SOLUTION
Private Sub ChdDirOutTextBox_AfterUpdate()
   DirectionOnUpdate ChdDirOutTextBox, oldChordDirTanOut
End Sub

Private Sub ChdDirOutTextBox_Enter()
   SelectAllText ChdDirOutTextBox
End Sub

Public Sub ChdDirOutTextBox_Enter_Field(Entry As String)
   ChdDirOutTextBox.text = Entry
   ChdDirOutTextBox_AfterUpdate
End Sub



'CURVE CHORD DIRECTION TEXTBOX FOR TANGENT OUT SOLUTION +180 BUTTON
Private Sub ChrOutPlus180Button_Click()
   Plus180 ChdDirOutTextBox
   ChdDirOutTextBox_AfterUpdate
End Sub



'CURVE TANGENT OUT DIRECTION CHORD SOLUTION
Private Sub TanOutChdTextBox_AfterUpdate()
   DirectionOnUpdate TanOutChdTextBox, oldTanOutDirChord
End Sub

Private Sub TanOutChdTextBox_Enter()
   SelectAllText TanOutChdTextBox
End Sub

Public Sub TanOutChdTextBox_Enter_Field(Entry As String)
   TanOutChdTextBox.text = Entry
   TanOutChdTextBox_AfterUpdate
End Sub



'TANGENT OUT CHORD SOLUTION +180 BUTTON
Private Sub TanOutChdPlus180Button_Click()
   Plus180 TanOutChdTextBox
   TanOutChdTextBox_AfterUpdate
End Sub




'CURVE CHORD DIRECTION TANGENT IN RADIO BUTTON
Private Sub OptionTanInChd_Click()
   CourseEntryControls
   If TanInChdTextBox.enabled Then
      TanInChdTextBox.SetFocus
   End If
End Sub



'CURVE TANGENT IN FOR CHORD SOLUTION
Private Sub TanInChdTextBox_AfterUpdate()
   DirectionOnUpdate TanInChdTextBox, oldTanInDirChord
End Sub

Private Sub TanInChdTextBox_Enter()
   SelectAllText TanInChdTextBox
End Sub

Public Sub TanInChdTextBox_Enter_Field(Entry As String)
   TanInChdTextBox.text = Entry
   TanInChdTextBox_AfterUpdate
End Sub



'TANGENT IN CHORD SOLUTION +180 BUTTON
Private Sub TanInChdPlus180Button_Click()
   Plus180 TanInChdTextBox
   TanInChdTextBox_AfterUpdate
End Sub



'CURVE TANGENT OUT FOR CHORD SOLUTION
Private Sub ChdTanInTextBox_AfterUpdate()
   DirectionOnUpdate ChdTanInTextBox, oldChordDirTanIn
End Sub

Private Sub ChdTanInTextBox_Enter()
   SelectAllText ChdTanInTextBox
End Sub

Public Sub ChdTanInTextBox_Enter_Field(Entry As String)
   ChdTanInTextBox.text = Entry
   ChdTanInTextBox_AfterUpdate
End Sub




'CHORD TANGENT IN SOLUTION +180 BUTTON
Private Sub ChdTanInPlus180Button_Click()
   Plus180 ChdTanInTextBox
   ChdTanInTextBox_AfterUpdate
End Sub



'CLOSE BUTTON
Private Sub CloseButton_Click()
   Unload Me
End Sub



'ENTER BUTTON
Private Sub EnterButton_Click()
'CHECK IF VALID CURVE
   If OptionCurve = True And OptionChordDef = True Then
       If (2# * CDbl(RadiusTextBox.text)) < CDbl(ChordTextBox.text) Then
          Beep
          Exit Sub
       End If
   End If
   NewRow currentIndex, operatingMode
   EnterCourseInListBox currentIndex
   If operatingMode = Mode_Edit Then
      FrmPlotLot.UpdateAll
      Me.Hide
   End If
   If operatingMode = Mode_Insert Then
      FrmPlotLot.CoursesListBox.listIndex = currentIndex
      FrmPlotLot.UpdateAll
   End If

   currentIndex = currentIndex + 1
   InsertCaption currentIndex
   If OptionLine.value = True Then
      AzimuthTextBox.SetFocus
   End If
   If OptionCurve.value = True Then
      RadiusTextBox.SetFocus
   End If
End Sub




'*************************************************************************************************************
'*******************************************CONTROL STATES****************************************************
Private Sub ChordAzimuthControls()
   Dim state As Boolean
   state = OptionChordDef.value And OptionCurve.value
   ChordAzLabel.enabled = state
   ChordAzTextBox.enabled = state
   ChordAzTextBox.BackColor = BackOLE_COLOR(state)
   ChordPlus180Button.enabled = state
   ChordLabel.enabled = state
   ChordTextBox.enabled = state
   ChordTextBox.BackColor = BackOLE_COLOR(state)
   OptionLeft.enabled = state
   OptionRight.enabled = state
End Sub



Private Sub CourseEntryControls()
   LineOptionControls
   CurveOptionControls
End Sub



Private Sub CurveOptionControls()
   Dim state As Boolean
   state = OptionCurve.value
   RadiusLabel.enabled = state
   RadiusTextBox.enabled = state
   RadiusTextBox.BackColor = BackOLE_COLOR(state)
   CheckBoxBig.enabled = state And (Not OptionTanOutChd.value) And (Not OptionTanInChd.value)
   OptionChordDef.enabled = state
   OptionRadials.enabled = state
   OptionTangents.enabled = state
   OptionTanOutChd.enabled = state
   OptionTanInChd.enabled = state
   CurveTypeControls
End Sub



Private Sub CurveTypeControls()
   ChordAzimuthControls
   RadialsControls
   TangentsControls
   ChdTanOutControls
   TanInChdControls
End Sub



Private Sub LineOptionControls()
   Dim state As Boolean
   state = OptionLine.value
   AzimuthLabel.enabled = state
   AzimuthTextBox.enabled = state
   AzimuthTextBox.BackColor = BackOLE_COLOR(state)
   DistanceLabel.enabled = state
   DistanceTextBox.enabled = state
   DistanceTextBox.BackColor = BackOLE_COLOR(state)
   Plus180AzButton.enabled = state
End Sub



Private Sub RadialsControls()
   Dim state As Boolean
   state = OptionRadials.value And OptionCurve.value
   RadialInLabel.enabled = state
   RadialInTextBox.enabled = state
   RadialInTextBox.BackColor = BackOLE_COLOR(state)
   RadialInPlus180Button.enabled = state
   RadialOutLabel.enabled = state
   RadialOutTextBox.enabled = state
   RadialOutTextBox.BackColor = BackOLE_COLOR(state)
   RadialOutPlus180Button.enabled = state
End Sub



Private Sub TangentsControls()
   Dim state As Boolean
   state = OptionTangents.value And OptionCurve.value
   TangentInLabel.enabled = state
   TangentInTextBox.enabled = state
   TangentInTextBox.BackColor = BackOLE_COLOR(state)
   TangentInPlus180Button.enabled = state
   TangentOutLabel.enabled = state
   TangentOutTextBox.enabled = state
   TangentOutTextBox.BackColor = BackOLE_COLOR(state)
   TangentOutPlus180Button.enabled = state
End Sub



Private Sub ChdTanOutControls()
   Dim state As Boolean
   state = OptionTanOutChd.value And OptionCurve.value
   ChdTanOutLabel.enabled = state
   ChdDirOutTextBox.enabled = state
   ChdDirOutTextBox.BackColor = BackOLE_COLOR(state)
   ChrOutPlus180Button.enabled = state
   TanOutLabel.enabled = state
   TanOutChdTextBox.enabled = state
   TanOutChdTextBox.BackColor = BackOLE_COLOR(state)
   TanOutChdPlus180Button.enabled = state
End Sub



Private Sub TanInChdControls()
   Dim state As Boolean
   state = OptionTanInChd.value And OptionCurve.value
   TanInChdLabel.enabled = state
   TanInChdTextBox.enabled = state
   TanInChdTextBox.BackColor = BackOLE_COLOR(state)
   TanInChdPlus180Button.enabled = state
   ChdTanInLabel.enabled = state
   ChdTanInTextBox.enabled = state
   ChdTanInTextBox.BackColor = BackOLE_COLOR(state)
   ChdTanInPlus180Button.enabled = state
End Sub



'*************************************************************************************************************
'**********************************************USERFORM EVENTS************************************************
Public Sub UserForm_Initialize()
'INITIALIZE FIELDS
   AzimuthTextBox_Enter_Field (GetSetting(APP_NAME, SECTION_LOT_CLOSURE_EDIT, KEY_LINE_AZIMUTH, "100^35'"))
   ChordAzTextBox_Enter_Field (GetSetting(APP_NAME, SECTION_LOT_CLOSURE_EDIT, KEY_CHORD_AZ, "100^35'"))
   RadialInTextBox_Enter_Field (GetSetting(APP_NAME, SECTION_LOT_CLOSURE_EDIT, KEY_RADIAL_IN, "100^35'"))
   RadialOutTextBox_Enter_Field (GetSetting(APP_NAME, SECTION_LOT_CLOSURE_EDIT, KEY_RADIAL_OUT, "100^35'"))
   TangentInTextBox_Enter_Field (GetSetting(APP_NAME, SECTION_LOT_CLOSURE_EDIT, KEY_TANGENT_AZ_IN, "100^35'"))
   TangentOutTextBox_Enter_Field (GetSetting(APP_NAME, SECTION_LOT_CLOSURE_EDIT, KEY_TANGENT_AZ_OUT, "100^35'"))
   DistanceTextBox_Enter_Field (GetSetting(APP_NAME, SECTION_LOT_CLOSURE_EDIT, KEY_LINE_DISTANCE, "100.00"))
   ChordTextBox_Enter_Field (GetSetting(APP_NAME, SECTION_LOT_CLOSURE_EDIT, KEY_CHORD, "100.00"))
   RadiusTextBox_Enter_Field (GetSetting(APP_NAME, SECTION_LOT_CLOSURE_EDIT, KEY_CURVE_RADIUS, "100.00"))
   TanOutChdTextBox_Enter_Field (GetSetting(APP_NAME, SECTION_LOT_CLOSURE_EDIT, KEY_TO_CHORD_DR, "100.00"))
   ChdDirOutTextBox_Enter_Field (GetSetting(APP_NAME, SECTION_LOT_CLOSURE_EDIT, KEY_CHORD_TAN_OUT, "100.00"))
   TanInChdTextBox_Enter_Field (GetSetting(APP_NAME, SECTION_LOT_CLOSURE_EDIT, KEY_TI_CHORD_DR, "100.00"))
   ChdTanInTextBox_Enter_Field (GetSetting(APP_NAME, SECTION_LOT_CLOSURE_EDIT, KEY_CHORD_TAN_IN, "100.00"))
'INITIALIZE BIGGER WHEN AMBIGUOUS CHECK BOX
   InitializeCheckBox CheckBoxBig, SECTION_LOT_CLOSURE_EDIT, KEY_TOGGLE_LARGER, False
   
'SET OPTIONS
   Dim myOption As String
   myOption = GetSetting(APP_NAME, SECTION_LOT_CLOSURE_EDIT, KEY_CHORD_ROT_LEFT, OPTION_TRUE)
   If myOption = OPTION_TRUE Then
      OptionLeft.value = True
   Else
      OptionRight.value = True
   End If
   myOption = GetSetting(APP_NAME, SECTION_LOT_CLOSURE_EDIT, KEY_CURVE_DEFINITION, CURVE_DEFINITION_CHORD)
   Select Case myOption
      Case CURVE_DEFINITION_CHORD
         OptionChordDef.value = True
      Case CURVE_DEFINITION_RADIALS
         OptionRadials.value = True
      Case CURVE_DEFINITION_TANGENTS
         OptionTangents.value = True
      Case CURVE_DEFINITION_TAN_OUT_CHD
         OptionTanOutChd.value = True
      Case CURVE_DEFINITION_TAN_IN_CHD
         OptionTanInChd.value = True
   End Select
   myOption = GetSetting(APP_NAME, SECTION_LOT_CLOSURE_EDIT, KEY_COURSE_TYPE, OPTION_LINE)
   If myOption = OPTION_LINE Then
      OptionLine.value = True
      OptionLine_Click
   Else
      OptionCurve.value = True
      OptionCurve_Click
   End If

'MOVE INTO LAST POSITION
   If GetSetting(APP_NAME, SECTION_LOT_CLOSURE_EDIT, KEY_START_TOP, "") = "" Then
      Me.StartUpPosition = 1
   Else
      Me.StartUpPosition = 0
      Me.Top = CDbl(GetSetting(APP_NAME, SECTION_LOT_CLOSURE_EDIT, KEY_START_TOP, WINDOW_DEFAULT_TOP))
      Me.Left = CDbl(GetSetting(APP_NAME, SECTION_LOT_CLOSURE_EDIT, KEY_START_LEFT, WINDOW_DEFAULT_LEFT))
   End If
   
'GET THE MODE
   operatingMode = FrmPlotLot.WhatModeAmIIn

'GET THE CURRENT INDEX
   currentIndex = FrmPlotLot.WhatIsTheCurrentIndex

'SET THE CAPTION, LOAD COURSE TO EDIT
   If operatingMode = Mode_Edit Then
      Me.Caption = "Edit Course " & FormatNumber(currentIndex + 1, 0)
      LoadCourse currentIndex
   Else
      InsertCaption currentIndex
   End If

'SIZE DIALOG BOX IF NEEDED
   If FrmPlotLot.Zoom = 100 Then
      Me.Zoom = 100
      Me.Width = 379.5
      Me.Height = 184.5
   Else
      FrmEnterCourse.Zoom = 140
      Me.Width = 379.5 * 1.4
      Me.Height = 184.5 * 1.4
   End If
End Sub



Private Sub UserForm_QueryClose(Cancel As Integer, CloseMode As Integer)
'SAVE USERFORM POSITION
   SaveSetting APP_NAME, SECTION_LOT_CLOSURE_EDIT, KEY_START_TOP, FormatNumber(Me.Top, 0)
   SaveSetting APP_NAME, SECTION_LOT_CLOSURE_EDIT, KEY_START_LEFT, FormatNumber(Me.Left, 0)
End Sub



Private Sub UserForm_Terminate()
   FrmPlotLot.ClearInsertingFlag
   SaveSetting APP_NAME, SECTION_LOT_CLOSURE_EDIT, KEY_LINE_AZIMUTH, AzimuthTextBox.text
   SaveSetting APP_NAME, SECTION_LOT_CLOSURE_EDIT, KEY_CHORD_AZ, ChordAzTextBox.text
   SaveSetting APP_NAME, SECTION_LOT_CLOSURE_EDIT, KEY_RADIAL_IN, RadialInTextBox.text
   SaveSetting APP_NAME, SECTION_LOT_CLOSURE_EDIT, KEY_RADIAL_OUT, RadialOutTextBox.text
   SaveSetting APP_NAME, SECTION_LOT_CLOSURE_EDIT, KEY_TANGENT_AZ_IN, TangentInTextBox.text
   SaveSetting APP_NAME, SECTION_LOT_CLOSURE_EDIT, KEY_TANGENT_AZ_OUT, TangentOutTextBox.text
   SaveSetting APP_NAME, SECTION_LOT_CLOSURE_EDIT, KEY_LINE_DISTANCE, DistanceTextBox.text
   SaveSetting APP_NAME, SECTION_LOT_CLOSURE_EDIT, KEY_CHORD, ChordTextBox.text
   SaveSetting APP_NAME, SECTION_LOT_CLOSURE_EDIT, KEY_CURVE_RADIUS, RadiusTextBox.text
   SaveSetting APP_NAME, SECTION_LOT_CLOSURE_EDIT, KEY_TI_CHORD_DR, TanInChdTextBox.text
   SaveSetting APP_NAME, SECTION_LOT_CLOSURE_EDIT, KEY_CHORD_TAN_IN, ChdTanInTextBox.text
   SaveSetting APP_NAME, SECTION_LOT_CLOSURE_EDIT, KEY_TO_CHORD_DR, TanOutChdTextBox.text
   SaveSetting APP_NAME, SECTION_LOT_CLOSURE_EDIT, KEY_CHORD_TAN_OUT, ChdDirOutTextBox.text

   If OptionLeft.value = True Then
      SaveSetting APP_NAME, SECTION_LOT_CLOSURE_EDIT, KEY_CHORD_ROT_LEFT, OPTION_TRUE
   Else
      SaveSetting APP_NAME, SECTION_LOT_CLOSURE_EDIT, KEY_CHORD_ROT_LEFT, OPTION_FALSE
   End If

   If OptionChordDef.value = True Then
      SaveSetting APP_NAME, SECTION_LOT_CLOSURE_EDIT, KEY_CURVE_DEFINITION, CURVE_DEFINITION_CHORD
   ElseIf OptionRadials.value = True Then
      SaveSetting APP_NAME, SECTION_LOT_CLOSURE_EDIT, KEY_CURVE_DEFINITION, CURVE_DEFINITION_RADIALS
   ElseIf OptionTanOutChd.value = True Then
      SaveSetting APP_NAME, SECTION_LOT_CLOSURE_EDIT, KEY_CURVE_DEFINITION, CURVE_DEFINITION_TAN_OUT_CHD
   ElseIf OptionTanInChd.value = True Then
      SaveSetting APP_NAME, SECTION_LOT_CLOSURE_EDIT, KEY_CURVE_DEFINITION, CURVE_DEFINITION_TAN_IN_CHD
   Else
      SaveSetting APP_NAME, SECTION_LOT_CLOSURE_EDIT, KEY_CURVE_DEFINITION, CURVE_DEFINITION_TANGENTS
   End If

   If OptionLine.value = True Then
      SaveSetting APP_NAME, SECTION_LOT_CLOSURE_EDIT, KEY_COURSE_TYPE, OPTION_LINE
   Else
      SaveSetting APP_NAME, SECTION_LOT_CLOSURE_EDIT, KEY_COURSE_TYPE, OPTION_CURVE
   End If
End Sub

Attribute VB_Name = "FrmEnterSide"
Attribute VB_Base = "0{55C76778-9683-4E0D-A247-7DB0BF4DD26D}{5ACE2C34-C62C-48DB-A71D-BDA8F727C674}"
Attribute VB_GlobalNameSpace = False
Attribute VB_Creatable = False
Attribute VB_PredeclaredId = True
Attribute VB_Exposed = False
Attribute VB_TemplateDerived = False
Attribute VB_Customizable = False
















'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit

Private IsInsertMode As Boolean



Public Sub EnterCorRecPoint(RecPoint As Point3d)
   CornerRecCoordNorthTextBox.text = FormatNumber(RecPoint.Y, START_COORD_PREC)
   NorthingOrNothing CornerRecCoordNorthTextBox, SECTION_COMPASS_RULE_2D_ENTER_SIDE, KEY_REC_NORTH
   CornerRecCoordEastTextBox.text = FormatNumber(RecPoint.X, START_COORD_PREC)
   CornerRecCoordEastTextBox_AfterUpdate
   Me.Show
End Sub



Public Sub EnterDiagramPlacementPoint(RecPoint As Point3d)
   PlaceDiagCoordNorthTextBox.text = FormatNumber(RecPoint.Y, START_COORD_PREC)
   NorthingOrNothing PlaceDiagCoordNorthTextBox, SECTION_COMPASS_RULE_2D_ENTER_SIDE, KEY_DIAGRAM_NORTH
   PlaceDiagCoordEastTextBox.text = FormatNumber(RecPoint.X, START_COORD_PREC)
   PlaceDiagCoordEastTextBox_AfterUpdate
   Me.Show
End Sub



Private Sub UpdateSideShotIfChecked()
   If UpdateCheckBox.value And UpdateCheckBox.enabled Then
      UpdateSideShot
   End If
End Sub



Private Sub UpdateSideShot()
   Dim cornerRecNorthString As String
   cornerRecNorthString = northStringToDecString(CornerRecCoordNorthTextBox)
   Dim cornerRecEastString As String
   cornerRecEastString = eastStringToDecString(CornerRecCoordEastTextBox)
   Dim diagramNorthString As String
   diagramNorthString = northStringToDecString(PlaceDiagCoordNorthTextBox)
   Dim diagramEastString As String
   diagramEastString = eastStringToDecString(PlaceDiagCoordEastTextBox)
   FrmCompassRule.EditSideShot PointnameTextBox.text, _
                               DescTextBox.text, _
                               BSTextBox.text, _
                               FSTextBox.text, _
                               HDTextBox.text, _
                               ShowDropCheckBox.value, _
                               cornerRecNorthString, _
                               cornerRecEastString, _
                               diagramNorthString, _
                               diagramEastString
End Sub


Private Function northStringToDecString(NorthingTextBox As TextBox) As String
   Dim theScaler As Double
   Dim origPrec As Long
   If IsNorthingString(NorthingTextBox.text, theScaler, origPrec) Then
       northStringToDecString = FormatNumber(theScaler, origPrec, vbTrue, vbFalse, vbFalse)
   Else
       northStringToDecString = NorthingTextBox.text
   End If
End Function



Private Function eastStringToDecString(EastingTextBox As TextBox) As String
   Dim theScaler As Double
   Dim origPrec As Long
   If IsEastingString(EastingTextBox.text, theScaler, origPrec) Then
       eastStringToDecString = FormatNumber(theScaler, origPrec, vbTrue, vbFalse, vbFalse)
   Else
       eastStringToDecString = EastingTextBox.text
   End If
End Function



Private Sub EastingOrNothing(ByRef EastingTextBox As TextBox, _
                             ByVal Section As String, _
                             ByVal Key As String)
   Dim theScaler As Double
   Dim origPrec As Long
   If IsEastingString(EastingTextBox.text, theScaler, origPrec) Then
      EastingTextBox.text = DoubleToEastingString(theScaler, origPrec, True)
      SaveSetting APP_NAME, Section, Key, EastingTextBox.text
   ElseIf EastingTextBox.text = STRING_SPACE Then
      SaveSetting APP_NAME, Section, Key, STRING_SPACE
   Else
      EastingTextBox.text = GetSetting(APP_NAME, Section, Key, STRING_SPACE)
   End If
End Sub



Private Sub NorthingOrNothing(ByRef NorthingTextBox As TextBox, _
                              ByVal Section As String, _
                              ByVal Key As String)
   Dim theScaler As Double
   Dim origPrec As Long
   If IsNorthingString(NorthingTextBox.text, theScaler, origPrec) Then
      NorthingTextBox.text = DoubleToNorthingString(theScaler, origPrec, True)
      SaveSetting APP_NAME, Section, Key, NorthingTextBox.text
   ElseIf NorthingTextBox.text = STRING_SPACE Then
      SaveSetting APP_NAME, Section, Key, STRING_SPACE
   Else
      NorthingTextBox.text = GetSetting(APP_NAME, Section, Key, STRING_SPACE)
   End If
End Sub



Private Sub CalcTheSide(Setup As Point3d, sideShotPoint As Point3d)
   Dim SetupPoint As Point3d
   Dim BackAzDegrees As Double
   Dim SetupName As String
   FrmCompassRule.AtSetupPoint SetupPoint, BackAzDegrees, SetupName
   Setup = SetupPoint
   
   Dim backsightAngle As Double
   If Not AngleStringToDegree(BSTextBox.text, backsightAngle) Then
      backsightAngle = 0#
   End If

   Dim ForesightAngle As Double
   If Not AngleStringToDegree(FSTextBox.text, ForesightAngle) Then
      ForesightAngle = 0#
   End If
   sideShotPoint = CoordFwdSAz(SetupPoint, (BackAzDegrees + ForesightAngle - backsightAngle), CDbl(HDTextBox.text))
End Sub



Private Sub IncSSPointName()
   Dim formattedPointName As String
   If IsPointnameString(PointnameTextBox.text, formattedPointName) Then
      PointnameTextBox.text = IncPointName(formattedPointName)
   Else
      PointnameTextBox.text = ""
   End If
End Sub



Private Function DefaultShowDrop() As Boolean
   If IsInsertMode Then
      DefaultShowDrop = True
   Else
      DefaultShowDrop = StringTrueFalse(GetSetting(APP_NAME, SECTION_COMPASS_RULE_2D_ENTER_SIDE, KEY_SHOW_DROP, OPTION_TRUE))
   End If
End Function



'******************************************************************************************************
'****************************************CONTROLS******************************************************
'BACK SIGHT TEXTBOX
Private Sub BSTextBox_AfterUpdate()
   SaveDeltaEntry BSTextBox, SECTION_COMPASS_RULE_2D_ENTER_SIDE, KEY_BACK_SIGHT_ANGLE, FrmCompassRule.GetAngleStyle
End Sub

Private Sub BSTextBox_Enter()
'SELECT ALL TEXT WHEN FIELD GETS FOCUS
   SelectAllText BSTextBox
End Sub

Private Function DefaultBSAngle() As String
   DefaultBSAngle = GetSetting(APP_NAME, _
                    SECTION_COMPASS_RULE_2D_ENTER_SIDE, _
                    KEY_BACK_SIGHT_ANGLE, _
                    DegreesToAngleString(0#, 4, FrmCompassRule.GetAngleStyle))
End Function



'POINT NAME TEXTBOX
Private Sub PointNameTextBox_AfterUpdate()
   SavePointNameEntry PointnameTextBox, SECTION_COMPASS_RULE_2D_ENTER_SIDE, KEY_POINTNAME
End Sub

Private Sub PointNameTextBox_Enter()
'SELECT ALL TEXT WHEN FIELD GETS FOCUS
   SelectAllText PointnameTextBox
End Sub

Private Function DefaultPointName() As String
   DefaultPointName = GetSetting(APP_NAME, SECTION_COMPASS_RULE_2D_ENTER_SIDE, KEY_POINTNAME, "Trav 1")
End Function



'FORE SIGHT TEXTBOX
Private Sub FSTextBox_AfterUpdate()
   SaveDeltaEntry FSTextBox, SECTION_COMPASS_RULE_2D_ENTER_SIDE, KEY_FORE_SIGHT_ANGLE, FrmCompassRule.GetAngleStyle
End Sub

Private Sub FSTextBox_Enter()
'SELECT ALL TEXT WHEN FIELD GETS FOCUS
   SelectAllText FSTextBox
End Sub

Private Function DefaultFSAngle() As String
   DefaultFSAngle = GetSetting(APP_NAME, SECTION_COMPASS_RULE_2D_ENTER_SIDE, KEY_FORE_SIGHT_ANGLE, DegreesToAngleString("0.0000", 4, FrmCompassRule.GetAngleStyle))
End Function



'HD TEXTBOX
Private Sub HDTextBox_AfterUpdate()
   SaveNonnegativeEntry HDTextBox, SECTION_COMPASS_RULE_2D_ENTER_TRAV, KEY_HORIZONTAL_DISTANCE, MAX_DISTANCE, MAX_PRECISION_DISTANCE, True, 100#
End Sub

Private Sub HDTextBox_Enter()
   SelectAllText HDTextBox
End Sub

Private Function DefaultHD() As String
   DefaultHD = GetSetting(APP_NAME, SECTION_COMPASS_RULE_2D_ENTER_SIDE, KEY_HORIZONTAL_DISTANCE, "100.00")
End Function



'DESCRIPTION TEXTBOX
Private Sub DescTextBox_AfterUpdate()
   SavePointDescEntry DescTextBox, SECTION_COMPASS_RULE_2D_ENTER_SIDE, KEY_POINT_DESC
End Sub

Private Sub DescTextBox_Enter()
   SelectAllText DescTextBox
End Sub

Private Function DefaultDescription() As String
   DefaultDescription = GetSetting(APP_NAME, SECTION_COMPASS_RULE_2D_ENTER_SIDE, KEY_POINT_DESC, "Pipe")
End Function



'CANCEL BUTTON
Private Sub CancelButton_Click()
   Unload Me
End Sub



'ENTER BUTTON
Private Sub EnterButton_Click()
   If IsInsertMode Then
      Dim cornerRecNorthString As String
      cornerRecNorthString = northStringToDecString(CornerRecCoordNorthTextBox)
      Dim cornerRecEastString As String
      cornerRecEastString = eastStringToDecString(CornerRecCoordEastTextBox)
      Dim diagramNorthString As String
      diagramNorthString = northStringToDecString(PlaceDiagCoordNorthTextBox)
      Dim diagramEastString As String
      diagramEastString = eastStringToDecString(PlaceDiagCoordEastTextBox)
      FrmCompassRule.InsertSideShot PointnameTextBox.text, _
                                    DescTextBox.text, _
                                    BSTextBox.text, _
                                    FSTextBox.text, _
                                    HDTextBox.text, _
                                    ShowDropCheckBox.value, _
                                    cornerRecNorthString, _
                                    cornerRecEastString, _
                                    diagramNorthString, _
                                    diagramEastString
      CornerRecCoordNorthTextBox.text = STRING_SPACE
      CornerRecCoordNorthTextBox_AfterUpdate
      CornerRecCoordEastTextBox.text = STRING_SPACE
      CornerRecCoordEastTextBox_AfterUpdate
      PlaceDiagCoordNorthTextBox.text = STRING_SPACE
      PlaceDiagCoordNorthTextBox_AfterUpdate
      PlaceDiagCoordEastTextBox.text = STRING_SPACE
      PlaceDiagCoordEastTextBox_AfterUpdate
      
      IncSSPointName
      PointnameTextBox.SetFocus
   Else
      UpdateSideShot
      Unload Me
   End If
End Sub



'UPDATE AFTER PICK
Private Sub UpdateCheckBox_Click()
   SaveCheckBoxSetting UpdateCheckBox, SECTION_COMPASS_RULE_2D_ENTER_SIDE, KEY_UPDATE_AFTER
End Sub



'CORNER RECORD COORDINATE NORTHING TEXTBOX
Private Sub CornerRecCoordNorthTextBox_AfterUpdate()
   NorthingOrNothing CornerRecCoordNorthTextBox, SECTION_COMPASS_RULE_2D_ENTER_SIDE, KEY_REC_NORTH
   UpdateSideShotIfChecked
End Sub

Private Function DefaultCRNorth() As String
   DefaultCRNorth = DefaultCoordTextSub(SECTION_COMPASS_RULE_2D_ENTER_SIDE, KEY_REC_NORTH)
End Function

Private Function DefaultCoordTextSub(ByVal Section As String, ByVal Key As String) As String
   If IsInsertMode Then
      DefaultCoordTextSub = STRING_SPACE
   Else
      DefaultCoordTextSub = GetSetting(APP_NAME, Section, Key, STRING_SPACE)
   End If
End Function



'CORNER RECORD COORDINATE EASTING TEXTBOX
Private Sub CornerRecCoordEastTextBox_AfterUpdate()
   EastingOrNothing CornerRecCoordEastTextBox, SECTION_COMPASS_RULE_2D_ENTER_SIDE, KEY_REC_EAST
   UpdateSideShotIfChecked
End Sub

Private Function DefaultCREast() As String
   DefaultCREast = DefaultCoordTextSub(SECTION_COMPASS_RULE_2D_ENTER_SIDE, KEY_REC_EAST)
End Function



'PICK CORNER RECORD COORDINATE BUTTON
Private Sub CornerRecCoordPickButton_Click()
   FrmCompassRule.Hide
   Me.Hide
   Dim SetupPoint As Point3d
   Dim sideShotPoint As Point3d
   CalcTheSide SetupPoint, sideShotPoint
   Dim pickTool As New CompassRuleRecCorPrimitive
   pickTool.SideShot = sideShotPoint
   pickTool.Setup = SetupPoint
   CommandState.StartPrimitive pickTool
End Sub



'PLACE DIAGRAM COORDINATE NORTHING TEXTBOX
Private Sub PlaceDiagCoordNorthTextBox_AfterUpdate()
   NorthingOrNothing PlaceDiagCoordNorthTextBox, SECTION_COMPASS_RULE_2D_ENTER_SIDE, KEY_DIAGRAM_NORTH
   UpdateSideShotIfChecked
End Sub

Private Function DefaultPlaceDiagNorth() As String
   DefaultPlaceDiagNorth = DefaultCoordTextSub(SECTION_COMPASS_RULE_2D_ENTER_SIDE, KEY_DIAGRAM_NORTH)
End Function



'PLACE DIAGRAM COORDINATE EASTING TEXTBOX
Private Sub PlaceDiagCoordEastTextBox_AfterUpdate()
   EastingOrNothing PlaceDiagCoordEastTextBox, SECTION_COMPASS_RULE_2D_ENTER_SIDE, KEY_DIAGRAM_EAST
   UpdateSideShotIfChecked
End Sub

Private Function DefaultPlaceDiagEast() As String
   DefaultPlaceDiagEast = DefaultCoordTextSub(SECTION_COMPASS_RULE_2D_ENTER_SIDE, KEY_DIAGRAM_EAST)
End Function



'PICK DIAGRAM COORDINATE BUTTON
Private Sub PlaceDiagCoordPickButton_Click()
   FrmCompassRule.Hide
   Me.Hide
   Dim SetupPoint As Point3d
   Dim sideShotPoint As Point3d
   CalcTheSide SetupPoint, sideShotPoint
   Dim pickTool As New CompassRulePlaceDiaPrimitive
   pickTool.SideShot = sideShotPoint
   pickTool.Setup = SetupPoint
   CommandState.StartPrimitive pickTool
End Sub




'******************************************************************************************************
'******************************************USER FORM EVENTS********************************************
Private Sub UserForm_Initialize()
'MOVE INTO LAST POSITION
   If GetSetting(APP_NAME, SECTION_COMPASS_RULE_2D_ENTER_SIDE, KEY_START_TOP, "") = "" Then
      Me.StartUpPosition = 1
   Else
      Me.StartUpPosition = 0
      Me.Top = CDbl(GetSetting(APP_NAME, SECTION_COMPASS_RULE_2D_ENTER_SIDE, KEY_START_TOP, WINDOW_DEFAULT_TOP))
      Me.Left = CDbl(GetSetting(APP_NAME, SECTION_COMPASS_RULE_2D_ENTER_SIDE, KEY_START_LEFT, WINDOW_DEFAULT_LEFT))
   End If
   
'GET MODE
   IsInsertMode = FrmCompassRule.IsInsertMode

'FILL IN DEFAULT VALUES
   PointnameTextBox.text = DefaultPointName()
   If IsInsertMode Then
      IncSSPointName
   End If
   DescTextBox.text = DefaultDescription()
   BSTextBox.text = DefaultBSAngle()
   FSTextBox.text = DefaultFSAngle()
   HDTextBox.text = DefaultHD()
   ShowDropCheckBox.value = DefaultShowDrop()
   CornerRecCoordNorthTextBox.text = DefaultCRNorth()
   NorthingOrNothing CornerRecCoordNorthTextBox, SECTION_COMPASS_RULE_2D_ENTER_SIDE, KEY_REC_NORTH
   CornerRecCoordEastTextBox = DefaultCREast()
   EastingOrNothing CornerRecCoordEastTextBox, SECTION_COMPASS_RULE_2D_ENTER_SIDE, KEY_REC_EAST
   PlaceDiagCoordNorthTextBox = DefaultPlaceDiagNorth()
   NorthingOrNothing PlaceDiagCoordNorthTextBox, SECTION_COMPASS_RULE_2D_ENTER_SIDE, KEY_DIAGRAM_NORTH
   PlaceDiagCoordEastTextBox = DefaultPlaceDiagEast()
   EastingOrNothing PlaceDiagCoordEastTextBox, SECTION_COMPASS_RULE_2D_ENTER_SIDE, KEY_DIAGRAM_EAST

'INITIALIZE CHECKBOX
   InitializeCheckBox UpdateCheckBox, SECTION_COMPASS_RULE_2D_ENTER_SIDE, KEY_UPDATE_AFTER, True
   
'SET CAPTION IN TITLE BAR, DISABLE CHECKBOX IF INSERT MODE
   If IsInsertMode Then
      Me.Caption = "Insert Side Shot"
      UpdateCheckBox.enabled = False
   Else
      Me.Caption = "Edit Side SHot"
   End If

'FILL IN SETUP POINT NAME
   Dim SetupPoint As Point3d
   Dim BackAzDegrees As Double
   Dim SetupName As String
   FrmCompassRule.AtSetupPoint SetupPoint, BackAzDegrees, SetupName
   SetupPointLabel.Caption = SetupName

'SET MAX LENGTH OF FIELD
   BSTextBox.MaxLength = MAX_LEN_DIR_STRING
   PointnameTextBox.MaxLength = MAX_LEN_POINT_NAME
   FSTextBox.MaxLength = MAX_LEN_DIR_STRING
   HDTextBox.MaxLength = MAX_LEN_DIST_STRING
   DescTextBox.MaxLength = MAX_LEN_POINT_DESC
   CornerRecCoordNorthTextBox.MaxLength = MAX_LEN_COORDINATE_STRING
   CornerRecCoordEastTextBox.MaxLength = MAX_LEN_COORDINATE_STRING
   PlaceDiagCoordNorthTextBox.MaxLength = MAX_LEN_COORDINATE_STRING
   PlaceDiagCoordEastTextBox.MaxLength = MAX_LEN_COORDINATE_STRING
End Sub

Private Sub UserForm_QueryClose(Cancel As Integer, CloseMode As Integer)
'SAVE USERFORM POSITION
   SaveSetting APP_NAME, SECTION_COMPASS_RULE_2D_ENTER_SIDE, KEY_START_TOP, FormatNumber(Me.Top, 0)
   SaveSetting APP_NAME, SECTION_COMPASS_RULE_2D_ENTER_SIDE, KEY_START_LEFT, FormatNumber(Me.Left, 0)
End Sub


Private Sub UserForm_Terminate()
   FrmCompassRule.enabled = True
End Sub

Attribute VB_Name = "FrmEnterTrav"
Attribute VB_Base = "0{D7F89380-A69A-4737-8F79-F29162E8207D}{28ACACF2-E7BB-4D10-8139-D290EA9F0FB7}"
Attribute VB_GlobalNameSpace = False
Attribute VB_Creatable = False
Attribute VB_PredeclaredId = True
Attribute VB_Exposed = False
Attribute VB_TemplateDerived = False
Attribute VB_Customizable = False
















'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit

Private IsInsertMode           As Boolean
Private ForesightExists        As Boolean

Private Const DEFAULT_ELEVATION_STRING As String = "0.00"

'******************************************************************************************************
'*********************************************CONTROLS*************************************************
'POINT NAME TEXTBOX
Private Sub PointNameTextBox_AfterUpdate()
   SavePointNameEntry PointnameTextBox, SECTION_COMPASS_RULE_2D_ENTER_TRAV, KEY_POINTNAME
End Sub

Private Sub PointNameTextBox_Enter()
'SELECT ALL TEXT WHEN FIELD GETS FOCUS
   SelectAllText PointnameTextBox
End Sub

Private Function DefaultPointName() As String
   If IsInsertMode Then
      If ForesightExists Then
         DefaultPointName = ""
      Else
         DefaultPointName = FrmCompassRule.DefaultFSName
      End If
   Else
      DefaultPointName = GetSetting(APP_NAME, SECTION_COMPASS_RULE_2D_ENTER_TRAV, KEY_POINTNAME, "")
   End If
End Function



'DESCRIPTION TEXTBOX
Private Sub DescTextBox_AfterUpdate()
   SavePointDescEntry DescTextBox, SECTION_COMPASS_RULE_2D_ENTER_TRAV, KEY_POINT_DESC
End Sub

Private Sub DescTextBox_Enter()
   SelectAllText DescTextBox
End Sub

Private Function DefaultDescription() As String
   DefaultDescription = GetSetting(APP_NAME, SECTION_COMPASS_RULE_2D_ENTER_TRAV, KEY_POINT_DESC, "Pipe")
End Function



'ELEVATION TEXTBOX
Private Sub ElevationTextBox_AfterUpdate()
   Dim origPrec As Long
   Dim value As Double
   If IsElevationString(ElevationTextBox.text, value, origPrec) Then
      ElevationTextBox.text = FormatNumber(value, origPrec, vbTrue, vbFalse, vbTrue)
   Else
      ElevationTextBox.text = DEFAULT_ELEVATION_STRING
   End If
End Sub

Private Sub ElevationTextBox_Enter()
   SelectAllText ElevationTextBox
End Sub



'BACK SIGHT TEXTBOX
Private Sub BSTextBox_AfterUpdate()
   SaveDeltaEntry BSTextBox, SECTION_COMPASS_RULE_2D_ENTER_TRAV, KEY_BACK_SIGHT_ANGLE, FrmCompassRule.GetAngleStyle
End Sub

Private Sub BSTextBox_Enter()
'SELECT ALL TEXT WHEN FIELD GETS FOCUS
   SelectAllText BSTextBox
End Sub

Private Function DefaultBSAngle() As String
   DefaultBSAngle = GetSetting(APP_NAME, SECTION_COMPASS_RULE_2D_ENTER_TRAV, KEY_BACK_SIGHT_ANGLE, DegreesToAngleString(0#, 4, FrmCompassRule.GetAngleStyle))
End Function



'FORE SIGHT TEXTBOX
Private Sub FSTextBox_AfterUpdate()
   SaveDeltaEntry FSTextBox, SECTION_COMPASS_RULE_2D_ENTER_TRAV, KEY_FORE_SIGHT_ANGLE, FrmCompassRule.GetAngleStyle
End Sub

Private Sub FSTextBox_Enter()
'SELECT ALL TEXT WHEN FIELD GETS FOCUS
   SelectAllText FSTextBox
End Sub

Private Function DefaultFSAngle() As String
   DefaultFSAngle = GetSetting(APP_NAME, SECTION_COMPASS_RULE_2D_ENTER_TRAV, KEY_FORE_SIGHT_ANGLE, DegreesToAngleString(0#, 4, FrmCompassRule.GetAngleStyle))
End Function



'HD TEXTBOX
Private Sub HDTextBox_AfterUpdate()
   SaveNonnegativeEntry HDTextBox, SECTION_COMPASS_RULE_2D_ENTER_TRAV, KEY_HORIZONTAL_DISTANCE, MAX_DISTANCE, MAX_PRECISION_DISTANCE, False, 100#
End Sub

Private Sub HDTextBox_Enter()
'SELECT ALL TEXT WHEN FIELD GETS FOCUS
   SelectAllText HDTextBox
End Sub

Private Function DefaultHD() As String
   DefaultHD = GetSetting(APP_NAME, SECTION_COMPASS_RULE_2D_ENTER_TRAV, KEY_HORIZONTAL_DISTANCE, "100.00")
End Function



'FS POINT NAME TEXTBOX
Private Sub FSNameTextBox_AfterUpdate()
   SavePointNameEntry FSNameTextBox, SECTION_COMPASS_RULE_2D_ENTER_TRAV, KEY_FS_NAME
End Sub

Private Sub FSNameTextBox_Enter()
   SelectAllText FSNameTextBox
End Sub

Private Function DefaultFSPointName() As String
   DefaultFSPointName = FrmCompassRule.DefaultFSName
End Function

Private Sub IncFSPointName()
   Dim formattedName As String
   If (Not ForesightExists) And IsPointnameString(PointnameTextBox.text, formattedName) Then
      FSNameTextBox.text = IncPointName(formattedName)
      FSNameTextBox_AfterUpdate
   End If
   If ForesightExists Then
      FSNameTextBox.text = FrmCompassRule.DefaultFSName
      FSNameTextBox_AfterUpdate
   End If
End Sub



'CANCEL BUTTON
Private Sub CancelButton_Click()
   Unload Me
End Sub



'ENTER BUTTON
Private Sub EnterButton_Click()
   If IsInsertMode Then
'ENTER NEW TRAVERSE
      StoFutureTravName
      FrmCompassRule.InsertTraverse PointnameTextBox.text, _
                                    DescTextBox.text, _
                                    BSTextBox.text, _
                                    FSTextBox.text, _
                                    HDTextBox.text, _
                                    ElevationTextBox.text, _
                                    PlottElCheckBox.value
'RESET TO DEFAULT ELEVATION
      ElevationTextBox.text = DEFAULT_ELEVATION_STRING
'RESET PLOT ELEV. CHECKBOX
      PlottElCheckBox.value = False

'SUGGEST BACK SIGHT ANGLE
'NEED TO USE TEMP OR IT DOESN'T WORK, DON'T KNOW WHY
      Dim temp As String
      temp = FSTextBox.text
      If ReverseDirText(temp) Then
         BSTextBox.text = temp
         BSTextBox_AfterUpdate
      End If

'RESET TO POINT NAME
      ForesightExists = FrmCompassRule.ForesightExists
      If ForesightExists Then
         PointnameTextBox.text = ""
      Else
         PointnameTextBox.text = FSNameTextBox.text
         PointNameTextBox_AfterUpdate
      End If
      IncFSPointName
      PointnameTextBox.SetFocus
   Else
'ENTER REVISED TRAVERSE
      StoFutureTravName
      FrmCompassRule.EditTraverse PointnameTextBox.text, _
                                  DescTextBox.text, _
                                  BSTextBox.text, _
                                  FSTextBox.text, _
                                  HDTextBox.text, _
                                  ElevationTextBox.text, _
                                  PlottElCheckBox.value
'QUIT END FORM
      Unload Me
   End If
End Sub

Private Sub StoFutureTravName()
   If Not ForesightExists Then
      FrmCompassRule.LastFSName = FSNameTextBox.text
   End If
End Sub



'******************************************************************************************************
'******************************************USER FORM EVENTS********************************************
Private Sub UserForm_Initialize()
'MOVE INTO LAST POSITION
   If GetSetting(APP_NAME, SECTION_COMPASS_RULE_2D_ENTER_TRAV, KEY_START_TOP, "") = "" Then
      Me.StartUpPosition = 1
   Else
      Me.StartUpPosition = 0
      Me.Top = CDbl(GetSetting(APP_NAME, SECTION_COMPASS_RULE_2D_ENTER_TRAV, KEY_START_TOP, WINDOW_DEFAULT_TOP))
      Me.Left = CDbl(GetSetting(APP_NAME, SECTION_COMPASS_RULE_2D_ENTER_TRAV, KEY_START_LEFT, WINDOW_DEFAULT_LEFT))
   End If
   
'CHECK IF LAST TRAVERSE IN LIST
   ForesightExists = FrmCompassRule.ForesightExists

'GET MODE
   IsInsertMode = FrmCompassRule.IsInsertMode

'FILL IN DEFAULT VALUES
   PointnameTextBox.text = DefaultPointName()
   DescTextBox.text = DefaultDescription()
   DescTextBox_AfterUpdate
   BSTextBox.text = DefaultBSAngle()
   BSTextBox_AfterUpdate
   FSTextBox.text = DefaultFSAngle()
   FSTextBox_AfterUpdate
   HDTextBox.text = DefaultHD()
   HDTextBox_AfterUpdate
   IncFSPointName

   If IsInsertMode Then
      ElevationTextBox.text = DEFAULT_ELEVATION_STRING
   Else
      Dim travElString As String
      travElString = GetSetting(APP_NAME, SECTION_COMPASS_RULE_2D_ENTER_TRAV, KEY_ELEVATION, "")
      If travElString = "" Then
         ElevationTextBox.text = DEFAULT_ELEVATION_STRING
         PlottElCheckBox.value = False
      Else
         Dim elevString As String
         Dim plotElev As Boolean
         FrmCompassRule.ParseTravElString travElString, plotElev, elevString
         ElevationTextBox.text = elevString
         PlottElCheckBox.value = plotElev
      End If
   End If

'SET CAPTION IN TITLE BAR
   If IsInsertMode Then
      Me.Caption = "Insert Traverse"
   Else
      Me.Caption = "Edit Traverse"
   End If

'INITIALIZE FS POINTNAME TEXTBOX STATE
   FSPointnameState

'SET MAX LENGTH OF FIELDS
   FSNameTextBox.MaxLength = MAX_LEN_POINT_NAME
   PointnameTextBox.MaxLength = MAX_LEN_POINT_NAME
   DescTextBox.MaxLength = MAX_LEN_POINT_DESC
   BSTextBox.MaxLength = MAX_LEN_DIR_STRING
   FSTextBox.MaxLength = MAX_LEN_DIR_STRING
   HDTextBox.MaxLength = MAX_LEN_DIST_STRING
   ElevationTextBox.MaxLength = MAX_LEN_ELEV_STRING
End Sub



Private Sub UserForm_QueryClose(Cancel As Integer, CloseMode As Integer)
'SAVE USERFORM POSITION
   SaveSetting APP_NAME, SECTION_COMPASS_RULE_2D_ENTER_TRAV, KEY_START_TOP, FormatNumber(Me.Top, 2)
   SaveSetting APP_NAME, SECTION_COMPASS_RULE_2D_ENTER_TRAV, KEY_START_LEFT, FormatNumber(Me.Left, 2)
End Sub



Private Sub UserForm_Terminate()
   FrmCompassRule.enabled = True
End Sub



'******************************************************************************************************
'************************************************STATES************************************************
Private Sub FSPointnameState()
   Dim enabledState As Boolean
   enabledState = Not ForesightExists
   FSPointnameLabel.enabled = enabledState
   FSNameTextBox.enabled = enabledState
   FSNameTextBox.BackColor = BackOLE_COLOR(enabledState)
End Sub

Attribute VB_Name = "FrmHelp"
Attribute VB_Base = "0{B06B55B8-CBD8-4CB5-B786-1FD0F85A3D79}{242FDCF0-3CD0-4E37-BB28-12A85D4E290C}"
Attribute VB_GlobalNameSpace = False
Attribute VB_Creatable = False
Attribute VB_PredeclaredId = True
Attribute VB_Exposed = False
Attribute VB_TemplateDerived = False
Attribute VB_Customizable = False
















'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.


Private Sub UserForm_Initialize()
   Dim StatementString As String
   StatementString = "This routine is for entering side shots using a coordinate file.  It is unique and usage is not entirely obvious." & vbNewLine & vbNewLine
   StatementString = StatementString & "The first thing to do is load coordinates from a file.  The file should be your standard ASCII PNEZD file which "
   StatementString = StatementString & "contains the coordinates of your traverses and side shots.  The actual coordinates in your file might "
   StatementString = StatementString & "be a little different than the ones generated by the compass rule program, so it's required you have the "
   StatementString = StatementString & "traverse values too, otherwise the program could just inverse the values and use that to enter the side shots.  "
   StatementString = StatementString & "Once you've loaded the file, the points should be listed in the box.  If they aren't listed, something is wrong.  " & vbNewLine & vbNewLine
   StatementString = StatementString & "The side shots get entered for the traverse that is selected in the Traverse listbox on the Entry tab of the Compass Rule 2D "
   StatementString = StatementString & "window.  Don't worry.  If the correct traverse isn't the one selected, use the Close button to close the dialog box instead "
   StatementString = StatementString & "of the X in the corner and the points should remain in the listbox when you return to it.  Once you've closed the dialog box, you "
   StatementString = StatementString & "can select the traverse you want the points to be entered for.  This is an important point to remember because you probably are going to "
   StatementString = StatementString & "enter side shots for several traverses." & vbNewLine & vbNewLine
   StatementString = StatementString & "Next, you enter your occupied coordinate.  It should be for the same point you've selected in the traverse listbox.  To make things easier, "
   StatementString = StatementString & "you can just select in the coordinate from the ones you've loaded and press the Get Occupied Point button.  This will fill in the Northing and "
   StatementString = StatementString & "Easting fields.  Of course, you can also just key them in.  " & vbNewLine & vbNewLine
   StatementString = StatementString & "The back sight azimuth field is for the azimuth from the occupied point you just entered to the point you used to back sight for this setup.  "
   StatementString = StatementString & "It must be the same point as the one used in the Traverse listbox.  An azimuth should be filled in the field, but it might be a little different "
   StatementString = StatementString & "or it could be for a different occupied point.  You need to inspect it.  At this point, if you select the point you used for back sight, the "
   StatementString = StatementString & "Calculate Inverse button should activate.  You can press this button and it will show you the inverse and a couple of additional buttons will appear. "
   StatementString = StatementString & "The Cancel button will return the window to its previous state and the Enter button will enter the newly calculated back sight azimuth into the field.  "
   StatementString = StatementString & "You choose which is better for you.  " & vbNewLine & vbNewLine
   StatementString = StatementString & "The final step is for you to select points you want inserted.  It's a multiselect listbox, so you can select more than one.  Once you've done that, "
   StatementString = StatementString & "you just press the Apply button and the side shots will be added.  Note that the ones just added were removed from the list.  " & vbNewLine & vbNewLine
   StatementString = StatementString & "You likely have side shots from more than one traverse.  Use the Close button to close the window so that you can access the Compass Rule 2D window.  Select "
   StatementString = StatementString & "the traverse you want to add side shots for and press the Ins. by Coord. button to get back.  The remaining list of points should still be there.  "
   StatementString = StatementString & "Just enter the new occupied point and the new back sight azimuth if needed, select the side shots and apply.  Simple!"
'   StatementString = StatementString & ""
'   StatementString = StatementString & ""
'   StatementString = StatementString & ""
'   StatementString = StatementString & ""
'   StatementString = StatementString & ""
'   StatementString = StatementString & ""
'   StatementString = StatementString & ""
   StatementTextBox.text = StatementString
End Sub

Attribute VB_Name = "FrmInsByCoord"
Attribute VB_Base = "0{C672789C-3529-4C32-986F-9E0BDE50D654}{F65C0BFD-BFE6-4E7D-AEC3-1CF7F3B5B5B2}"
Attribute VB_GlobalNameSpace = False
Attribute VB_Creatable = False
Attribute VB_PredeclaredId = True
Attribute VB_Exposed = False
Attribute VB_TemplateDerived = False
Attribute VB_Customizable = False
















'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit



Private Function LoadCoordinateFile(filename As String, ByRef CoordinateListBox As ListBox) As Boolean
'LOAD LOT FILE INTO USERFORM, RETURNS TRUE IF SUCCESSFUL

'INITIALIZE RETURN VALUE
   LoadCoordinateFile = False

'JUMP ON ERROR
   On Error GoTo errhnd

'OPEN FILE
   Dim FFILE As Long
   FFILE = FreeFile
   Open filename For Input As #FFILE

'READ FILE ONE LINE AT A TIME
   Dim LineNum As Long
   LineNum = 0
   Dim TextLine As String
   Dim OpenFileErrors As Long
   OpenFileErrors = 0
   Do While EOF(FFILE) = False
      Line Input #FFILE, TextLine
      LineNum = LineNum + 1
      Dim pointName As String
      Dim northing As String
      Dim easting As String
      Dim elevation As String
      Dim description As String
      If ParsePointString(TextLine, pointName, northing, easting, elevation, description) Then
         LoadCoordinateFile = True
         Dim RowNum As Long
         RowNum = CoordinateListBox.ListCount
         Dim formattedName As String
         If IsPointnameString(pointName, formattedName) Then
            pointName = formattedName
         Else
            pointName = "invalid"
         End If
         CoordinateListBox.AddItem pointName
         CoordinateListBox.List(RowNum, 1) = northing
         CoordinateListBox.List(RowNum, 2) = easting
         CoordinateListBox.List(RowNum, 3) = elevation
         If Len(description) > MAX_LEN_POINT_DESC Then
            description = Left(description, MAX_LEN_POINT_DESC)
         End If
         CoordinateListBox.List(RowNum, 4) = description
      Else
         Close #FFILE
         GoTo errhnd
      End If
   Loop

'CLOSE FILE
   Close #FFILE
   
'CHECK IF ANY POINTS LOADED
   If CoordinateListBox.ListCount < 1 Then
      GoTo errhnd
   End If
      
'JUMP PAST ERROR CODE
   Exit Function

'ERROR HANDLING
errhnd:
   LoadCoordinateFile = False
   ErrorMess Err.Number
   Err.Clear
End Function


'*************************************************************************************************************
'**********************************************USERFORM EVENTS************************************************
Private Sub UserForm_Activate()
'MAKE MAIN WINDOW MODAL
   FrmCompassRule.enabled = False

'SET BACK SIGHT
   BSAzTextBox.text = DefaultBSAngle()
   updateButtonStates

'UPDATE CAPTION
   updateCap
End Sub



Private Sub UserForm_Deactivate()
   FrmCompassRule.enabled = True
End Sub



Private Sub UserForm_QueryClose(Cancel As Integer, CloseMode As Integer)
'SAVE USERFORM POSITION
   SaveSetting APP_NAME, SECTION_SIDE_SHOT_BY_COORD, KEY_START_TOP, FormatNumber(Me.Top, 2)
   SaveSetting APP_NAME, SECTION_SIDE_SHOT_BY_COORD, KEY_START_LEFT, FormatNumber(Me.Left, 2)
End Sub



Private Sub UserForm_Initialize()
'MOVE INTO LAST POSITION
   If GetSetting(APP_NAME, SECTION_SIDE_SHOT_BY_COORD, KEY_START_TOP, "") = "" Then
      Me.StartUpPosition = 1
   Else
      Me.StartUpPosition = 0
      Me.Top = CDbl(GetSetting(APP_NAME, SECTION_SIDE_SHOT_BY_COORD, KEY_START_TOP, WINDOW_DEFAULT_TOP))
      Me.Left = CDbl(GetSetting(APP_NAME, SECTION_SIDE_SHOT_BY_COORD, KEY_START_LEFT, WINDOW_DEFAULT_LEFT))
   End If
   
'SET SIZE OF COURSESLISTBOX COLUMNS
   CoordinateListBox.ColumnCount = 5
   Dim ColumnWidthString As String
   ColumnWidthString = FormatNumber(1# * Column_Width_Multiplier, 2) & " in; " & _
                       FormatNumber(1# * Column_Width_Multiplier, 2) & " in; " & _
                       FormatNumber(1# * Column_Width_Multiplier, 2) & " in; " & _
                       FormatNumber(0.5 * Column_Width_Multiplier, 2) & " in; " & _
                       FormatNumber(1.3 * Column_Width_Multiplier, 2) & " in"
   CoordinateListBox.ColumnWidths = ColumnWidthString

'INITIALIZE BS TEXTBOX
   BSAzTextBox.text = DefaultBSAngle()

'INITIALIZE BUTTON STATES
   updateButtonStates
   toggleMain True

'SET COMMAND NAME IN TITLE BLOCK
   updateCap
End Sub



Private Sub UserForm_Terminate()
   FrmCompassRule.enabled = True
End Sub



'*************************************************************************************************************
'*********************************************CONTROLS********************************************************
'HELP BUTTON
Private Sub HelpButton_Click()
   FrmHelp.Show
End Sub



'CALCULATE INVERSE BUTTON
Private Sub InvButton_Click()
   Dim origPrec As Long
   Dim theScaler As Double
   If IsNorthingString(NorthingTextBox.text, theScaler, origPrec) Then
      Dim startPt As Point3d
      startPt.Y = theScaler
   Else
      toggleMain False
      Exit Sub
   End If
   If IsEastingString(EastingTextBox.text, theScaler, origPrec) Then
      startPt.X = theScaler
   Else
      toggleMain False
      Exit Sub
   End If
   
   Dim ListboxIndex As Long
   ListboxIndex = getSelectedIndex(CoordinateListBox)
   If ListboxIndex = -1 Then
      Dim selNorth As String
      Dim selEast As String
      selNorth = ""
      selEast = ""
   Else
      selNorth = CoordinateListBox.List(ListboxIndex, 1)
      selEast = CoordinateListBox.List(ListboxIndex, 2)
   End If

   If Not IsNumeric(selNorth) Then
      toggleMain False
      Exit Sub
   End If
   If Not IsNumeric(selEast) Then
      toggleMain False
      Exit Sub
   End If

'FILL IN DISPLAYS
   Dim endPt As Point3d
   endPt.X = CDbl(selEast)
   endPt.Y = CDbl(selNorth)
   Dim sAzDegrees As Double
   Dim dist As Double
   Inverse startPt, endPt, sAzDegrees, dist
   InvAzLabel.Caption = SAzToAzimuthStr(sAzDegrees, 4, FrmCompassRule.GetAngleStyle())
   InvDisLabel.Caption = FormatNumber(dist, 2, vbTrue, vbFalse, vbTrue)
   toggleMain False
End Sub



'BACK SIGHT TEXTBOX
Private Sub BSAzTextBox_AfterUpdate()
   Dim origPrec As Long
   Dim degPart As Long
   Dim minPart As Long
   Dim secPart As Double
   If IsDeltaString(BSAzTextBox.text, origPrec, degPart, minPart, secPart) Then
      Dim angleInDegrees As Double
      angleInDegrees = DmsToDec(degPart, minPart, secPart)
      BSAzTextBox.text = DegreesToAngleString(angleInDegrees, origPrec, FrmCompassRule.GetAngleStyle())
   Else
      BSAzTextBox.text = DefaultBSAngle()
      Beep
   End If
End Sub

Private Sub BSAzTextBox_Enter()
   SelectAllText BSAzTextBox
End Sub

Private Function DefaultBSAngle() As String
   DefaultBSAngle = GetSetting(APP_NAME, _
                               SECTION_COMPASS_RULE_2D_ENTER_SIDE, _
                               KEY_BACK_SIGHT_ANGLE, _
                               DegreesToAngleString(0, 4, FrmCompassRule.GetAngleStyle()))
End Function



'CANCEL BUTTON
Private Sub CancelButton_Click()
   toggleMain True
End Sub



'ENTER BUTTON
Private Sub EnterButton_Click()
   BSAzTextBox = InvAzLabel.Caption
   selectionAll False, CoordinateListBox
   toggleMain True
End Sub



'NORTHING TEXTBOX
Private Sub NorthingTextbox_AfterUpdate()
   Dim theScaler As Double
   Dim origPrec As Long
   If IsNorthingString(NorthingTextBox.text, theScaler, origPrec) Then
      NorthingTextBox.text = DoubleToNorthingString(theScaler, origPrec)
   Else
      NorthingTextBox.text = ""
   End If
   updateButtonStates
End Sub



'EASTING TEXTBOX
Private Sub EastingTextbox_AfterUpdate()
   Dim theScaler As Double
   Dim origPrec As Long
   If IsEastingString(EastingTextBox.text, theScaler, origPrec) Then
      EastingTextBox.text = DoubleToEastingString(theScaler, origPrec)
   Else
      EastingTextBox.text = ""
   End If
   updateButtonStates
End Sub



'GET OCCUPIED POINT BUTTON
Private Sub GetOccButton_Click()
   Dim ListboxIndex As Long
   ListboxIndex = getSelectedIndex(CoordinateListBox)
   If ListboxIndex = -1 Then
      Exit Sub
   End If
   NorthingTextBox.text = CoordinateListBox.List(ListboxIndex, 1)
   NorthingTextbox_AfterUpdate
   EastingTextBox.text = CoordinateListBox.List(ListboxIndex, 2)
   EastingTextbox_AfterUpdate
   CoordinateListBox.Selected(ListboxIndex) = False
   updateButtonStates
End Sub



'COORDINATE LISTBOX
Private Sub CoordinateListBox_Change()
   updateButtonStates
End Sub



'CLOSE BUTTON
Private Sub CloseButton_Click()
   FrmCompassRule.enabled = True
   NorthingTextBox.text = ""
   EastingTextBox.text = ""
   updateButtonStates
   Me.Hide
End Sub



'CLEAR BUTTON
Private Sub ClearButton_Click()
   CoordinateListBox.Clear
   updateButtonStates
End Sub



'LOAD BUTTON
Private Sub LoadButton_Click()
   Dim LastFullFileName As String
   LastFullFileName = GetSetting(APP_NAME, SECTION_SIDE_SHOT_BY_COORD, KEY_FILENAME_COORDINATE, "C:\Input.asc")
   Dim ToOpenFileName As String
   If OpenCoordFilename(LastFullFileName, ToOpenFileName) Then
      SaveSetting APP_NAME, SECTION_SIDE_SHOT_BY_COORD, KEY_FILENAME_COORDINATE, ToOpenFileName
      If Not LoadCoordinateFile(ToOpenFileName, CoordinateListBox) Then
         MsgBox "problem with file"
      End If
   End If
   updateButtonStates
End Sub



'SELECT ALL BUTTON
Private Sub SelectAllButton_Click()
   selectionAll True, CoordinateListBox
   updateButtonStates
End Sub



'UNSELECT ALL BUTTON
Private Sub UnselectAllButton_Click()
   selectionAll False, CoordinateListBox
   updateButtonStates
End Sub



'APPLY BUTTON
Private Sub ApplyButton_Click()
   Dim theScaler As Double
   Dim origPrec As Long
   Dim startPt As Point3d
   If IsEastingString(EastingTextBox.text, theScaler, origPrec) Then
      startPt.X = theScaler
   Else
      updateButtonStates
      MsgBox "invalid Easting"
      Exit Sub
   End If
   If IsNorthingString(NorthingTextBox.text, theScaler, origPrec) Then
      startPt.Y = theScaler
   Else
      updateButtonStates
      MsgBox "invalid Northing"
      Exit Sub
   End If

   Dim i As Long
   For i = 0 To CoordinateListBox.ListCount - 1
      If CoordinateListBox.Selected(i) Then
         Dim selName As String
         selName = CoordinateListBox.List(i, 0)
         Dim selNorth As String
         selNorth = CoordinateListBox.List(i, 1)
         Dim selEast As String
         selEast = CoordinateListBox.List(i, 2)
         Dim selDesc As String
         selDesc = CoordinateListBox.List(i, 4)
         Dim endPt As Point3d
         endPt.X = CDbl(selEast)
         endPt.Y = CDbl(selNorth)
         Dim sAzDegrees As Double
         Dim dist As Double
         Inverse startPt, endPt, sAzDegrees, dist
         Dim DistString As String
         DistString = FormatNumber(dist, 2, vbTrue, vbFalse, vbTrue)
         Dim aziString As String
         aziString = SAzToAzimuthStr(sAzDegrees, 4, FrmCompassRule.GetAngleStyle())
         If CDbl(DistString) > 0 Then
            FrmCompassRule.insertSideSub selName, _
                                         selDesc, _
                                         BSAzTextBox.text, _
                                         aziString, _
                                         DistString, _
                                         True, _
                                         STRING_SPACE, _
                                         STRING_SPACE, _
                                         STRING_SPACE, _
                                         STRING_SPACE
         End If
      End If
   Next i
   For i = CoordinateListBox.ListCount - 1 To 0 Step -1
      If CoordinateListBox.Selected(i) Then
         CoordinateListBox.RemoveItem i
      End If
   Next i
   FrmCompassRule.insertSideUpdateSub
   updateButtonStates
End Sub



'*************************************************************************************************************
'**********************************************CONTROL STATES*************************************************
Private Sub updateButtonStates()
   If CoordinateListBox.ListCount <= 0 Then
      GetOccButton.enabled = False
      ApplyButton.enabled = False
      InvButton.enabled = False
      Exit Sub
   End If
   
   Dim count As Long
   count = 0
   Dim i As Long
   For i = 0 To CoordinateListBox.ListCount - 1
      If CoordinateListBox.Selected(i) Then
         count = count + 1
      End If
      If count > 1 Then
         Exit For
      End If
   Next i
   If count = 0 Then
      GetOccButton.enabled = False
      ApplyButton.enabled = False
      InvButton.enabled = False
   End If
   
   If count = 1 Then
      GetOccButton.enabled = True
   Else
      GetOccButton.enabled = False
   End If
   
   Dim occupiedIsGood As Boolean
   Dim theScaler As Double
   Dim origPrec As Long
   occupiedIsGood = IsNorthingString(NorthingTextBox.text, theScaler, origPrec) _
                 And IsEastingString(EastingTextBox, theScaler, origPrec)
   
   If count = 1 And occupiedIsGood Then
      InvButton.enabled = True
   Else
      InvButton.enabled = False
   End If
   
   If count >= 1 And occupiedIsGood Then
      ApplyButton.enabled = True
   Else
      ApplyButton.enabled = False
   End If
End Sub



Private Sub toggleMain(mainOn As Boolean)
   InvButton.enabled = mainOn
   NorthingTextBox.enabled = mainOn
   EastingTextBox.enabled = mainOn
   GetOccButton.enabled = mainOn
   CoordinateListBox.enabled = mainOn
   closeButton.enabled = mainOn
   ClearButton.enabled = mainOn
   LoadButton.enabled = mainOn
   SelectAllButton.enabled = mainOn
   UnselectAllButton.enabled = mainOn
   ApplyButton.enabled = mainOn
   Dim inverseControlsState As Boolean
   inverseControlsState = Not mainOn
   AzLabel.Visible = inverseControlsState
   InvAzLabel.Visible = inverseControlsState
   DisLabel.Visible = inverseControlsState
   InvDisLabel.Visible = inverseControlsState
   CancelButton.Visible = inverseControlsState
   EnterButton.Visible = inverseControlsState
End Sub



'*************************************************************************************************************
'***********************************************DISPLAY*******************************************************
Private Sub updateCap()
'FILL IN SETUP POINT NAME
   Dim SetupPoint As Point3d
   Dim BackSAzDegrees As Double
   Dim SetupName As String
   FrmCompassRule.AtSetupPoint SetupPoint, BackSAzDegrees, SetupName
   
'SET COMMAND NAME IN TITLE BLOCK
   Me.Caption = COMMAND_NAME_SIDE_BY_COORD & " - " & SetupName
End Sub

Attribute VB_Name = "FrmLabelCoord"
Attribute VB_Base = "0{58239ECC-4F75-4D62-99D9-560CC4BF29EB}{E4B570AA-F99A-47E7-8670-45E14A5B80D3}"
Attribute VB_GlobalNameSpace = False
Attribute VB_Creatable = False
Attribute VB_PredeclaredId = True
Attribute VB_Exposed = False
Attribute VB_TemplateDerived = False
Attribute VB_Customizable = False
















'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

'GENERAL NOTES:
'PROGRAM ASSUMES MASTER UNIT IS FOOT OR SURVEY FOOT, SOME KIND OF FOOT

Option Explicit

Private OkayToClose As Boolean

Private Const TEXTBOX_ELEVATION     As Integer = 1
Private Const TEXTBOX_POINT_DESC    As Integer = 2
Private Const TEXTBOX_POINT_NAME    As Integer = 3

Private textBoxNumber As Integer

'*************************************************************************************************************
'**********************************INTERFACE FOR PICKING TEXT ROUTINE*****************************************
Public Sub EnterText(ByVal Entry As String)
   Select Case textBoxNumber
      Case TEXTBOX_POINT_NAME
         Dim formattedString As String
         If IsPointnameString(Entry, formattedString) Then
            FrmLabelCoord.PointNumTextBox.text = formattedString
            FrmLabelCoord.PointNumTextBox_afterUpdate
         End If
      Case TEXTBOX_ELEVATION
         Dim floatString As String
         If StrToFloatStr(Entry, floatString) Then
            UseElevTextBox.text = floatString
            UseElevTextBox_AfterUpdate
         End If
      Case TEXTBOX_POINT_DESC
         If Len(Entry) > MAX_LEN_POINT_DESC Then
            Entry = Mid(Entry, 1, MAX_LEN_POINT_DESC)
         End If
         DescTextBox.text = Entry
         DescTextBox_AfterUpdate
   End Select
End Sub



'*************************************************************************************************************
'*******************************FOR COORDINATING WITH ILOCATE AND IPRIMITIVE CLASSES**************************
Public Sub NotifyOfClosing()
   If OkayToClose Then
      Unload Me
   End If
End Sub



Public Sub NotifyOfOpenning()
   OkayToClose = True
End Sub



Public Sub SetNotOkayToClose()
   OkayToClose = False
End Sub



Public Function GetElPrec() As Long
   GetElPrec = CLng(ElPrecComboBox.text)
End Function



Public Function GetTextTemp() As TextElement
'TO INTERFACE WITH TEXT PLACING ROUTINE
   Set GetTextTemp = CreateTextTemplate(SECTION_SAMPLE, _
                                        FontComboBox, _
                                        KEY_FONT, _
                                        LevelComboBox, _
                                        KEY_LEVEL, _
                                        WeightComboBox, _
                                        ColorComboBox, _
                                        StyleComboBox, _
                                        KEY_STYLE, , _
                                        msdTextJustificationRightCenter)
End Function



'*************************************************************************************************************
'*********************************************LABEL TAB*******************************************************
'PRECISION COMBOBOX
Private Sub PrecisionComboBox_Change()
   SaveSetting APP_NAME, SECTION_LABEL_COORD, KEY_PRECISION, FormatNumber(PrecisionComboBox.listIndex, 0)
End Sub



'ELEVATION PRECISION COMBOBOX
Private Sub ElPrecComboBox_Change()
   SaveSetting APP_NAME, SECTION_LABEL_COORD, KEY_PRECISION_ELEV, FormatNumber(ElPrecComboBox.listIndex, 0)
   UseElevTextBox_AfterUpdate
End Sub



'OVERRIDE PICKED ELEVATION CHECKBOX
Private Sub OverrideCheckBox_Click()
   SaveCheckBoxSetting OverrideCheckBox, SECTION_LABEL_COORD, KEY_OVERRIDE
   ControlStates
End Sub



'USE ELEVATION TEXTBOX
Public Sub UseElevTextBox_AfterUpdate()
   SaveElevationEntry UseElevTextBox, SECTION_LABEL_COORD, KEY_OVERRIDE_ELEVATION, GetElPrec()
End Sub



'PICK ELEVATION BUTTON
Private Sub PickElButton_Click()
   SetNotOkayToClose
   textBoxNumber = TEXTBOX_ELEVATION
   Dim myTool As New LabelCoordLocateText
   Set myTool.hostForm = Me
   CommandState.StartLocate myTool
End Sub



'DESCRIPTION TEXTBOX
Private Sub DescTextBox_AfterUpdate()
   SaveSetting APP_NAME, SECTION_LABEL_COORD, KEY_DESCRIPTION, DescTextBox.text
End Sub

Private Sub DescTextBox_Enter()
   SelectAllText DescTextBox
End Sub



'PICK DESCRIPTION BUTTON
Private Sub PickButton_Click()
   SetNotOkayToClose
   textBoxNumber = TEXTBOX_POINT_DESC
   Dim myTool As New LabelCoordLocateText
   Set myTool.hostForm = Me
   CommandState.StartLocate myTool
End Sub



'SHOW ELEVATION CHECKBOX
Private Sub ElevationCheckBox_Click()
   SaveCheckBoxSetting ElevationCheckBox, SECTION_LABEL_COORD, KEY_SHOW_ELEVATION
   ControlStates
End Sub



'SHOW DESCRIPTION CHECKBOX
Private Sub ShowDescCheckBox_Click()
   SaveCheckBoxSetting ShowDescCheckBox, SECTION_LABEL_COORD, KEY_SHOW_DESCRIPTION
   ControlStates
End Sub



'SHOW N,E CHECKBOX
Private Sub NEandNumCheckBox_Click()
   SaveCheckBoxSetting NEandNumCheckBox, SECTION_LABEL_COORD, KEY_SHOW_NE
End Sub



'ALIGN LEFT RADIO BUTTON
Private Sub AlignLeftOption_Click()
   SaveSetting APP_NAME, SECTION_LABEL_COORD, KEY_OPTION_ALIGN, OPTION_ALIGN_LEFT
End Sub



'ALIGN RIGHT RADIO BUTTON
Private Sub AlignRightOption_Click()
   SaveSetting APP_NAME, SECTION_LABEL_COORD, KEY_OPTION_ALIGN, OPTION_ALIGN_RIGHT
End Sub



'OUTPUT TO FILE CHECKBOX
Private Sub OutFileCheckBox_Click()
   SaveCheckBoxSetting OutFileCheckBox, SECTION_LABEL_COORD, KEY_OUTPUT_TO_FILE
   ControlStates
End Sub



'OPEN FILE BUTTON
Private Sub OpenButton_Click()
'DISABLE USERFORM
   Me.enabled = False

'OPEN EXISTING COORDINATE FILE
   Dim CurrentFullFileName As String
   CurrentFullFileName = GetSetting(APP_NAME, SECTION_LABEL_COORD, KEY_FILENAME, "")
   Dim CoordFilename As String
   If OpenCoordFilename(CurrentFullFileName, CoordFilename) Then
      SaveSetting APP_NAME, SECTION_LABEL_COORD, KEY_FILENAME, CoordFilename
'UPDATE TEXT BOX
      Dim xSplit2 As Variant
      xSplit2 = Split(CoordFilename, "\")
      FilenameLabel.Caption = xSplit2(UBound(xSplit2))
   End If

'REENABLE USERFORM
   Me.enabled = True
End Sub



'NEW FILE BUTTON
Private Sub NewButton_Click()
'DISABLE USERFORM
   Me.enabled = False

'CREATE NEW COORDINATE FILE
   Dim CurrentFullFileName As String
   CurrentFullFileName = GetSetting(APP_NAME, SECTION_LABEL_COORD, KEY_FILENAME, "")
   Dim CoordFilename As String
   If GetNewCoordFilename(CurrentFullFileName, CoordFilename) Then
      CreateNewCoordinateFile CoordFilename
      SaveSetting APP_NAME, SECTION_LABEL_COORD, KEY_FILENAME, CoordFilename
'UPDATE TEXT BOX
      Dim xSplit2 As Variant
      xSplit2 = Split(CoordFilename, "\")
      FilenameLabel.Caption = xSplit2(UBound(xSplit2))
   End If

'REENABLE USERFORM
   Me.enabled = True
End Sub



'POINTNAME TEXTBOX
Public Sub PointNumTextBox_afterUpdate()
   SavePointNameEntry PointNumTextBox, SECTION_LABEL_COORD, KEY_POINTNAME
End Sub

Private Sub PointNumTextBox_Enter()
   SelectAllText PointNumTextBox
End Sub



'PICK POINTNAME BUTTON
Private Sub PickPointButton_Click()
   SetNotOkayToClose
   textBoxNumber = TEXTBOX_POINT_NAME
   Dim myTool As New LabelCoordLocateText
   Set myTool.hostForm = Me
   CommandState.StartLocate myTool
End Sub



'*************************************************************************************************************
'**********************************************SETTINGS TAB***************************************************
'COLOR COMBOBOX
Private Sub ColorComboBox_AfterUpdate()
   ColorBoxOnUpdate ColorComboBox, SECTION_LABEL_COORD, KEY_COLOR
End Sub

'COLOR PICKER
Private Sub ChooseColorButton_Click()
   Dim MyColor As String
   If ChooseMyTableColor(MyColor) Then
      ColorComboBox.text = MyColor
      ColorComboBox_AfterUpdate
   End If
End Sub



'LEVEL COMBOBOX
Private Sub LevelComboBox_AfterUpdate()
   If Not LevelBoxOnUpdate(LevelComboBox, SECTION_LABEL_COORD, KEY_LEVEL) Then
      PopulateLevelBox LevelComboBox, SECTION_LABEL_COORD, KEY_LEVEL
      Beep
   End If
End Sub

'STYLE COMBOBOX
Private Sub StyleComboBox_AfterUpdate()
   If Not LineStyleBoxOnUpdate(StyleComboBox, SECTION_LABEL_COORD, KEY_STYLE) Then
      PopulateLinestyleBox StyleComboBox, SECTION_LABEL_COORD, KEY_STYLE
      Beep
   End If
End Sub

'WEIGHT COMBOBOX
Private Sub WeightComboBox_AfterUpdate()
   WeightBoxOnUpdate WeightComboBox, SECTION_LABEL_COORD, KEY_WEIGHT
End Sub

'FONT COMBOBOX
Private Sub FontComboBox_AfterUpdate()
   If Not FontBoxOnUpdate(FontComboBox, SECTION_LABEL_COORD, KEY_FONT) Then
      PopulateFontBox FontComboBox, SECTION_LABEL_COORD, KEY_FONT
      Beep
   End If
End Sub



'SETTINGS BUTTON
Private Sub SettingsButton_Click()
   Setting
End Sub



'*************************************************************************************************************
'********************************************CONTROL STATES***************************************************
Private Sub ControlStates()
   Dim enabledState As Boolean
   enabledState = ShowDescCheckBox.value Or OutFileCheckBox.value
   DescLabel.enabled = enabledState
   DescTextBox.enabled = enabledState
   DescTextBox.BackColor = BackOLE_COLOR(enabledState)
   PickButton.enabled = enabledState
   
   NEandNumCheckBox.enabled = OutFileCheckBox.value

   OverrideCheckBox.enabled = ElevationCheckBox.value Or OutFileCheckBox.value
   enabledState = OverrideCheckBox.value And OverrideCheckBox.enabled
   UseElevationLabel.enabled = enabledState
   UseElevTextBox.enabled = enabledState
   UseElevTextBox.BackColor = BackOLE_COLOR(enabledState)
   PickElButton.enabled = enabledState

   enabledState = OutFileCheckBox.value
   Dim BackColor As OLE_COLOR
   BackColor = BackOLE_COLOR(enabledState)
   FileLabel.enabled = enabledState
   NewButton.enabled = enabledState
   OpenButton.enabled = enabledState
   PointNumTextBox.enabled = enabledState
   PointNumTextBox.BackColor = BackColor
   PointLabel.enabled = enabledState
   FilenameLabel.enabled = enabledState
   PickPointButton.enabled = enabledState
End Sub



'*************************************************************************************************************
'**********************************************USERFORM EVENTS************************************************
Private Sub UserForm_Initialize()
'SET FLAG
   OkayToClose = True
   
'INITIALIZE SHOW ELEVATION CHECK BOX
   InitializeCheckBox ElevationCheckBox, SECTION_LABEL_COORD, KEY_SHOW_ELEVATION

'INITIALIZE POINT NUMBER TEXT BOX
   PointNumTextBox.MaxLength = MAX_LEN_POINT_NAME
   PointNumTextBox.text = GetSetting(APP_NAME, SECTION_LABEL_COORD, KEY_POINTNAME, "1")

'INITIALIZE DESCRIPTION TEXT BOX
   DescTextBox.MaxLength = MAX_LEN_POINT_DESC
   DescTextBox.text = GetSetting(APP_NAME, SECTION_LABEL_COORD, KEY_DESCRIPTION, "")

'INITIALIZE FILENAME TEXT BOX
   Dim strFName As String
   strFName = Trim(GetSetting(APP_NAME, SECTION_LABEL_COORD, KEY_FILENAME, ""))
   If strFName <> "" Then
      Dim XSplit As Variant
      XSplit = Split(strFName, "\")
      FilenameLabel.Caption = XSplit(UBound(XSplit))
   Else
      FilenameLabel.Caption = ""
   End If

'INITIALIZE OUTPUT TO FILE CHECK BOX
   InitializeCheckBox OutFileCheckBox, SECTION_LABEL_COORD, KEY_OUTPUT_TO_FILE
   
'INITIALIZE OVERRIDE ELEVATION CHECK BOX
   InitializeCheckBox OverrideCheckBox, SECTION_LABEL_COORD, KEY_OVERRIDE
   
'INITIALIZE SHOW DESCRIPTION CHECK BOX
   InitializeCheckBox ShowDescCheckBox, SECTION_LABEL_COORD, KEY_SHOW_DESCRIPTION

'INITIALIZE SHOW N,E WITH POINT NUMBER CHECK BOX
   InitializeCheckBox NEandNumCheckBox, SECTION_LABEL_COORD, KEY_SHOW_NE

'INITIALIZE OVERRIDE ELEVATION
   UseElevTextBox.MaxLength = MAX_LEN_ELEV_STRING
   UseElevTextBox.text = GetSetting(APP_NAME, SECTION_LABEL_COORD, KEY_OVERRIDE_ELEVATION, "0.00")

'INITIALIZE TEXT ALIGNMENT STATES
   Dim Alignment As String
   Alignment = GetSetting(APP_NAME, SECTION_LABEL_COORD, KEY_OPTION_ALIGN, OPTION_ALIGN_LEFT)
   If Alignment = OPTION_ALIGN_LEFT Then
      AlignLeftOption.value = True
   Else
      AlignRightOption.value = True
   End If

'SET STATES OF BUTTONS AND STUFF
   ControlStates
   
'POPULATE PRECISION COMBOBOX
   PrecisionComboBox.AddItem "2"
   PrecisionComboBox.AddItem "3"
   PrecisionComboBox.AddItem "4"
   PrecisionComboBox.AddItem "5"

'SET INITIAL PRECISION (INDEX)
   PrecisionComboBox.listIndex = CLng(GetSetting(APP_NAME, SECTION_LABEL_COORD, KEY_PRECISION, "0"))
   
'POPULATE ELEVATION PRECISION COMBOBOX
   ElPrecComboBox.AddItem "0"
   ElPrecComboBox.AddItem "1"
   ElPrecComboBox.AddItem "2"
   ElPrecComboBox.AddItem "3"
   ElPrecComboBox.AddItem "4"

'SET INITIAL ELEVATION PRECISION (INDEX)
   ElPrecComboBox.listIndex = CLng(GetSetting(APP_NAME, SECTION_LABEL_COORD, KEY_PRECISION_ELEV, "0"))

'TEXT ATTRIBUTES
'LEVEL COMBOBOX
   PopulateLevelBox LevelComboBox, SECTION_LABEL_COORD, KEY_LEVEL
'COLOR COMBOBOX
   PopulateColorBox ColorComboBox, SECTION_LABEL_COORD, KEY_COLOR
'STYLE COMBOBOX
   PopulateLinestyleBox StyleComboBox, SECTION_LABEL_COORD, KEY_STYLE
'WEIGHT COMBOBOX
   PopulateWeightBox WeightComboBox, SECTION_LABEL_COORD, KEY_WEIGHT
'FONT COMBOBOX
   PopulateFontBox FontComboBox, SECTION_LABEL_COORD, KEY_FONT

'SET CAPTION
   Me.Caption = COMMAND_NAME_LABELCOORD

'BRING LABEL PAGE TO FOREGROUND
   Me.MultiPage1.value = 0

'MOVE INTO LAST POSITION
   If GetSetting(APP_NAME, SECTION_LABEL_COORD, KEY_START_TOP, "") = "" Then
      Me.StartUpPosition = 1
   Else
      Me.StartUpPosition = 0
      Me.Top = CDbl(GetSetting(APP_NAME, SECTION_LABEL_COORD, KEY_START_TOP, WINDOW_DEFAULT_TOP))
      Me.Left = CDbl(GetSetting(APP_NAME, SECTION_LABEL_COORD, KEY_START_LEFT, WINDOW_DEFAULT_LEFT))
   End If
End Sub



Private Sub UserForm_QueryClose(Cancel As Integer, CloseMode As Integer)
'SAVE USERFORM POSITION
   SaveSetting APP_NAME, SECTION_LABEL_COORD, KEY_START_TOP, FormatNumber(Me.Top, 2)
   SaveSetting APP_NAME, SECTION_LABEL_COORD, KEY_START_LEFT, FormatNumber(Me.Left, 2)
End Sub



Private Sub UserForm_Terminate()
   CommandState.StartDefaultCommand
End Sub

Attribute VB_Name = "FrmLabelCurve"
Attribute VB_Base = "0{94A3DAE1-DE7A-4946-B942-13EA272AAB80}{4C483986-D764-40E2-8506-C1611796A943}"
Attribute VB_GlobalNameSpace = False
Attribute VB_Creatable = False
Attribute VB_PredeclaredId = True
Attribute VB_Exposed = False
Attribute VB_TemplateDerived = False
Attribute VB_Customizable = False











'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

'GENERAL NOTES:
'PROGRAM ASSUMES MASTER UNIT IS FOOT OR SURVEY FOOT, SOME KIND OF FOOT

Option Explicit

Public Sub arcMode(modeArc As Boolean)
   HeadingLabel.enabled = modeArc
   HeadingTextBox.enabled = modeArc
   AlignLeftOption.enabled = modeArc
   AlignRightOption.enabled = modeArc
   PrecisionFrame.enabled = modeArc
   OptionSecond.enabled = modeArc
   OptionTenthOfASecond.enabled = modeArc
End Sub

Public Function GetPrecision() As Long
   If OptionSecond.value = True Then
      GetPrecision = 0
   Else
      GetPrecision = 1
   End If
End Function



Public Function GetPrefix() As String
   GetPrefix = CurveDataPrefixTextBox.text
End Function



Public Function GetHeading() As String
   GetHeading = HeadingTextBox.text
End Function



Public Function GetAlignRight() As Boolean
   GetAlignRight = AlignRightOption.value
End Function



'*************************************************************************************************************
'*********************************************CONTROLS********************************************************
'PREFIX TEXTBOX
Private Sub CurveDataPrefixTextBox_AfterUpdate()
   SaveSetting APP_NAME, SECTION_LABEL_CURVE, KEY_PREFIX, CurveDataPrefixTextBox.text
End Sub

Private Sub CurveDataPrefixTextBox_Enter()
   SelectAllText CurveDataPrefixTextBox
End Sub



'HEADING TEXTBOX
Private Sub HeadingTextBox_AfterUpdate()
   SaveSetting APP_NAME, SECTION_LABEL_CURVE, KEY_HEADING, HeadingTextBox.text
End Sub

Private Sub HeadingTextBox_Enter()
   SelectAllText HeadingTextBox
End Sub



'ALIGN LEFT RADIO BUTTON
Private Sub AlignLeftOption_Click()
   SaveSetting APP_NAME, SECTION_LABEL_CURVE, KEY_OPTION_ALIGN, OPTION_ALIGN_LEFT
End Sub



'ALIGN RIGHT RADIO BUTTON
Private Sub AlignRightOption_Click()
   SaveSetting APP_NAME, SECTION_LABEL_CURVE, KEY_OPTION_ALIGN, OPTION_ALIGN_RIGHT
End Sub



'1 SECOND RADIO BUTTON
Private Sub OptionSecond_Click()
   SavePrecision
End Sub



'0.1 SECOND RADIO BUTTON
Private Sub OptionTenthOfASecond_Click()
   SavePrecision
End Sub



Private Sub SavePrecision()
   If OptionSecond.value = True Then
      SaveSetting APP_NAME, SECTION_LABEL_CURVE, KEY_PRECISION, OPTION_PREC_ANG_SEC
   ElseIf OptionTenthOfASecond.value = True Then
      SaveSetting APP_NAME, SECTION_LABEL_CURVE, KEY_PRECISION, OPTION_PREC_ANG_SEC1
   End If
End Sub



'SETTINGS BUTTON
Private Sub SettingsButton_Click()
   Setting
End Sub




'CURVE DATA LEVEL COMBOBOX
Private Sub CurveDataLevelComboBox_AfterUpdate()
   If Not LevelBoxOnUpdate(CurveDataLevelComboBox, SECTION_LABEL_CURVE, KEY_CURVE_DATA_LEVEL) Then
      PopulateLevelBox CurveDataLevelComboBox, SECTION_LABEL_CURVE, KEY_CURVE_DATA_LEVEL
      Beep
   End If
End Sub

'CURVE DATA COLOR COMBOBOX
Private Sub CurveDataColorComboBox_AfterUpdate()
   ColorBoxOnUpdate CurveDataColorComboBox, SECTION_LABEL_CURVE, KEY_CURVE_DATA_COLOR
End Sub

'CURVE DATA COLOR CHOOSER
Private Sub CurveDataColorChooserButton_Click()
   Dim MyColor As String
   If ChooseMyTableColor(MyColor) Then
      CurveDataColorComboBox.text = MyColor
      CurveDataColorComboBox_AfterUpdate
   End If
End Sub

'CURVE DATA STYLE COMBOBOX
Private Sub CurveDataStyleComboBox_AfterUpdate()
   If Not LineStyleBoxOnUpdate(CurveDataStyleComboBox, SECTION_LABEL_CURVE, KEY_CURVE_DATA_STYLE) Then
      PopulateLinestyleBox CurveDataStyleComboBox, SECTION_LABEL_CURVE, KEY_CURVE_DATA_STYLE
      Beep
   End If
End Sub

'CURVE DATA WEIGHT COMBOBOX
Private Sub CurveDataWeightComboBox_AfterUpdate()
   WeightBoxOnUpdate CurveDataWeightComboBox, SECTION_LABEL_CURVE, KEY_CURVE_DATA_WEIGHT
End Sub

'CURVE DATA FONT COMBOBOX
Private Sub CurveDataFontComboBox_AfterUpdate()
   If Not FontBoxOnUpdate(CurveDataFontComboBox, SECTION_LABEL_CURVE, KEY_CURVE_DATA_FONT) Then
      PopulateFontBox CurveDataFontComboBox, SECTION_LABEL_CURVE, KEY_CURVE_DATA_FONT
      Beep
   End If
End Sub



'*************************************************************************************************************
'**********************************************USERFORM EVENTS************************************************
Private Sub UserForm_Initialize()
'INITIALIZE CURVE DATA PREFIX TEXT BOX
   CurveDataPrefixTextBox.text = GetSetting(APP_NAME, SECTION_LABEL_CURVE, KEY_PREFIX, "{ ")
   CurveDataPrefixTextBox.MaxLength = MAX_LEN_PREFIX

'INITIALIZE HEADING TEXT BOX
   HeadingTextBox.text = GetSetting(APP_NAME, SECTION_LABEL_CURVE, KEY_HEADING, "Curve Data")
   HeadingTextBox.MaxLength = MAX_LEN_HEADING

'INITIALIZE PRECISION BUTTONS
   Dim myOption As String
   myOption = GetSetting(APP_NAME, SECTION_LABEL_CURVE, KEY_PRECISION, OPTION_PREC_ANG_SEC)
   If myOption = OPTION_PREC_ANG_SEC Then
      OptionSecond.value = True
   Else
      OptionTenthOfASecond.value = True
   End If

'INITIALIZE TEXT ALIGNMENT STATES
   Dim Alignment As String
   Alignment = GetSetting(APP_NAME, SECTION_LABEL_CURVE, KEY_OPTION_ALIGN, OPTION_ALIGN_LEFT)
   If Alignment = OPTION_ALIGN_LEFT Then
      AlignLeftOption.value = True
   Else
      AlignRightOption.value = True
   End If

'POPULATE CURVE DATA SETTINGS COMBO BOXES
   PopulateLevelBox CurveDataLevelComboBox, SECTION_LABEL_CURVE, KEY_CURVE_DATA_LEVEL
   PopulateColorBox CurveDataColorComboBox, SECTION_LABEL_CURVE, KEY_CURVE_DATA_COLOR
   PopulateLinestyleBox CurveDataStyleComboBox, SECTION_LABEL_CURVE, KEY_CURVE_DATA_STYLE
   PopulateWeightBox CurveDataWeightComboBox, SECTION_LABEL_CURVE, KEY_CURVE_DATA_WEIGHT
   PopulateFontBox CurveDataFontComboBox, SECTION_LABEL_CURVE, KEY_CURVE_DATA_FONT

'INITIALIZE CAPTION
   Me.Caption = COMMAND_NAME_LABEL_CURVE

'MOVE INTO LAST POSITION
   If GetSetting(APP_NAME, SECTION_LABEL_CURVE, KEY_START_TOP, "") = "" Then
      Me.StartUpPosition = 1
   Else
      Me.StartUpPosition = 0
      Me.Top = CDbl(GetSetting(APP_NAME, SECTION_LABEL_CURVE, KEY_START_TOP, WINDOW_DEFAULT_TOP))
      Me.Left = CDbl(GetSetting(APP_NAME, SECTION_LABEL_CURVE, KEY_START_LEFT, WINDOW_DEFAULT_LEFT))
   End If
End Sub



Private Sub UserForm_QueryClose(Cancel As Integer, CloseMode As Integer)
'SAVE USERFORM POSITION
   SaveSetting APP_NAME, SECTION_LABEL_CURVE, KEY_START_TOP, FormatNumber(Me.Top, 2)
   SaveSetting APP_NAME, SECTION_LABEL_CURVE, KEY_START_LEFT, FormatNumber(Me.Left, 2)
End Sub



Private Sub UserForm_Terminate()
'END THIS COMMAND
   CommandState.StartDefaultCommand
End Sub




'*************************************************************************************************************
'**************************************************TEMPLATES**************************************************
Public Function textTemplate() As TextElement
   Set textTemplate = CreateTextTemplate(SECTION_LABEL_CURVE, _
                                         CurveDataFontComboBox, _
                                         KEY_CURVE_DATA_FONT, _
                                         CurveDataLevelComboBox, _
                                         KEY_CURVE_DATA_LEVEL, _
                                         CurveDataWeightComboBox, _
                                         CurveDataColorComboBox, _
                                         CurveDataStyleComboBox, _
                                         KEY_CURVE_DATA_STYLE)
   
End Function

Attribute VB_Name = "FrmLabelLine"
Attribute VB_Base = "0{3B97361B-CE25-45DA-961F-BF8BFD925930}{B7059204-FCCB-40CC-B8AB-8DB4ABE71A26}"
Attribute VB_GlobalNameSpace = False
Attribute VB_Creatable = False
Attribute VB_PredeclaredId = True
Attribute VB_Exposed = False
Attribute VB_TemplateDerived = False
Attribute VB_Customizable = False
















'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.



'GENERAL NOTES:
'ALL THESE ROUTINES WERE WRITTEN BY JASON LOOK.  THEY ARE NOT
'WRITTEN IN THE STYLE COMMONLY USED BY PROFESSIONAL PROGRAMMERS.
'THEY ARE WRITTEN IN THE STYLE PREFERRED BY JASON.  JASON IS NOT
'A PROFESSIONAL PROGRAMMER!

'PROGRAM ASSUMES MASTER UNIT IS FOOT OR SURVEY FOOT, SOME KIND OF FOOT

Option Explicit



Public Function LabelOption() As String
   If OptionAandD.value = True Then
      LabelOption = OPTION_AZ_DIST
   ElseIf OptionAzimuth.value = True Then
      LabelOption = OPTION_AZ
   ElseIf OptionDistance.value = True Then
      LabelOption = OPTION_DIST
   End If
End Function



Public Function DirPrec() As String
   If OptionOneSec.value = True Then
      DirPrec = OPTION_PREC_ANG_SEC
   ElseIf Option10thSec.value = True Then
      DirPrec = OPTION_PREC_ANG_SEC1
   ElseIf Option100thSec.value = True Then
      DirPrec = OPTION_PREC_ANG_SEC01
   ElseIf Option1000thSec.value = True Then
      DirPrec = OPTION_PREC_ANG_SEC001
   End If
End Function



Public Function distPrec() As String
   If OptionDist01.value = True Then
      distPrec = OPTION_PREC_DIST_FT01
   ElseIf OptionDist001.value = True Then
      distPrec = OPTION_PREC_DIST_FT001
   ElseIf OptionDist0001.value = True Then
      distPrec = OPTION_PREC_DIST_FT0001
   ElseIf OptionDist00001.value = True Then
      distPrec = OPTION_PREC_DIST_FT00001
   End If
End Function



Public Function LeaveOffOption() As String
   If OptionLeaveOffNothing.value = True Then
      LeaveOffOption = OPTION_NOTHING
   ElseIf OptionLeaveOffSec.value = True Then
      LeaveOffOption = OPTION_NO_00
   ElseIf OptionLeaveOffMin.value = True Then
      LeaveOffOption = OPTION_NO_00_00
   End If
End Function



Public Function dirType() As String
   If AzOption.value Then
      dirType = OPTION_DIR_TYPE_AZIMUTH
   Else
      dirType = OPTION_DIR_TYPE_BEARING
   End If
End Function



Public Function textTemplate() As TextElement
   Set textTemplate = CreateTextTemplate(SECTION_LABEL_LINE, _
                                         FontComboBox, _
                                         KEY_FONT, _
                                         LevelComboBox, _
                                         KEY_LEVEL, _
                                         WeightComboBox, _
                                         ColorComboBox, _
                                         StyleComboBox, _
                                         KEY_STYLE)
End Function



'*************************************************************************************************************
'************************************************LABEL TAB****************************************************
'NO FIT CHECKBOX
Private Sub CheckBoxBkAz_Click()
   SaveCheckBoxSetting CheckBoxBkAz, SECTION_LABEL_LINE, KEY_OPTION_BK_AZ
End Sub



'FORCE A LEADER LINE CHECKBOX
Private Sub LeaderCheckBox_Click()
   OverUnderStates
   SaveLeaderChk
End Sub



Private Sub SaveLeaderChk()
   SaveCheckBoxSetting LeaderCheckBox, SECTION_LABEL_LINE, KEY_OPTION_FORCE_LEADER
End Sub



'AZIMUTH AND DISTANCE RADIO BUTTON
Private Sub OptionAandD_Change()
   OverUnderStates
   SaveAandDOptions
End Sub



'OVER/UNDER LINE ONLY
Private Sub CheckBoxOverUnder_Click()
   SaveCheckBoxSetting CheckBoxOverUnder, SECTION_LABEL_LINE, KEY_OPTION_OVERUNDER
End Sub



'AZIMUTH RADIO BUTTON
Private Sub OptionAzimuth_Click()
   SaveAandDOptions
End Sub



'DISTANCE RADIO BUTTON
Private Sub OptionDistance_Click()
   SaveAandDOptions
End Sub



Private Sub SaveAandDOptions()
   SaveSetting APP_NAME, SECTION_LABEL_LINE, KEY_LABEL_STYLE, LabelOption()
End Sub



'ERASE OLD LABEL CHECKBOX
Private Sub EraseOldCheckBox_Click()
   SaveCheckBoxSetting EraseOldCheckBox, SECTION_LABEL_LINE, KEY_ERASE_OLD
End Sub



'AZIMUTH OPTION
Private Sub AzOption_Click()
   SaveSetting APP_NAME, SECTION_LABEL_LINE, KEY_DIRECTION_TYPE, OPTION_DIR_TYPE_AZIMUTH
End Sub



'BEARING OPTION
Private Sub BearOptionButton_Click()
   SaveSetting APP_NAME, SECTION_LABEL_LINE, KEY_DIRECTION_TYPE, OPTION_DIR_TYPE_BEARING
End Sub



'*************************************************************************************************************
'**********************************************PRECISION TAB**************************************************
'1 SECOND RADIO BUTTON
Private Sub OptionOneSec_Change()
   SaveSetting APP_NAME, SECTION_LABEL_LINE, KEY_PRECISION_ANG, DirPrec()
End Sub



'0.1 SECOND RADIO BUTTON
Private Sub Option10thSec_Click()
   SaveSetting APP_NAME, SECTION_LABEL_LINE, KEY_PRECISION_ANG, DirPrec()
End Sub



'0.01 SECOND RADIO BUTTON
Private Sub Option100thSec_Click()
   SaveSetting APP_NAME, SECTION_LABEL_LINE, KEY_PRECISION_ANG, DirPrec()
End Sub



'0.001 SECOND RADIO BUTTON
Private Sub Option1000thSec_Click()
   SaveSetting APP_NAME, SECTION_LABEL_LINE, KEY_PRECISION_ANG, DirPrec()
End Sub



Private Sub SaveAzPrec()
   SaveSetting APP_NAME, SECTION_LABEL_LINE, KEY_PRECISION_ANG, DirPrec()
End Sub



'LEAVE OFF 00" RADIO BUTTON
Private Sub OptionLeaveOffSec_Click()
   SaveSetting APP_NAME, SECTION_LABEL_LINE, KEY_LEAVE_OFF, LeaveOffOption
End Sub



'LEAVE OFF 00' 00" RADIO BUTTON
Private Sub OptionLeaveOffMin_Click()
   SaveSetting APP_NAME, SECTION_LABEL_LINE, KEY_LEAVE_OFF, LeaveOffOption
End Sub



'LEAVE OFF NOTHING RADIO BUTTON
Private Sub OptionLeaveOffNothing_Click()
   SaveSetting APP_NAME, SECTION_LABEL_LINE, KEY_LEAVE_OFF, LeaveOffOption
End Sub






'0.01 RADIO BUTTON
Private Sub OptionDist01_Click()
   SaveSetting APP_NAME, SECTION_LABEL_LINE, KEY_PRECISION_DIST, distPrec()
End Sub



'0.001 RADIO BUTTON
Private Sub OptionDist001_Click()
   SaveSetting APP_NAME, SECTION_LABEL_LINE, KEY_PRECISION_DIST, distPrec()
End Sub



'0.0001 RADIO BUTTON
Private Sub OptionDist0001_Click()
   SaveSetting APP_NAME, SECTION_LABEL_LINE, KEY_PRECISION_DIST, distPrec()
End Sub



'0.00001 RADIO BUTTON
Private Sub OptionDist00001_Click()
   SaveSetting APP_NAME, SECTION_LABEL_LINE, KEY_PRECISION_DIST, distPrec()
End Sub



'*************************************************************************************************************
'*********************************************ATTRIBUTES TAB**************************************************
'COLOR COMBOBOX
Private Sub ColorComboBox_AfterUpdate()
   ColorBoxOnUpdate ColorComboBox, SECTION_LABEL_LINE, KEY_COLOR
End Sub



'COLOR PICKER
Private Sub ChooseColorButton_Click()
   Dim MyColor As String
   If ChooseMyTableColor(MyColor) Then
      ColorComboBox.text = MyColor
      ColorComboBox_AfterUpdate
   End If
End Sub



'LEVEL COMBOBOX
Private Sub LevelComboBox_AfterUpdate()
   If Not LevelBoxOnUpdate(LevelComboBox, SECTION_LABEL_LINE, KEY_LEVEL) Then
      PopulateLevelBox LevelComboBox, SECTION_LABEL_LINE, KEY_LEVEL
      Beep
   End If
End Sub



'STYLE COMBOBOX
Private Sub StyleComboBox_AfterUpdate()
   If Not LineStyleBoxOnUpdate(StyleComboBox, SECTION_LABEL_LINE, KEY_STYLE) Then
      PopulateLinestyleBox StyleComboBox, SECTION_LABEL_LINE, KEY_STYLE
      Beep
   End If
End Sub



'WEIGHT COMBOBOX
Private Sub WeightComboBox_AfterUpdate()
   WeightBoxOnUpdate WeightComboBox, SECTION_LABEL_LINE, KEY_WEIGHT
End Sub



'FONT COMBOBOX
Private Sub FontComboBox_AfterUpdate()
   If Not FontBoxOnUpdate(FontComboBox, SECTION_LABEL_LINE, KEY_FONT) Then
      PopulateFontBox FontComboBox, SECTION_LABEL_LINE, KEY_FONT
      Beep
   End If
End Sub



'SETTINGS BUTTON
Private Sub SettingsButton_Click()
   Setting
End Sub



'*************************************************************************************************************
'*********************************************CONTROL STATES**************************************************
Private Sub OverUnderStates()
'SET THE STATE FOR THE OVER/UNDER LINE ONLY CHECK BOX
   CheckBoxOverUnder.enabled = Not (LeaderCheckBox.value = True Or OptionAandD.value = False)
End Sub



'*************************************************************************************************************
'*********************************************USERFORM EVENTS*************************************************
Private Sub UserForm_Initialize()
'INITIALIZE AZIMUTH AND DISTANCE RADIO BUTTONS
   Dim Options As String
   Options = GetSetting(APP_NAME, SECTION_LABEL_LINE, KEY_LABEL_STYLE, OPTION_AZ_DIST)
   Select Case Options
      Case OPTION_AZ_DIST
         OptionAandD.value = True
      Case OPTION_AZ
         OptionAzimuth.value = True
      Case OPTION_DIST
         OptionDistance.value = True
   End Select

'INITIALIZE FORCE LEADER CHECK BOX
   InitializeCheckBox LeaderCheckBox, SECTION_LABEL_LINE, KEY_OPTION_FORCE_LEADER

'INITIALIZE BACK AZ CHECK BOX
   InitializeCheckBox CheckBoxBkAz, SECTION_LABEL_LINE, KEY_OPTION_BK_AZ

'INITIALIZE OVER/UNDER CHECK BOX
   InitializeCheckBox CheckBoxOverUnder, SECTION_LABEL_LINE, KEY_OPTION_OVERUNDER
   
'INITIALIZE ERASE OLD LABEL CHECK BOX
   InitializeCheckBox EraseOldCheckBox, SECTION_LABEL_LINE, KEY_ERASE_OLD
   
   If OptionAandD.value = True Then
      CheckBoxOverUnder.enabled = True
   Else
      CheckBoxOverUnder.enabled = False
   End If

   Options = GetSetting(APP_NAME, SECTION_LABEL_LINE, KEY_DIRECTION_TYPE, OPTION_DIR_TYPE_AZIMUTH)
   If Options = OPTION_DIR_TYPE_AZIMUTH Then
      AzOption.value = True
   Else
      BearOptionButton.value = True
   End If

   Options = GetSetting(APP_NAME, SECTION_LABEL_LINE, KEY_PRECISION_ANG, OPTION_PREC_ANG_SEC)
   Select Case Options
      Case OPTION_PREC_ANG_SEC
         OptionOneSec.value = True
      Case OPTION_PREC_ANG_SEC1
         Option10thSec.value = True
      Case OPTION_PREC_ANG_SEC01
         Option100thSec.value = True
      Case OPTION_PREC_ANG_SEC001
         Option1000thSec.value = True
   End Select


   Options = GetSetting(APP_NAME, SECTION_LABEL_LINE, KEY_LEAVE_OFF, OPTION_NOTHING)
   Select Case Options
      Case OPTION_NOTHING
         OptionLeaveOffNothing.value = True
      Case OPTION_NO_00
         OptionLeaveOffSec.value = True
      Case OPTION_NO_00_00
         OptionLeaveOffMin.value = True
   End Select
      
      
   Options = GetSetting(APP_NAME, SECTION_LABEL_LINE, KEY_PRECISION_DIST, OPTION_PREC_DIST_FT01)
   Select Case Options
      Case OPTION_PREC_DIST_FT01
         OptionDist01.value = True
      Case OPTION_PREC_DIST_FT001
         OptionDist001.value = True
      Case OPTION_PREC_DIST_FT0001
         OptionDist0001.value = True
      Case OPTION_PREC_DIST_FT00001
         OptionDist00001.value = True
   End Select

   OverUnderStates

'LEVEL COMBOBOX
   PopulateLevelBox LevelComboBox, SECTION_LABEL_LINE, KEY_LEVEL

'COLOR COMBOBOX
   PopulateColorBox ColorComboBox, SECTION_LABEL_LINE, KEY_COLOR

'STYLE COMBOBOX
   PopulateLinestyleBox StyleComboBox, SECTION_LABEL_LINE, KEY_STYLE

'WEIGHT COMBOBOX
   PopulateWeightBox WeightComboBox, SECTION_LABEL_LINE, KEY_WEIGHT

'FONT COMBOBOX
   PopulateFontBox FontComboBox, SECTION_LABEL_LINE, KEY_FONT

'BRING LABEL PAGE TO FRONT
   MultiPage1.value = 0

'SET TITLE BAR CAPTION
   Me.Caption = COMMAND_NAME_LABEL_LINE

'MOVE INTO LAST POSITION
   If GetSetting(APP_NAME, SECTION_LABEL_LINE, KEY_START_TOP, "") = "" Then
      Me.StartUpPosition = 1
   Else
      Me.StartUpPosition = 0
      Me.Top = CDbl(GetSetting(APP_NAME, SECTION_LABEL_LINE, KEY_START_TOP, WINDOW_DEFAULT_TOP))
      Me.Left = CDbl(GetSetting(APP_NAME, SECTION_LABEL_LINE, KEY_START_LEFT, WINDOW_DEFAULT_LEFT))
   End If
End Sub



Private Sub UserForm_QueryClose(Cancel As Integer, CloseMode As Integer)
'SAVE USERFORM POSITION
   SaveSetting APP_NAME, SECTION_LABEL_LINE, KEY_START_TOP, FormatNumber(Me.Top, 2)
   SaveSetting APP_NAME, SECTION_LABEL_LINE, KEY_START_LEFT, FormatNumber(Me.Left, 2)
End Sub



Private Sub UserForm_Terminate()
   CommandState.StartDefaultCommand
End Sub

Attribute VB_Name = "FrmMeasureDir"
Attribute VB_Base = "0{BFD6489C-2CCE-4DE6-B732-64275DDB32F5}{1335A323-55BE-4F5B-8247-6E8C9EA8CCD3}"
Attribute VB_GlobalNameSpace = False
Attribute VB_Creatable = False
Attribute VB_PredeclaredId = True
Attribute VB_Exposed = False
Attribute VB_TemplateDerived = False
Attribute VB_Customizable = False
















'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

'GENERAL NOTES:
'PROGRAM ASSUMES MASTER UNIT IS FOOT OR SURVEY FOOT, SOME KIND OF FOOT

Option Explicit

Public Sub setMeaseredPoints(startPoint As Point3d, endPoint As Point3d)
'CALCULATE THE MEASUREMENTS
   Dim southAzimuthDegrees As Double
   Dim horizontalDist As Double
   Inverse startPoint, endPoint, southAzimuthDegrees, horizontalDist
   
   Select Case AngPrecComboBox.text
      Case OPTION_PREC_ANG_SEC
         Dim anglePrec As Long
         anglePrec = 4
      Case OPTION_PREC_ANG_SEC1
         anglePrec = 5
      Case OPTION_PREC_ANG_SEC01
         anglePrec = 6
      Case OPTION_PREC_ANG_SEC001
         anglePrec = 7
   End Select
   If OptionAzimuth.value Then
      Dim dirType As Integer
      dirType = DIR_TYPE_AZIMUTH
      Dim dirPrefix As String
      dirPrefix = "Az: "
   Else
      dirType = DIR_TYPE_BEARING
      dirPrefix = "Br: "
   End If
   Dim style As Integer
   style = STYLE_ANGLE_SPACE + STYLE_ANGLE_LEAD
   DirDispLabel.Caption = dirPrefix & SAzToDirectionStr(southAzimuthDegrees, anglePrec, dirType, style)
   
   Select Case DisPrecComboBox.text
      Case OPTION_PREC_DIST_FT
         Dim distPrec As Long
         distPrec = 0
      Case OPTION_PREC_DIST_FT1
         distPrec = 1
      Case OPTION_PREC_DIST_FT01
         distPrec = 2
      Case OPTION_PREC_DIST_FT001
         distPrec = 3
      Case OPTION_PREC_DIST_FT0001
         distPrec = 4
      Case OPTION_PREC_DIST_FT00001
         distPrec = 5
   End Select
   DistDispLabel.Caption = "Dis: " & FormatNumber(horizontalDist, distPrec, vbTrue, vbFalse, vbTrue) & " ft."
End Sub



Private Sub AngPrecComboBox_AfterUpdate()
   SaveSetting APP_NAME, SECTION_MEASURE_DIR, KEY_PRECISION_ANG, AngPrecComboBox.text
   ClearLastMeasure
End Sub



Private Sub BearingOption_Click()
   saveDirTypeOption
End Sub



Private Sub DisPrecComboBox_AfterUpdate()
   SaveSetting APP_NAME, SECTION_MEASURE_DIR, KEY_PRECISION_DIST, DisPrecComboBox.text
   ClearLastMeasure
End Sub



Private Sub OptionAzimuth_Click()
   saveDirTypeOption
End Sub



Private Sub saveDirTypeOption()
   If OptionAzimuth.value Then
      SaveSetting APP_NAME, SECTION_MEASURE_DIR, KEY_DIRECTION_TYPE, OPTION_DIR_TYPE_AZIMUTH
   Else
      SaveSetting APP_NAME, SECTION_MEASURE_DIR, KEY_DIRECTION_TYPE, OPTION_DIR_TYPE_BEARING
   End If
End Sub


'SETTING BUTTON
Private Sub SettingsButton_Click()
   Setting
End Sub



Private Sub UserForm_Initialize()
'MAKE SURE NO PROBLEM WITH NO ACTIVE FONT
   HandleNoActiveLevel
   
'SET CAPTION
   Me.Caption = COMMAND_NAME_MESAURE_DIR

'POPULATE AZIMUTH PRECISION BOX
   AngPrecComboBox.style = fmStyleDropDownList
   AngPrecComboBox.Clear
   AngPrecComboBox.AddItem OPTION_PREC_ANG_SEC
   AngPrecComboBox.AddItem OPTION_PREC_ANG_SEC1
   AngPrecComboBox.AddItem OPTION_PREC_ANG_SEC01
   AngPrecComboBox.AddItem OPTION_PREC_ANG_SEC001
   AngPrecComboBox.text = GetSetting(APP_NAME, SECTION_MEASURE_DIR, KEY_PRECISION_ANG, OPTION_PREC_ANG_SEC)

'POPULATE DISTANCE PRECISION BOX
   DisPrecComboBox.style = fmStyleDropDownList
   DisPrecComboBox.Clear
   DisPrecComboBox.AddItem OPTION_PREC_DIST_FT
   DisPrecComboBox.AddItem OPTION_PREC_DIST_FT1
   DisPrecComboBox.AddItem OPTION_PREC_DIST_FT01
   DisPrecComboBox.AddItem OPTION_PREC_DIST_FT001
   DisPrecComboBox.AddItem OPTION_PREC_DIST_FT0001
   DisPrecComboBox.AddItem OPTION_PREC_DIST_FT00001
   DisPrecComboBox.text = GetSetting(APP_NAME, SECTION_MEASURE_DIR, KEY_PRECISION_DIST, OPTION_PREC_DIST_FT01)

'CLEAR DISPLAY
   ClearLastMeasure

'INITIALIZE RADIO BUTTONS
   Dim theOption As String
   theOption = GetSetting(APP_NAME, SECTION_MEASURE_DIR, KEY_DIRECTION_TYPE, OPTION_DIR_TYPE_AZIMUTH)
   If theOption = OPTION_DIR_TYPE_AZIMUTH Then
      OptionAzimuth.value = True
   Else
      BearingOption.value = True
   End If

'MOVE INTO LAST POSITION
   If GetSetting(APP_NAME, SECTION_MEASURE_DIR, KEY_START_TOP, "") = "" Then
      Me.StartUpPosition = 1
   Else
      Me.StartUpPosition = 0
      Me.Top = CDbl(GetSetting(APP_NAME, SECTION_MEASURE_DIR, KEY_START_TOP, WINDOW_DEFAULT_TOP))
      Me.Left = CDbl(GetSetting(APP_NAME, SECTION_MEASURE_DIR, KEY_START_LEFT, WINDOW_DEFAULT_LEFT))
   End If
End Sub



Private Sub UserForm_QueryClose(Cancel As Integer, CloseMode As Integer)
'SAVE USERFORM POSITION
   SaveSetting APP_NAME, SECTION_MEASURE_DIR, KEY_START_TOP, FormatNumber(Me.Top, 2)
   SaveSetting APP_NAME, SECTION_MEASURE_DIR, KEY_START_LEFT, FormatNumber(Me.Left, 2)
End Sub



Private Sub ClearLastMeasure()
   DirDispLabel.Caption = ""
   DistDispLabel.Caption = ""
   ShowStatus ""
End Sub



Private Sub UserForm_Terminate()
   CommandState.StartDefaultCommand
End Sub

Attribute VB_Name = "FrmOpener"
Attribute VB_Base = "0{D66B1628-0FDE-483B-84B8-1C4842D00BC0}{AA39242C-464F-4F9E-A54E-2A45677B90DD}"
Attribute VB_GlobalNameSpace = False
Attribute VB_Creatable = False
Attribute VB_PredeclaredId = True
Attribute VB_Exposed = False
Attribute VB_TemplateDerived = False
Attribute VB_Customizable = False
















'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit

Public Sub AzModeIndicator()
'SHOW AZIMUTH MODE
   If NORTH_AZIMUTH_MODE Then
      ModeLabel.Caption = "N"
      ModeLabel.ControlTipText = "Azimuth mode is North"
   Else
      ModeLabel.Caption = "S"
      ModeLabel.ControlTipText = "Azimuth mode is South"
   End If
End Sub



'*************************************************************************************************************
'************************************************CONTROLS*****************************************************
'AZ/AZ INTERSECT BUTTON
Private Sub AAIntButton_Click()
   AAInt
End Sub



'ARC/LINE INTERSECT BUTTON
Private Sub AzDistButton_Click()
   ALInt
End Sub



'COMPASS RULE ADJUSTMENT
Private Sub CompassRuleButton_Click()
   CR2D
End Sub



'CURVE SOLVER BUTTON
Private Sub CurveSolverButton_Click()
   CurveSolver
End Sub



'ARC/ARC INTERSECT
Private Sub DDIntButton_Click()
   DDInt
End Sub



'DRAW TRAVERSE BUTTON
Private Sub DrawTraverseButton_Click()
   DrawTrav
End Sub



'DROP DIAGRAM
Private Sub DropDiagramButton_Click()
   Dropster
End Sub



'DUP FINDER
Private Sub DupFindButton_Click()
   DupFind
End Sub



'LABEL COORDINATE BUTTON
Private Sub LabelCoordButton_Click()
   LabelCoord
End Sub



'LABEL CURVE BUTTON
Private Sub LabelCurveButton_Click()
   LabelCurve
End Sub



'LABEL LINE BUTTON
Private Sub LabelLineButton_Click()
   LabelLine
End Sub



'MEASURE DIRECTION AND DISTANCE BUTTON
Private Sub MeasureButton_Click()
   MeasureDandD
End Sub



'PLOT LOT BUTTON
Private Sub PlotLotButton_Click()
   Plotlot
End Sub



'SAMPLE BUTTON
Private Sub SampleButton_Click()
   Sample
End Sub



'OPEN WHEN MICROSTATION STARTS UP CHECK BOX
Private Sub OpenStartUpCheckBox_Click()
   SaveCheckBoxSetting OpenStartUpCheckBox, SECTION_LAUNCHER, KEY_CHECKBOX
End Sub



'SETTINGS BUTTON
Private Sub SettingsButton_Click()
   Setting
End Sub


'LABEL STATION BUTTON
Private Sub LabelStationButton_Click()
   StationInverse
End Sub



'PLOT BY STATION BUTTON
Private Sub StationPlotButton_Click()
   StationPlot
End Sub



'STATION TEXT BUTTON
Private Sub StationTextButton_Click()
   StationText
End Sub



'*************************************************************************************************************
'**********************************************USERFORM EVENTS************************************************
Private Sub UserForm_Initialize()
'INITIALIZE CHECK BOXES
   InitializeCheckBox OpenStartUpCheckBox, SECTION_LAUNCHER, KEY_CHECKBOX
   
'UPDATE CAPTION
   Me.Caption = APP_PROGRAM_NAME & " " & APP_VERSION & APP_UPDATE

'TOOL TIPS
   StationPlotButton.ControlTipText = COMMAND_NAME_STATION_PLOT
   CurveSolverButton.ControlTipText = COMMAND_NAME_CURVE_SOLVER
   StationTextButton.ControlTipText = COMMAND_NAME_STATION_TEXT
   MeasureButton.ControlTipText = COMMAND_NAME_MESAURE_DIR
   DrawTraverseButton.ControlTipText = COMMAND_NAME_TRVERSE
   LabelStationButton.ControlTipText = COMMAND_NAME_STATION_INVERSE
   LabelCoordButton.ControlTipText = COMMAND_NAME_LABELCOORD
   SettingsButton.ControlTipText = COMMAND_NAME_SETTINGS
   SampleButton.ControlTipText = COMMAND_NAME_SAMPLE
   LabelCurveButton.ControlTipText = COMMAND_NAME_LABEL_CURVE
   LabelLineButton.ControlTipText = COMMAND_NAME_LABEL_LINE
   AAIntButton.ControlTipText = COMMAND_NAME_AZ_AZ_INT
   DDIntButton.ControlTipText = COMMAND_NAME_ARC_ARC_INT
   CompassRuleButton.ControlTipText = COMMAND_NAME_COMPASS_RULE_2D
   AzDistButton.ControlTipText = COMMAND_NAME_ARC_LINE_INT
   DupFindButton.ControlTipText = COMMAND_NAME_DUP_FINDER
   PlotLotButton.ControlTipText = COMMAND_NAME_LOT_CLOSURE
   DropDiagramButton.ControlTipText = COMMAND_NAME_DROP_DIAGRAM
   
'SHOW AZIMUTH MODE
   AzModeIndicator

'MOVE INTO LAST POSITION
   If GetSetting(APP_NAME, SECTION_LAUNCHER, KEY_START_TOP, "") = "" Then
      Me.StartUpPosition = 1
   Else
      Me.StartUpPosition = 0
      Me.Top = CDbl(GetSetting(APP_NAME, SECTION_LAUNCHER, KEY_START_TOP, WINDOW_DEFAULT_TOP))
      Me.Left = CDbl(GetSetting(APP_NAME, SECTION_LAUNCHER, KEY_START_LEFT, WINDOW_DEFAULT_LEFT))
   End If
End Sub



Private Sub UserForm_QueryClose(Cancel As Integer, CloseMode As Integer)
'SAVE USERFORM POSITION
   SaveSetting APP_NAME, SECTION_LAUNCHER, KEY_START_TOP, FormatNumber(Me.Top, 2)
   SaveSetting APP_NAME, SECTION_LAUNCHER, KEY_START_LEFT, FormatNumber(Me.Left, 2)
End Sub

Attribute VB_Name = "FrmPlotLot"
Attribute VB_Base = "0{AAE11532-8CC7-4B15-9588-34BF36163E32}{98F1BAC3-79B8-4B6A-9153-7FB70E0A2EE2}"
Attribute VB_GlobalNameSpace = False
Attribute VB_Creatable = False
Attribute VB_PredeclaredId = True
Attribute VB_Exposed = False
Attribute VB_TemplateDerived = False
Attribute VB_Customizable = False








'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

'GENERAL NOTES:
'ALL THESE ROUTINES WERE WRITTEN BY JASON LOOK.  THEY ARE NOT
'WRITTEN IN THE STYLE COMMONLY USED BY PROFESSIONAL PROGRAMMERS.
'THEY ARE WRITTEN IN THE STYLE PREFERRED BY JASON.  JASON IS NOT
'A PROFESSIONAL PROGRAMMER!

'PROGRAM ASSUMES MASTER UNIT IS FOOT OR SURVEY FOOT, SOME KIND OF FOOT

Option Explicit

Dim tecNormal               As TransientElementContainer 'CONTAINER FOR TEMPORARY UNHIGHLIGHTED GRAPHICS
Dim tecHilite               As TransientElementContainer 'CONTAINER FOR TEMPORARY HIGHLIGHTED GRAPHICS

Private courseEntryMode     As Long                'FLAG FOR EDITOR DIALOG BOX
Private currentIndex        As Long                'FOR PASSING THE COURSES LISTBOX INDEX TO THE EDITOR DIALOG BOX
Private fileIsLoaded        As Boolean             'FLAG IF FILE IS LOADED
Private startingPoint       As Point3d             'START PONT
Private amInsertingCourses  As Boolean             'FLAG FOR REDRAWING NOT GRAPHICS BEFORE INSERTION IS COMPLETE
Private curveArea           As Double              'SUM OF LEFT AND RIGHT CURVES, WHERE LEFT CURVES ARE NEGATIVE AND RIGHT ARE POSITIVE
Private circuitPerimeter    As Double              'SUM OF ARC LENGTHS AND LINE LENGTHS
Private myCellArray()       As Element             'ARRAY FOR CREATING THE PERMANENT GRAPHICS CELL
Private myComplexArray()    As ChainableElement    'ARRAY FOR CREATING THE PERMANENT GRAPHICS CELL
Private selectingBoundary   As Boolean             'SIGNAL THAT MULTISELECT IS FOR BOUNDARY REPORT
Private boundaryLength      As Double              'SUM OF ARC LENGTHS AND LINE LENGTHS FOR BOUNDARY
Private maxBoundaryPrec     As Long                'MAX PRECISION WITH ENTERED DISTANCES

Dim scaleErrorEncountered   As Boolean             'TRANSFORMATION SCALE ERROR

Private openCloseHandler    As ClsOpenClosePlotLot 'MAKE SURE DOESN'T CRASH ON FILE CLOSE


'*************************************************************************************************************
'****************************************STATIC VARIABLE HANDLERS*********************************************
Private Sub AddElementToCellArray(theElement As Element)
   Set myCellArray(UBound(myCellArray)) = theElement
   ReDim Preserve myCellArray(UBound(myCellArray) + 1)
End Sub



Private Sub AddElementToComplexArray(theElement As ChainableElement)
   Set myComplexArray(UBound(myComplexArray)) = theElement
   ReDim Preserve myComplexArray(UBound(myComplexArray) + 1)
End Sub



Private Sub AddToCurveArea(ByVal TheArea As Double)
   curveArea = curveArea + TheArea
End Sub



Private Sub AddToPerimeter(ByVal TheLength As Double)
   circuitPerimeter = circuitPerimeter + TheLength
End Sub



Private Sub ClearCurveArea()
   curveArea = 0
End Sub



Private Sub CreateHiliteTransientContainer()
'CREATE TEMPORARY GRAPHICS CONTAINER FOR HIGHLIGHTED ELEMENTS
   Dim flags As MsdTransientFlags
   flags = msdTransientFlagsOverlay + msdTransientFlagsSnappable
   Set tecHilite = CreateTransientElementContainer1(Nothing, flags, msdViewAll - msdViewMask8 - msdViewMask7, msdDrawingModeHilite)
End Sub



Public Sub ClearInsertingFlag()
   amInsertingCourses = False
End Sub



Private Sub CreateNormalTransientContainer()
'CREATE TEMPORARY GRAPHICS CONTAINER FOR REGULARLY DISPLAYED ELEMENTS
   Dim flags As MsdTransientFlags
   flags = msdTransientFlagsOverlay + msdTransientFlagsSnappable
   Set tecNormal = CreateTransientElementContainer1(Nothing, flags, msdViewAll - msdViewMask8 - msdViewMask7, msdDrawingModeNormal)
End Sub



Private Sub ClearPerimeter()
   circuitPerimeter = 0
End Sub



Private Sub ClearLength()
   boundaryLength = 0
End Sub



Private Sub ZeroMaxPrec()
   maxBoundaryPrec = 0
End Sub



Private Sub MaxPrecUpd(prec As Long)
   maxBoundaryPrec = MaxLong(maxBoundaryPrec, prec)
End Sub



Private Function CreateTheCellAndAddIt(POB As Point3d) As CellElement
   ReDim Preserve myCellArray(UBound(myCellArray) - 1)
   Dim LotCell As CellElement
   Set LotCell = CreateCellElement1(vbNullString, myCellArray, POB)
   ActiveModelReference.AddElement LotCell
   Set CreateTheCellAndAddIt = LotCell
End Function



Private Function CreateTheComplexChain() As ComplexStringElement
   ReDim Preserve myComplexArray(UBound(myComplexArray) - 1)
   Set CreateTheComplexChain = CreateComplexStringElement1(myComplexArray)
End Function



Public Function GetInsertingFlag()
   GetInsertingFlag = amInsertingCourses
End Function



Public Function GetStartPoint() As Point3d
   GetStartPoint = startingPoint
End Function



Private Function GetTheCurveArea() As Double
   GetTheCurveArea = curveArea
End Function



Private Function GetThePerimeter() As Double
   GetThePerimeter = circuitPerimeter
End Function



Private Function IsFileLoaded() As Boolean
   IsFileLoaded = fileIsLoaded
End Function



Private Sub ResetCellArray()
   ReDim myCellArray(0)
End Sub



Private Sub ResetComplexArray()
   ReDim myComplexArray(0)
End Sub



Private Sub SetFileIsLoaded()
   fileIsLoaded = True
   SaveAsButton.enabled = True
End Sub



Public Sub SetInsertingFlag()
   amInsertingCourses = True
End Sub



Private Sub SetModeIAmIn(ByVal TheMode As Long)
   courseEntryMode = TheMode
End Sub



Public Sub SetStartPoint(NewStartPoint As Point3d)
   startingPoint.X = Round(NewStartPoint.X, StartPointPrec)
   startingPoint.Y = Round(NewStartPoint.Y, StartPointPrec)
   startingPoint.z = Round(NewStartPoint.z, StartPointPrec)
   
   UpdateStartPointText
End Sub



Public Sub SetTheCurrentIndex(ByVal TheIndex As Long)
   currentIndex = TheIndex
End Sub



Private Sub UnsetFileIsLoaded()
   fileIsLoaded = False
   SaveAsButton.enabled = False
End Sub



Public Function WhatIsTheCurrentIndex() As Long
   WhatIsTheCurrentIndex = currentIndex
End Function



Public Function WhatModeAmIIn() As Long
   WhatModeAmIIn = courseEntryMode
End Function



'*************************************************************************************************************
'***************************************DISPLAY HANDLERS******************************************************
Private Sub ClearCourseInfo()
   CourseNumberDispLabel.Caption = STRING_SPACE
   CourseTypeDispLabel.Caption = STRING_SPACE
   ChordAzDispLabel.Caption = STRING_SPACE
   ChordDistDispLabel.Caption = STRING_SPACE
   BeginPointNorDispLabel.Caption = STRING_SPACE
   BeginPointEastDispLabel.Caption = STRING_SPACE
   EndPointNorDispLabel.Caption = STRING_SPACE
   EndPointEastDispLabel.Caption = STRING_SPACE
   RadPointNorDispLabel.Caption = STRING_SPACE
   RadPointEastDispLabel.Caption = STRING_SPACE
   SegmentAreaDispLabel.Caption = STRING_SPACE
End Sub



Private Sub ClearStatus()
   NorthErrorDispLabel.Caption = STRING_SPACE
   EastErrorDispLabel.Caption = STRING_SPACE
   CloseAzimuthDispLabel.Caption = STRING_SPACE
   CloseDistanceDispLabel.Caption = STRING_SPACE
   TotalAreaDispLabel.Caption = STRING_SPACE
   TotalAcresLabel.Caption = STRING_SPACE
End Sub



Private Sub CurveCourseInfo(ByVal TheListBoxIndex As Long, _
                            beginPoint As Point3d, _
                            endPoint As Point3d, _
                            radiusPoint As Point3d, _
                            chordAzString As String, _
                            ChordDistString As String, _
                            TheSegmentArea As Double)
   Dim BeginPointCopy As Point3d
   BeginPointCopy = beginPoint
   Dim EndPointCopy As Point3d
   EndPointCopy = endPoint
   Dim RadiusPointCopy As Point3d
   RadiusPointCopy = radiusPoint
   CourseNumberDispLabel.Caption = FormatNumber(TheListBoxIndex + 1, 0, vbFalse, vbFalse, vbFalse)
   CourseTypeDispLabel.Caption = Lot_Closure_List_Type_Curve
   BeginPointNorDispLabel.Caption = DoubleToNorthingString(BeginPointCopy.Y, DisplayPointPrec)
   BeginPointEastDispLabel.Caption = DoubleToEastingString(BeginPointCopy.X, DisplayPointPrec)
   EndPointNorDispLabel.Caption = DoubleToNorthingString(EndPointCopy.Y, DisplayPointPrec)
   EndPointEastDispLabel.Caption = DoubleToEastingString(EndPointCopy.X, DisplayPointPrec)
   RadPointNorDispLabel.Caption = DoubleToNorthingString(RadiusPointCopy.Y, DisplayPointPrec)
   RadPointEastDispLabel.Caption = DoubleToEastingString(RadiusPointCopy.X, DisplayPointPrec)
   ChordAzDispLabel.Caption = chordAzString
   ChordDistDispLabel.Caption = ChordDistString
   SegmentAreaDispLabel.Caption = FormatNumber(Round(Abs(TheSegmentArea), 3), 3, vbTrue, vbFalse, vbTrue) & " sq. ft."
End Sub



Private Sub LineCourseInfo(ByVal TheListBoxIndex As Long, beginPoint As Point3d, endPoint As Point3d)
   Dim BeginPointCopy As Point3d
   BeginPointCopy = beginPoint
   Dim EndPointCopy As Point3d
   EndPointCopy = endPoint
   CourseNumberDispLabel.Caption = FormatNumber(TheListBoxIndex + 1, 0)
   CourseTypeDispLabel.Caption = Lot_Closure_List_Type_Line
   BeginPointNorDispLabel.Caption = DoubleToNorthingString(BeginPointCopy.Y, DisplayPointPrec)
   BeginPointEastDispLabel.Caption = DoubleToEastingString(BeginPointCopy.X, DisplayPointPrec)
   EndPointNorDispLabel.Caption = DoubleToNorthingString(EndPointCopy.Y, DisplayPointPrec)
   EndPointEastDispLabel.Caption = DoubleToEastingString(EndPointCopy.X, DisplayPointPrec)
End Sub



Private Sub UpdateStartPointText()
'UPDATES TEXT FOR STARTING POINT TEXTBOXES
   Dim startPoint As Point3d
   startPoint = GetStartPoint()
   NorthingTextBox.text = DoubleToNorthingString(startPoint.Y, StartPointPrec)
   EastingTextBox.text = DoubleToEastingString(startPoint.X, StartPointPrec)
   ZTextbox.text = FormatNumber(startPoint.z, StartPointPrec, vbTrue, vbFalse, vbTrue)
End Sub



Private Sub UpdateStatus(POB As Point3d, ClosingPoint As Point3d, AreaInSquareFeet As Double)
   Dim NorthingError As Double
   NorthingError = ClosingPoint.Y - POB.Y
   Dim EastingError As Double
   EastingError = ClosingPoint.X - POB.X
   Dim ClosingAzimuth As Double
   Dim ClosingDistance As Double
   Inverse ClosingPoint, POB, ClosingAzimuth, ClosingDistance
   NorthErrorDispLabel.Caption = FormatNumber(NorthingError, 4, vbTrue, vbFalse, vbTrue)
   EastErrorDispLabel.Caption = FormatNumber(EastingError, 4, vbTrue, vbFalse, vbTrue)
   CloseAzimuthDispLabel.Caption = SAzToAzimuthStr(ClosingAzimuth, 4, PlotLotEntryAngleStyle)
   CloseDistanceDispLabel.Caption = FormatNumber(ClosingDistance, 4, vbTrue, vbFalse, vbTrue)
   TotalAreaDispLabel.Caption = FormatNumber(AreaInSquareFeet, 0, vbTrue, vbFalse, vbTrue) & " sq. ft."
   TotalAcresLabel.Caption = FormatNumber((Round(AreaInSquareFeet, 0) / Square_Feet_Per_Acre), 3, vbTrue, vbFalse, vbTrue) & " acres"
End Sub



'*************************************************************************************************************
'*************************************CHANGE HANDLERS*********************************************************
Public Sub CalcAndDrawCourses()
   DrawTheCourses GetStartPoint(), Mode_Draw_Transient_Hilite_Sel
End Sub



Public Sub UpdateAll()
   WriteLotFile
   CalcAndDrawCourses
   OutputButtonsStates
   TransformationStates
   EditDelButtonsStates
   AddDGNButtonStates
End Sub



Private Sub WriteLotFileIfLoaded()
   If IsFileLoaded() Then
      WriteLotFile
   End If
End Sub



'*************************************************************************************************************
'***************************************PROCESSING THE COURSES************************************************
Private Sub AddCourseToFileOrCell(TheElementToAdd As Element)
   If AllCoursesCheckBox.value = False Then
'ADD TO FILE HERE
      ActiveModelReference.AddElement TheElementToAdd
   ElseIf CreateAsCellCheckBox.value Then
'ADD TO CELL ARRAY HERE
      AddElementToCellArray TheElementToAdd
   Else
'ADD TO FILE HERE
      ActiveModelReference.AddElement TheElementToAdd
   End If
End Sub



Private Sub AddCourseToFileOrCellOrComplex(TheElementToAdd As Element)
   If AllCoursesCheckBox.value = False Then
'ADD TO FILE HERE
      ActiveModelReference.AddElement TheElementToAdd
   ElseIf ComplexCheckBox.value Then
'ADD ELEMENT TO COMPLEX CHAIN ARRAY
      AddElementToComplexArray TheElementToAdd
   ElseIf CreateAsCellCheckBox.value Then
'ADD TO CELL ARRAY HERE
      AddElementToCellArray TheElementToAdd
   Else
'ADD TO FILE HERE
      ActiveModelReference.AddElement TheElementToAdd
   End If
End Sub



Private Sub CurveByChordToElement(chordAzString As String, _
                                  ByVal TheIndex As Long, _
                                  beginPoint As Point3d, _
                                  ByRef latitude As Double, _
                                  ByRef departure As Double, _
                                  endPoint As Point3d, _
                                  chordString As String, _
                                  theChord As Double, _
                                  theRadius As Double, _
                                  radiusPoint As Point3d, _
                                  lefthandCurve As Boolean, _
                                  delta As Double, _
                                  theArcElement As ArcElement)

'MAKE WORKING COPY OF BEGIN POINT
   Dim workingPoint As Point3d
   workingPoint = beginPoint

'CONVERT CHORD AZIMUTH STRING TO SOUTH AZIMUTH
   Dim sAzimuth As Double
   Dim origPrec As Long
   Dim dirType As Integer
   Dim quad As Integer
   If Not DirStringToSAz(chordAzString, sAzimuth, origPrec, dirType, quad) Then
     Err.Raise ERROR_NUM_541
   End If

'CONVERT CHORD DISTANCE DOUBLE
   Dim wholeString As String
   wholeString = CoursesListBox.List(TheIndex, Lot_Closure_Column_Data_2)
   Dim temp As String
   SplitData wholeString, temp, chordString
   If IsNumeric(chordString) Then
      theChord = CDbl(chordString)
   Else
        Err.Raise ERROR_NUM_542
   End If

'GET THE RADIUS INTO DOUBLE
   wholeString = CoursesListBox.List(TheIndex, Lot_Closure_Column_Data_3)
   Dim radiusString As String
   SplitData wholeString, temp, radiusString
   If IsNumeric(radiusString) Then
      theRadius = CDbl(radiusString)
   Else
      Err.Raise ERROR_NUM_543
   End If

'CALCULATE END POINT
   endPoint = CoordFwdSAz2(workingPoint, sAzimuth, theChord, latitude, departure)

'GET ROTATION STRING
   wholeString = CoursesListBox.List(TheIndex, Lot_Closure_Column_Data_4)
   Dim rotString As String
   SplitData wholeString, temp, rotString
   
'GET SIZE STRING
   wholeString = CoursesListBox.List(TheIndex, Lot_Closure_Column_Data_5)
   Dim sizeString As String
   SplitData wholeString, temp, sizeString
   
'CALCULATE MID CHORD POINT
   Dim theMidPoint As Point3d
   theMidPoint = CalcMidPoint(workingPoint, endPoint)
   
'DETEREMINE IF LEFT HAND CURVE, CALCULATE RADIUS POINT
   Dim a As Double
   a = Calc_a(theRadius, theChord)
   If sizeString = Lot_Closure_Data_Size_Small Or theRadius = theChord / 2# Then
      If rotString = Lot_Closure_Data_Rot_Left Then
         radiusPoint = CoordFwdSAz(theMidPoint, sAzimuth + 270#, a)
         lefthandCurve = True
      Else
         radiusPoint = CoordFwdSAz(theMidPoint, sAzimuth + 90#, a)
         lefthandCurve = False
      End If
   Else
      If rotString = Lot_Closure_Data_Rot_Left Then
         radiusPoint = CoordFwdSAz(theMidPoint, sAzimuth + 90#, a)
         lefthandCurve = True
      Else
         radiusPoint = CoordFwdSAz(theMidPoint, sAzimuth + 270#, a)
         lefthandCurve = False
      End If
   End If

'CALCULATE DELTA
   If a >= theRadius Or theChord <= 0 Then 'should not occur, delta either 0 or 360
      If sizeString = Lot_Closure_Data_Size_Small Then
         delta = 0#
      Else
         delta = 360#
      End If
   ElseIf theChord >= theRadius + theRadius Then
      delta = 180#
   Else
      Dim halfDelta As Double
      halfDelta = 90# - Degrees(Atn(a / (theChord / 2#)))
      delta = halfDelta + halfDelta
      If sizeString = Lot_Closure_Data_Size_Large Then
         delta = 360# - delta
      End If
   End If

'CREATE THE ARC ELEMENT
   If rotString = Lot_Closure_Data_Rot_Left Then
      Set theArcElement = CreateArcElement1(Nothing, workingPoint, radiusPoint, endPoint)
   Else
      Set theArcElement = CreateArcElement1(Nothing, endPoint, radiusPoint, workingPoint)
   End If
End Sub



Private Sub CurveByRadialsToElement(radialInString As String, _
                                    ByVal TheIndex As Long, _
                                    beginPoint As Point3d, _
                                    ByRef latitude As Double, _
                                    ByRef departure As Double, _
                                    endPoint As Point3d, _
                                    theRadius As Double, _
                                    radiusPoint As Point3d, _
                                    lefthandCurve As Boolean, _
                                    delta As Double, _
                                    theArcElement As ArcElement, _
                                    ByRef origPrecIn As Long, _
                                    ByRef origPrecOut As Long, _
                                    ByRef radialInSAz As Double, _
                                    ByRef dirInType As Integer)

'MAKE WORKING COPY OF BEGIN POINT
   Dim workingPoint As Point3d
   workingPoint = beginPoint

'CONVERT RADIAL IN STRING TO SOUTH AZIMUTH
   Dim quad As Integer
   If Not DirStringToSAz(radialInString, radialInSAz, origPrecIn, dirInType, quad) Then
      Err.Raise ERROR_NUM_545
   End If

'GET THE RADIUS INTO DOUBLE
   Dim wholeString As String
   Dim temp As String
   Dim radiusString As String
   wholeString = CoursesListBox.List(TheIndex, Lot_Closure_Column_Data_2)
   SplitData wholeString, temp, radiusString
   If IsNumeric(radiusString) Then
      theRadius = CDbl(radiusString)
   Else
      Err.Raise ERROR_NUM_546
   End If

'GET THE RADIAL OUT INTO SOUTH AZIMUTH
   Dim radialOutString As String
   wholeString = CoursesListBox.List(TheIndex, Lot_Closure_Column_Data_3)
   SplitData wholeString, temp, radialOutString
   Dim radialOutSAz As Double
   Dim dirType As Integer
   If Not DirStringToSAz(radialOutString, radialOutSAz, origPrecOut, dirType, quad) Then
      Err.Raise ERROR_NUM_547
   End If
   
'GET SIZE STRING
   Dim sizeString As String
   wholeString = CoursesListBox.List(TheIndex, Lot_Closure_Column_Data_4)
   SplitData wholeString, temp, sizeString

'CALCULATE END POINT AND RADIUS POINT
   Dim LatTemp As Double
   Dim DepTemp As Double
   radiusPoint = CoordFwdSAz2(workingPoint, radialInSAz, theRadius, LatTemp, DepTemp)
   Dim LatTemp2 As Double
   Dim DepTemp2 As Double
   endPoint = CoordFwdSAz2(radiusPoint, radialOutSAz, theRadius, LatTemp2, DepTemp2)
   latitude = LatTemp + LatTemp2
   departure = DepTemp + DepTemp2
   
'DETEMINE LEFT OR RIGHT AND DELTA
   Dim relativeAngle As Double
   relativeAngle = To360(radialInSAz, radialOutSAz)
   If sizeString = Lot_Closure_Data_Size_Small Then
      If relativeAngle <= 180# Then
         lefthandCurve = False
         delta = relativeAngle
      Else
         lefthandCurve = True
         delta = 360# - relativeAngle
      End If
   Else
      If relativeAngle <= 180# Then
         lefthandCurve = True
         delta = 360# - relativeAngle
      Else
         lefthandCurve = False
         delta = relativeAngle
      End If
      If delta = 0# Then
         delta = 360#
      End If
   End If

'GENERATE ARC ELEMENT
   If lefthandCurve Then
      Set theArcElement = CreateArcElement1(Nothing, workingPoint, radiusPoint, endPoint)
   Else
      Set theArcElement = CreateArcElement1(Nothing, endPoint, radiusPoint, workingPoint)
   End If
End Sub



Private Sub CurveByTangentsToElement(tangentInString As String, _
                                     ByVal TheIndex As Long, _
                                     beginPoint As Point3d, _
                                     ByRef latitude As Double, _
                                     ByRef departure As Double, _
                                     endPoint As Point3d, _
                                     theRadius As Double, _
                                     radiusPoint As Point3d, _
                                     lefthandCurve As Boolean, _
                                     delta As Double, _
                                     theArcElement As ArcElement, _
                                     ByRef origInPrec As Long, _
                                     ByRef origOutPrec As Long, _
                                     ByRef tanInSAz As Double, _
                                     ByRef dirInType As Integer)
                                    
'MAKE WORKING COPY OF BEGIN POINT
   Dim workingPoint As Point3d
   workingPoint = beginPoint

'CONVERT TANGENT IN STRING TO SOUTH AZIMUTH
   Dim quad As Integer
   If Not DirStringToSAz(tangentInString, tanInSAz, origInPrec, dirInType, quad) Then
     Err.Raise ERROR_NUM_548
   End If

'GET THE RADIUS INTO DOUBLE
   Dim wholeString As String
   wholeString = CoursesListBox.List(TheIndex, Lot_Closure_Column_Data_2)
   Dim temp As String
   Dim radiusString As String
   SplitData wholeString, temp, radiusString
   If IsNumeric(radiusString) Then
      theRadius = CDbl(radiusString)
   Else
      Err.Raise ERROR_NUM_549
   End If

'GET THE TANGENT OUT INTO SOUTH AZIMUTH
   Dim tangentOutString As String
   wholeString = CoursesListBox.List(TheIndex, Lot_Closure_Column_Data_3)
   SplitData wholeString, temp, tangentOutString
   Dim tanOutSAz As Double
   Dim dirOutType As Integer
   If Not DirStringToSAz(tangentOutString, tanOutSAz, origOutPrec, dirOutType, quad) Then
     Err.Raise ERROR_NUM_550
   End If

'GET SIZE STRING
   Dim sizeString As String
   wholeString = CoursesListBox.List(TheIndex, Lot_Closure_Column_Data_4)
   SplitData wholeString, temp, sizeString
 
'DETEMINE LEFT OR RIGHT AND DELTA
   Dim relativeAngle As Double
   relativeAngle = To360(tanInSAz, tanOutSAz)
   If sizeString = Lot_Closure_Data_Size_Small Then
      If relativeAngle >= 180# Then
         lefthandCurve = False
         delta = relativeAngle - 180#
      Else
         lefthandCurve = True
         delta = 180# - relativeAngle
      End If
   Else
      If relativeAngle <= 180# Then
         lefthandCurve = False
         delta = 360# - (180# - relativeAngle)
      Else
         lefthandCurve = True
         delta = 360# - (relativeAngle - 180#)
      End If
      If delta = 0 Then
         delta = 360#
      End If
   End If

'GENERATE ARC ELEMENT, CALCULATE END POINT
   If lefthandCurve Then
      Dim LatTemp As Double
      Dim DepTemp As Double
      radiusPoint = CoordFwdSAz2(workingPoint, tanInSAz + 270#, theRadius, LatTemp, DepTemp)
      Dim LatTemp2 As Double
      Dim DepTemp2 As Double
      endPoint = CoordFwdSAz2(radiusPoint, tanOutSAz + 90#, theRadius, LatTemp2, DepTemp2)
      Set theArcElement = CreateArcElement1(Nothing, workingPoint, radiusPoint, endPoint)
   Else
      radiusPoint = CoordFwdSAz2(workingPoint, tanInSAz + 90#, theRadius, LatTemp, DepTemp)
      endPoint = CoordFwdSAz2(radiusPoint, tanOutSAz + 270#, theRadius, LatTemp2, DepTemp2)
      Set theArcElement = CreateArcElement1(Nothing, endPoint, radiusPoint, workingPoint)
   End If
   latitude = LatTemp + LatTemp2
   departure = DepTemp + DepTemp2
End Sub



Private Sub CurveByTanOutChrToElement(tangentOutString As String, _
                                      ByVal TheIndex As Long, _
                                      beginPoint As Point3d, _
                                      ByRef latitude As Double, _
                                      ByRef departure As Double, _
                                      endPoint As Point3d, _
                                      theRadius As Double, _
                                      radiusPoint As Point3d, _
                                      lefthandCurve As Boolean, _
                                      delta As Double, _
                                      theArcElement As ArcElement, _
                                      ByRef chdDirString As String, _
                                      ByRef chdDirPrec As Long, _
                                      ByRef tanOutPrec As Long, _
                                      ByRef tanOutType As Integer, _
                                      ByRef radialInSAz As Double, _
                                      ByRef radialOutSAz As Double)
                                    
'MAKE WORKING COPY OF BEGIN POINT
   Dim workingPoint As Point3d
   workingPoint = beginPoint

'CONVERT TANGENT OUT STRING TO SOUTH AZIMUTH
   Dim quad As Integer
   Dim tanOutSAz As Double
   If Not DirStringToSAz(tangentOutString, tanOutSAz, tanOutPrec, tanOutType, quad) Then
     Err.Raise ERROR_NUM_556
   End If

'GET THE RADIUS INTO DOUBLE
   Dim wholeString As String
   wholeString = CoursesListBox.List(TheIndex, Lot_Closure_Column_Data_2)
   Dim temp As String
   Dim radiusString As String
   SplitData wholeString, temp, radiusString
   If IsNumeric(radiusString) Then
      theRadius = CDbl(radiusString)
   Else
      Err.Raise ERROR_NUM_557
   End If

'GET THE CHORD DIRECTION INTO SOUTH AZIMUTH
   wholeString = CoursesListBox.List(TheIndex, Lot_Closure_Column_Data_3)
   SplitData wholeString, temp, chdDirString
   Dim chdSAz As Double
   Dim chdType As Integer
   If Not DirStringToSAz(chdDirString, chdSAz, chdDirPrec, chdType, quad) Then
     Err.Raise ERROR_NUM_558
   End If
 
'DETEMINE LEFT OR RIGHT AND DELTA
   Dim relativeAngle As Double
   Dim tanInSAz As Double
   relativeAngle = To360(chdSAz, tanOutSAz)
   If relativeAngle >= 180# Then
      lefthandCurve = False
      delta = (relativeAngle - 180#) * 2#
      tanInSAz = tanOutSAz - delta
   Else
      lefthandCurve = True
      delta = (180# - relativeAngle) * 2#
      tanInSAz = tanOutSAz + delta
   End If
   MakeSure360 tanInSAz

'GENERATE ARC ELEMENT, CALCULATE END POINT
   If lefthandCurve Then
      Dim LatTemp As Double
      Dim DepTemp As Double
      radialInSAz = tanInSAz + 270#
      MakeSure360 radialInSAz
      radiusPoint = CoordFwdSAz2(workingPoint, radialInSAz, theRadius, LatTemp, DepTemp)
      Dim LatTemp2 As Double
      Dim DepTemp2 As Double
      radialOutSAz = tanOutSAz + 90#
      MakeSure360 radialOutSAz
      endPoint = CoordFwdSAz2(radiusPoint, radialOutSAz, theRadius, LatTemp2, DepTemp2)
      Set theArcElement = CreateArcElement1(Nothing, workingPoint, radiusPoint, endPoint)
   Else
      radialInSAz = tanInSAz + 90#
      MakeSure360 radialInSAz
      radiusPoint = CoordFwdSAz2(workingPoint, radialInSAz, theRadius, LatTemp, DepTemp)
      radialOutSAz = tanOutSAz + 270#
      MakeSure360 radialOutSAz
      endPoint = CoordFwdSAz2(radiusPoint, radialOutSAz, theRadius, LatTemp2, DepTemp2)
      Set theArcElement = CreateArcElement1(Nothing, endPoint, radiusPoint, workingPoint)
   End If

'FIX IF DELTA IS ZERO
   If relativeAngle = 180 Then
      theArcElement.SweepAngle = 0
   End If

'RETURN LATITUDE AND DEPARTURE
   latitude = LatTemp + LatTemp2
   departure = DepTemp + DepTemp2
End Sub
                                    
                                    
                                    
Private Sub CurveByTanInChrToElement(radiusString As String, _
                                     ByVal TheIndex As Long, _
                                     beginPoint As Point3d, _
                                     ByRef latitude As Double, _
                                     ByRef departure As Double, _
                                     endPoint As Point3d, _
                                     theRadius As Double, _
                                     radiusPoint As Point3d, _
                                     lefthandCurve As Boolean, _
                                     delta As Double, _
                                     theArcElement As ArcElement, _
                                     ByRef chdDirString As String, _
                                     ByRef chdDirPrec As Long, _
                                     ByRef tanInPrec As Long, _
                                     ByRef tanInType As Integer, _
                                     ByRef radialInSAz As Double, _
                                     ByRef radialOutSAz As Double)
                                    
'MAKE WORKING COPY OF BEGIN POINT
   Dim workingPoint As Point3d
   workingPoint = beginPoint

'GET THE RADIUS INTO DOUBLE
   If IsNumeric(radiusString) Then
      theRadius = CDbl(radiusString)
   Else
      Err.Raise ERROR_NUM_559
   End If

'CONVERT TANGENT IN STRING TO SOUTH AZIMUTH
   Dim wholeString As String
   wholeString = CoursesListBox.List(TheIndex, Lot_Closure_Column_Data_2)
   Dim temp As String
   Dim tangentInString As String
   SplitData wholeString, temp, tangentInString
   Dim quad As Integer
   Dim tanInSAz As Double
   If Not DirStringToSAz(tangentInString, tanInSAz, tanInPrec, tanInType, quad) Then
     Err.Raise ERROR_NUM_560
   End If

'GET THE CHORD DIRECTION INTO SOUTH AZIMUTH
   wholeString = CoursesListBox.List(TheIndex, Lot_Closure_Column_Data_3)
   SplitData wholeString, temp, chdDirString
   Dim chdSAz As Double
   Dim chdType As Integer
   If Not DirStringToSAz(chdDirString, chdSAz, chdDirPrec, chdType, quad) Then
     Err.Raise ERROR_NUM_561
   End If
 
'DETEMINE LEFT OR RIGHT AND DELTA
   Dim relativeAngle As Double
   relativeAngle = To360(tanInSAz, chdSAz)
   If relativeAngle >= 180# Then
      lefthandCurve = False
      delta = (relativeAngle - 180#) * 2#
      Dim tanOutSAz As Double
      tanOutSAz = tanInSAz + delta
   Else
      lefthandCurve = True
      delta = (180# - relativeAngle) * 2#
      tanOutSAz = tanInSAz - delta
   End If
   MakeSure360 tanOutSAz

'GENERATE ARC ELEMENT, CALCULATE END POINT
   If lefthandCurve Then
      Dim LatTemp As Double
      Dim DepTemp As Double
      radialInSAz = tanInSAz + 270#
      MakeSure360 radialInSAz
      radiusPoint = CoordFwdSAz2(workingPoint, radialInSAz, theRadius, LatTemp, DepTemp)
      Dim LatTemp2 As Double
      Dim DepTemp2 As Double
      radialOutSAz = tanOutSAz + 90#
      MakeSure360 radialOutSAz
      endPoint = CoordFwdSAz2(radiusPoint, radialOutSAz, theRadius, LatTemp2, DepTemp2)
      Set theArcElement = CreateArcElement1(Nothing, workingPoint, radiusPoint, endPoint)
   Else
      radialInSAz = tanInSAz + 90#
      MakeSure360 radialInSAz
      radiusPoint = CoordFwdSAz2(workingPoint, radialInSAz, theRadius, LatTemp, DepTemp)
      radialOutSAz = tanOutSAz + 270#
      MakeSure360 radialOutSAz
      endPoint = CoordFwdSAz2(radiusPoint, radialOutSAz, theRadius, LatTemp2, DepTemp2)
      Set theArcElement = CreateArcElement1(Nothing, endPoint, radiusPoint, workingPoint)
   End If

'FIX IF DELTA IS ZERO
   If relativeAngle = 180 Then
      theArcElement.SweepAngle = 0
   End If

'RETURN LATITUDE AND DEPARTURE
   latitude = LatTemp + LatTemp2
   departure = DepTemp + DepTemp2
End Sub
                                    


Private Sub DisplayElement(ByVal ListboxIndex As Long, _
                           theElement As Element, _
                           ByVal CourseDrawMode As Long, _
                           Optional DrawMode As MsdDrawingMode = msdDrawingModeNormal)
'TEMPORARY GRAPHICS
   Select Case CourseDrawMode
      Case Mode_Draw_Transient_Hilite_Sel
         If CoursesListBox.Selected(ListboxIndex) = True Then
            tecHilite.AppendCopyOfElement theElement
         Else
            tecNormal.AppendCopyOfElement theElement
         End If
      Case Mode_Draw_Transient_Blank_Sel
         If CoursesListBox.Selected(ListboxIndex) = False Then
            tecHilite.AppendCopyOfElement theElement
         End If
      Case Mode_Draw_Transient_Hilite_All
         tecHilite.AppendCopyOfElement theElement
      Case Mode_Draw_Dynamic
         theElement.Redraw DrawMode
      Case Else
         If CoursesListBox.Selected(ListboxIndex) = True Then
            tecHilite.AppendCopyOfElement theElement
         Else
            tecNormal.AppendCopyOfElement theElement
         End If
   End Select
End Sub






Private Function DrawCurveByChord(chordAzString As String, _
                                  ByVal TheIndex As Long, _
                                  beginPoint As Point3d, _
                                  ByVal CourseDrawMode As Long, _
                                  ByRef latitude As Double, _
                                  ByRef departure As Double, _
                                  Optional DrawMode As MsdDrawingMode = msdDrawingModeNormal) As Point3d
'BROKE THIS ROUTINE INTO TWO PIECES FOR LEG SEARCH ROUTINE
   Dim chordString As String
   Dim theChord As Double
   Dim theRadius As Double
   Dim endPoint As Point3d
   Dim radiusPoint As Point3d
   Dim lefthandCurve As Boolean
   Dim delta As Double
   Dim theArcElement As ArcElement
   CurveByChordToElement chordAzString, _
                         TheIndex, _
                         beginPoint, _
                         latitude, _
                         departure, _
                         endPoint, _
                         chordString, _
                         theChord, _
                         theRadius, _
                         radiusPoint, _
                         lefthandCurve, _
                         delta, _
                         theArcElement

'CALCULATE SEGMENT AREA HERE, ADD IT TO THE SUM
   Dim TheSegmentArea As Double
   TheSegmentArea = SegmentArea(delta, theChord, theRadius, lefthandCurve)
   AddToCurveArea TheSegmentArea

'CALCULATE ARC LENGTH HERE, ADD IT TO THE SUM
   AddToPerimeter ArcLength(delta, theRadius)

'WRITE REPORT STUFF HERE
   If CourseDrawMode = Mode_Draw_Report Then
      ReportCurveInput TheIndex, True
      Dim RadIn As Double
      Dim dummy As Double
      Inverse beginPoint, radiusPoint, RadIn, dummy
      Dim RadOut As Double
      Inverse radiusPoint, endPoint, RadOut, dummy
      Dim origPrec As Long
      Dim degPart As Long
      Dim minPart As Long
      Dim secPart As Double
      Dim dirType As Integer
      Dim quad As Integer
      If Not IsDirString(chordAzString, origPrec, degPart, minPart, secPart, dirType, quad) Then
         Err.Raise ERROR_NUM_544
      End If
      ReportCurveData2 TheSegmentArea, dirType, RadIn, RadOut, radiusPoint, origPrec
      ReportCoordinateString endPoint.Y, endPoint.X
   End If

'WRITE BOUNDARY REPORT STUFF HERE
   ReportBoundaryArcPart TheIndex, theArcElement, CourseDrawMode, True

'FILL IN COURSE INFO HERE
   If CourseDrawMode <> Mode_Draw_Transient_Blank_Sel And CoursesListBox.Selected(TheIndex) = True Then
      CurveCourseInfo TheIndex, beginPoint, endPoint, radiusPoint, chordAzString, chordString, TheSegmentArea
   End If

'DRAW THE ELEMENT
   DrawTheArcAndStuff theArcElement, beginPoint, endPoint, radiusPoint, lefthandCurve, TheIndex, CourseDrawMode, DrawMode

'RETURN THE END POINT
   DrawCurveByChord = endPoint
End Function



Private Function DrawCurveByRadials(radialInString As String, _
                                    ByVal TheIndex As Long, _
                                    beginPoint As Point3d, _
                                    ByVal CourseDrawMode As Long, _
                                    ByRef latitude As Double, _
                                    ByRef departure As Double, _
                                    Optional DrawMode As MsdDrawingMode = msdDrawingModeNormal) As Point3d

'MAKE WORKING COPY OF BEGIN POINT
   Dim workingPoint As Point3d
   workingPoint = beginPoint

'BROKE THIS ROUTINE INTO TWO PIECES FOR LEG SEARCH ROUTINE
   Dim theRadius As Double
   Dim radiusPoint As Point3d
   Dim endPoint As Point3d
   Dim lefthandCurve As Boolean
   Dim delta As Double
   Dim theArcElement As ArcElement
   Dim origPrecIn As Long
   Dim origPrecOut As Long
   Dim radialInSAz As Double
   Dim radialInType As Integer
   CurveByRadialsToElement radialInString, _
                           TheIndex, _
                           beginPoint, _
                           latitude, _
                           departure, _
                           endPoint, _
                           theRadius, _
                           radiusPoint, _
                           lefthandCurve, _
                           delta, _
                           theArcElement, _
                           origPrecIn, _
                           origPrecOut, _
                           radialInSAz, _
                           radialInType


'CALCULATE CHORD
   Dim ChordAzimuth As Double
   Dim ChordDistance As Double
   Inverse workingPoint, endPoint, ChordAzimuth, ChordDistance
   Dim rightAngle As Double
   rightAngle = -90#
   If lefthandCurve Then
      rightAngle = -rightAngle
   End If
   Dim tangentInSAz As Double
   tangentInSAz = radialInSAz + rightAngle
   MakeSure360 tangentInSAz
   ChordAzimuth = chordAz(tangentInSAz, delta, lefthandCurve)
   Dim chordDirPrecision As Long
   chordDirPrecision = MaxLong(origPrecIn, origPrecOut) + 1

'CALCULATE SEGMENT AREA HERE, ADD IT TO THE SUM
   Dim TheSegmentArea As Double
   TheSegmentArea = SegmentArea(delta, ChordDistance, theRadius, lefthandCurve)
   AddToCurveArea TheSegmentArea

'CALCULATE ARC LENGTH HERE, ADD IT TO THE SUM
   AddToPerimeter ArcLength(delta, theRadius)

'WRITE REPORT STUFF HERE
   If CourseDrawMode = Mode_Draw_Report Then
      ReportCurveInput TheIndex, False
      ReportCurveData TheSegmentArea, ChordAzimuth, ChordDistance, lefthandCurve, radiusPoint, chordDirPrecision, radialInType
      ReportCoordinateString endPoint.Y, endPoint.X
   End If

'WRITE BOUNDARY REPORT STUFF HERE
   ReportBoundaryArcPart TheIndex, theArcElement, CourseDrawMode, True

'FILL IN COURSE INFO HERE
   If CourseDrawMode <> Mode_Draw_Transient_Blank_Sel And CoursesListBox.Selected(TheIndex) = True Then
      Dim ChordAzimuthString As String
      ChordAzimuthString = SAzToDirectionStr(ChordAzimuth, chordDirPrecision, radialInType, PlotLotEntryAngleStyle)
      Dim ChordDistanceString As String
      ChordDistanceString = FormatNumber(ChordDistance, CLng(ChordPrecisionComboBox.text), vbTrue, vbFalse, vbTrue)
      CurveCourseInfo TheIndex, workingPoint, endPoint, radiusPoint, ChordAzimuthString, ChordDistanceString, TheSegmentArea
   End If

'DRAW THE ELEMENT
   DrawTheArcAndStuff theArcElement, workingPoint, endPoint, radiusPoint, lefthandCurve, TheIndex, CourseDrawMode, DrawMode

'RETURN THE END POINT
   DrawCurveByRadials = endPoint
End Function



Private Function DrawCurveByTangents(tangentInString As String, _
                                     ByVal TheIndex As Long, _
                                     beginPoint As Point3d, _
                                     ByVal CourseDrawMode As Long, _
                                     ByRef latitude As Double, _
                                     ByRef departure As Double, _
                                     Optional DrawMode As MsdDrawingMode = msdDrawingModeNormal) As Point3d
'MAKE WORKING COPY OF BEGIN POINT
   Dim workingPoint As Point3d
   workingPoint = beginPoint

'BROKE THIS ROUTINE INTO TWO PIECES FOR LEG SEARCH ROUTINE
   Dim theRadius As Double
   Dim delta As Double
   Dim lefthandCurve As Boolean
   Dim radiusPoint As Point3d
   Dim endPoint As Point3d
   Dim theArcElement As ArcElement
   Dim tanInSAz As Double
   Dim tanInType As Integer
   Dim origPrecIn As Long
   Dim origPrecOut As Long
   CurveByTangentsToElement tangentInString, _
                            TheIndex, _
                            beginPoint, _
                            latitude, _
                            departure, _
                            endPoint, _
                            theRadius, _
                            radiusPoint, _
                            lefthandCurve, _
                            delta, _
                            theArcElement, _
                            origPrecIn, _
                            origPrecOut, _
                            tanInSAz, _
                            tanInType

'CALCULATE CHORD
   Dim ChordAzimuth As Double
   Dim ChordDistance As Double
   Inverse workingPoint, endPoint, ChordAzimuth, ChordDistance
   ChordAzimuth = chordAz(tanInSAz, delta, lefthandCurve)
   Dim chordDirPrecision As Long
   chordDirPrecision = MaxLong(origPrecIn, origPrecOut) + 1

'CALCULATE SEGMENT AREA HERE, ADD IT TO THE SUM
   Dim TheSegmentArea As Double
   TheSegmentArea = SegmentArea(delta, ChordDistance, theRadius, lefthandCurve)
   AddToCurveArea TheSegmentArea

'CALCULATE ARC LENGTH HERE, ADD IT TO THE SUM
   AddToPerimeter ArcLength(delta, theRadius)

'WRITE REPORT STUFF HERE
   If CourseDrawMode = Mode_Draw_Report Then
      ReportCurveInput TheIndex, False
      ReportCurveData TheSegmentArea, ChordAzimuth, ChordDistance, lefthandCurve, radiusPoint, chordDirPrecision, tanInType
      ReportCoordinateString endPoint.Y, endPoint.X
   End If

'WRITE BOUNDARY REPORT STUFF HERE
   ReportBoundaryArcPart TheIndex, theArcElement, CourseDrawMode, True

'FILL IN COURSE INFO HERE
   If CourseDrawMode <> Mode_Draw_Transient_Blank_Sel And CoursesListBox.Selected(TheIndex) = True Then
      Dim ChordAzimuthString As String
      ChordAzimuthString = SAzToDirectionStr(ChordAzimuth, chordDirPrecision, tanInType, PlotLotEntryAngleStyle)
      Dim ChordDistanceString As String
      ChordDistanceString = FormatNumber(ChordDistance, CLng(ChordPrecisionComboBox.text), vbTrue, vbFalse, vbTrue)
      CurveCourseInfo TheIndex, workingPoint, endPoint, radiusPoint, ChordAzimuthString, ChordDistanceString, TheSegmentArea
   End If

'DRAW THE ELEMENT
   DrawTheArcAndStuff theArcElement, workingPoint, endPoint, radiusPoint, lefthandCurve, TheIndex, CourseDrawMode, DrawMode

'RETURN THE END POINT
   DrawCurveByTangents = endPoint
End Function



Private Function DrawCurveByTanOutChd(tangentOutString As String, _
                                      ByVal TheIndex As Long, _
                                      beginPoint As Point3d, _
                                      ByVal CourseDrawMode As Long, _
                                      ByRef latitude As Double, _
                                      ByRef departure As Double, _
                                      Optional DrawMode As MsdDrawingMode = msdDrawingModeNormal) As Point3d
'MAKE WORKING COPY OF BEGIN POINT
   Dim workingPoint As Point3d
   workingPoint = beginPoint

'BROKE THIS ROUTINE INTO TWO PIECES FOR LEG SEARCH ROUTINE
   Dim theRadius As Double
   Dim delta As Double
   Dim lefthandCurve As Boolean
   Dim radiusPoint As Point3d
   Dim endPoint As Point3d
   Dim theArcElement As ArcElement
   Dim tanOutPrec As Long
   Dim tanOutType As Integer
   Dim chdDirPrec As Long
   Dim chdDirString As String
   Dim radialInSAz As Double
   Dim radialOutSAz As Double
   
   CurveByTanOutChrToElement tangentOutString, _
                             TheIndex, _
                             beginPoint, _
                             latitude, _
                             departure, _
                             endPoint, _
                             theRadius, _
                             radiusPoint, _
                             lefthandCurve, _
                             delta, _
                             theArcElement, _
                             chdDirString, _
                             chdDirPrec, _
                             tanOutPrec, _
                             tanOutType, _
                             radialInSAz, _
                             radialOutSAz
                             

'CALCULATE CHORD
   Dim ChordDistance As Double
   ChordDistance = InverseHD(workingPoint, endPoint)

'CALCULATE SEGMENT AREA HERE, ADD IT TO THE SUM
   Dim TheSegmentArea As Double
   TheSegmentArea = SegmentArea(delta, ChordDistance, theRadius, lefthandCurve)
   AddToCurveArea TheSegmentArea

'CALCULATE ARC LENGTH HERE, ADD IT TO THE SUM
   AddToPerimeter ArcLength(delta, theRadius)

'WRITE REPORT STUFF HERE
   If CourseDrawMode = Mode_Draw_Report Then
      ReportCurveInputChdTanOut TheIndex
      ReportCurveData3 TheSegmentArea, ChordDistance, lefthandCurve, tanOutType, radialInSAz, radialOutSAz, radiusPoint, MaxLong(chdDirPrec, tanOutPrec)
      ReportCoordinateString endPoint.Y, endPoint.X
   End If

'WRITE BOUNDARY REPORT STUFF HERE
   ReportBoundaryArcPart TheIndex, theArcElement, CourseDrawMode, True

'FILL IN COURSE INFO HERE
   If CourseDrawMode <> Mode_Draw_Transient_Blank_Sel And CoursesListBox.Selected(TheIndex) = True Then
      Dim ChordDistanceString As String
      ChordDistanceString = FormatNumber(ChordDistance, CLng(ChordPrecisionComboBox.text), vbTrue, vbFalse, vbTrue)
      CurveCourseInfo TheIndex, workingPoint, endPoint, radiusPoint, chdDirString, ChordDistanceString, TheSegmentArea
   End If

'DRAW THE ELEMENT
   DrawTheArcAndStuff theArcElement, workingPoint, endPoint, radiusPoint, lefthandCurve, TheIndex, CourseDrawMode, DrawMode

'RETURN THE END POINT
   DrawCurveByTanOutChd = endPoint
End Function



Private Function DrawCurveByTanInChd(radiusString As String, _
                                     ByVal TheIndex As Long, _
                                     beginPoint As Point3d, _
                                     ByVal CourseDrawMode As Long, _
                                     ByRef latitude As Double, _
                                     ByRef departure As Double, _
                                     Optional DrawMode As MsdDrawingMode = msdDrawingModeNormal) As Point3d
'MAKE WORKING COPY OF BEGIN POINT
   Dim workingPoint As Point3d
   workingPoint = beginPoint

'BROKE THIS ROUTINE INTO TWO PIECES FOR LEG SEARCH ROUTINE
   Dim theRadius As Double
   Dim delta As Double
   Dim lefthandCurve As Boolean
   Dim radiusPoint As Point3d
   Dim endPoint As Point3d
   Dim theArcElement As ArcElement
   Dim tanInPrec As Long
   Dim tanInType As Integer
   Dim chdDirPrec As Long
   Dim chdDirString As String
   Dim radialInSAz As Double
   Dim radialOutSAz As Double
   
   CurveByTanInChrToElement radiusString, _
                            TheIndex, _
                            beginPoint, _
                            latitude, _
                            departure, _
                            endPoint, _
                            theRadius, _
                            radiusPoint, _
                            lefthandCurve, _
                            delta, _
                            theArcElement, _
                            chdDirString, _
                            chdDirPrec, _
                            tanInPrec, _
                            tanInType, _
                            radialInSAz, _
                            radialOutSAz
                             
'CALCULATE CHORD
   Dim ChordDistance As Double
   ChordDistance = InverseHD(workingPoint, endPoint)

'CALCULATE SEGMENT AREA HERE, ADD IT TO THE SUM
   Dim TheSegmentArea As Double
   TheSegmentArea = SegmentArea(delta, ChordDistance, theRadius, lefthandCurve)
   AddToCurveArea TheSegmentArea

'CALCULATE ARC LENGTH HERE, ADD IT TO THE SUM
   AddToPerimeter ArcLength(delta, theRadius)

'WRITE REPORT STUFF HERE
   If CourseDrawMode = Mode_Draw_Report Then
      ReportCurveInputChdTanIn TheIndex
      ReportCurveData3 TheSegmentArea, ChordDistance, lefthandCurve, tanInType, radialInSAz, radialOutSAz, radiusPoint, MaxLong(chdDirPrec, tanInPrec)
      ReportCoordinateString endPoint.Y, endPoint.X
   End If

'WRITE BOUNDARY REPORT STUFF HERE
   ReportBoundaryArcPart TheIndex, theArcElement, CourseDrawMode, True

'FILL IN COURSE INFO HERE
   If CourseDrawMode <> Mode_Draw_Transient_Blank_Sel And CoursesListBox.Selected(TheIndex) = True Then
      Dim ChordDistanceString As String
      ChordDistanceString = FormatNumber(ChordDistance, CLng(ChordPrecisionComboBox.text), vbTrue, vbFalse, vbTrue)
      CurveCourseInfo TheIndex, workingPoint, endPoint, radiusPoint, chdDirString, ChordDistanceString, TheSegmentArea
   End If

'DRAW THE ELEMENT
   DrawTheArcAndStuff theArcElement, workingPoint, endPoint, radiusPoint, lefthandCurve, TheIndex, CourseDrawMode, DrawMode

'RETURN THE END POINT
   DrawCurveByTanInChd = endPoint
End Function



Private Function DrawCurveCourse(ByVal TheIndex As Long, _
                                 beginPoint As Point3d, _
                                 ByVal CourseDrawMode As Long, _
                                 ByRef latitude As Double, _
                                 ByRef departure As Double, _
                                 Optional DrawMode As MsdDrawingMode = msdDrawingModeNormal) As Point3d
   Dim workingPoint As Point3d
   workingPoint = beginPoint
   Dim wholeData1String As String
   wholeData1String = CoursesListBox.List(TheIndex, Lot_Closure_Column_Data_1)
   Dim dataTypeString As String
   Dim data1String As String
   SplitData wholeData1String, dataTypeString, data1String
   Select Case dataTypeString
      Case Lot_Closure_Data_Prefix_Chord_Dr
         DrawCurveCourse = DrawCurveByChord(data1String, _
                                            TheIndex, _
                                            beginPoint, _
                                            CourseDrawMode, _
                                            latitude, _
                                            departure, _
                                            DrawMode)

      Case Lot_Closure_Data_Prefix_RadialIn
         DrawCurveCourse = DrawCurveByRadials(data1String, _
                                              TheIndex, _
                                              beginPoint, _
                                              CourseDrawMode, _
                                              latitude, _
                                              departure, _
                                              DrawMode)
         
      Case Lot_Closure_Data_Prefix_TangentIn
         DrawCurveCourse = DrawCurveByTangents(data1String, _
                                               TheIndex, _
                                               beginPoint, _
                                               CourseDrawMode, _
                                               latitude, _
                                               departure, _
                                               DrawMode)

      Case Lot_Closure_Data_Prefix_TangentOut
         DrawCurveCourse = DrawCurveByTanOutChd(data1String, _
                                                TheIndex, _
                                                beginPoint, _
                                                CourseDrawMode, _
                                                latitude, _
                                                departure, _
                                                DrawMode)
         
      Case Lot_Closure_Data_Prefix_Radius
         DrawCurveCourse = DrawCurveByTanInChd(data1String, _
                                               TheIndex, _
                                               beginPoint, _
                                               CourseDrawMode, _
                                               latitude, _
                                               departure, _
                                               DrawMode)
      
   End Select
End Function



Private Function DrawLineCourse(ByVal TheIndex As Long, _
                                beginPoint As Point3d, _
                                ByVal CourseDrawMode As Long, _
                                ByRef latitude As Double, _
                                ByRef departure As Double, _
                                Optional DrawMode As MsdDrawingMode = msdDrawingModeNormal) As Point3d
   Dim workingPoint As Point3d
   workingPoint = beginPoint
   
   Dim wholeString As String
   Dim directionString As String
   Dim temp As String
   wholeString = CoursesListBox.List(TheIndex, Lot_Closure_Column_Data_1)
   SplitData wholeString, temp, directionString
   Dim sAzimuth As Double
   Dim origPrec As Long
   Dim dirType As Integer
   Dim quad As Integer
   If Not DirStringToSAz(directionString, sAzimuth, origPrec, dirType, quad) Then
      Err.Raise ERROR_NUM_539
   End If
   Dim DistanceString As String
   wholeString = CoursesListBox.List(TheIndex, Lot_Closure_Column_Data_2)
   SplitData wholeString, temp, DistanceString
   If IsNumeric(DistanceString) Then
      Dim distance As Double
      distance = CDbl(DistanceString)
   Else
      Err.Raise ERROR_NUM_540
   End If
   Dim endPoint As Point3d
   endPoint = CoordFwdSAz2(workingPoint, sAzimuth, distance, latitude, departure)
   Dim theLineElement As LineElement
   Set theLineElement = CreateLineElement2(Nothing, workingPoint, endPoint)
   Dim oLineStyle As LineStyle
   Set oLineStyle = ActiveDesignFile.LineStyles.Find("0")
   Set theLineElement.LineStyle = oLineStyle
   theLineElement.color = GetTetherColor()
   Select Case CourseDrawMode
      Case Mode_Draw_Permanent
         Dim LineCourseTemplate As LineElement
         Set LineCourseTemplate = CreateBoundaryTemplate()
         MakePermanentLineCourse LineCourseTemplate, TheIndex, workingPoint, endPoint
      Case Mode_Draw_Report
'WRITE REPORT STUFF HERE
         Dim ReportString As String
         ReportString = PaddedCourseNum(TheIndex + 1) & _
                        PaddedAzimuthString(directionString) & " " & _
                        PaddedDistanceString(DistanceString)
         Print #2, ReportString
         ReportCoordinateString endPoint.Y, endPoint.X
         DisplayElement TheIndex, theLineElement, Mode_Draw_Transient_Hilite_Sel
      Case Mode_Draw_Boundary_Report
'WRITE BOUNDARY REPORT STUFF HERE
         If CoursesListBox.Selected(TheIndex) Then
            ReportString = PaddedCourseNum(TheIndex + 1) & _
                           PaddedAzimuthString(directionString) & " " & _
                           PaddedDistanceString(DistanceString)
            Print #2, ReportString
            boundaryLength = boundaryLength + CDbl(DistanceString)
            MaxPrecUpd StrPrec(DistanceString)
         End If
      Case Mode_Draw_Export
         DisplayElement TheIndex, theLineElement, Mode_Draw_Transient_Hilite_Sel
      Case Else
         DisplayElement TheIndex, theLineElement, CourseDrawMode, DrawMode
   End Select

'FILL IN COURSE INFO HERE
   If CourseDrawMode <> Mode_Draw_Transient_Blank_Sel And CoursesListBox.Selected(TheIndex) = True Then
      LineCourseInfo TheIndex, workingPoint, endPoint
   End If

'ADD TO THE PERIMETER HERE
   AddToPerimeter distance
   
'RETURN ENDING COORDINATE
   DrawLineCourse = endPoint
End Function



Private Sub DrawTheArcAndStuff(theArcElement As ArcElement, _
                               startPoint As Point3d, _
                               endPoint As Point3d, _
                               radiusPoint As Point3d, _
                               ByVal lefthandCurve As Boolean, _
                               ByVal TheIndex As Long, _
                               ByVal CourseDrawMode As Long, _
                               Optional DrawMode As MsdDrawingMode = msdDrawingModeNormal)
   Dim StartPointCopy As Point3d
   StartPointCopy = startPoint
   Dim EndPointCopy As Point3d
   EndPointCopy = endPoint
   Dim RadiusPointCopy As Point3d
   RadiusPointCopy = radiusPoint
   Dim oLineStyle As LineStyle
   Set oLineStyle = ActiveDesignFile.LineStyles.Find("0")
   Set theArcElement.LineStyle = oLineStyle
   theArcElement.color = GetTetherColor()
   Dim RadialLineStyle As LineStyle
   Set RadialLineStyle = ActiveDesignFile.LineStyles.Find("2")
   Dim RadialLine1 As LineElement
   Set RadialLine1 = CreateLineElement2(Nothing, StartPointCopy, RadiusPointCopy)
   Set RadialLine1.LineStyle = RadialLineStyle
   RadialLine1.color = GetTetherColor()
   Dim RadialLine2 As LineElement
   Set RadialLine2 = CreateLineElement2(RadialLine1, RadiusPointCopy, EndPointCopy)

   Select Case CourseDrawMode
      Case Mode_Draw_Permanent
'DRAW PERMANENT ARC
         Dim ArcTemplate As LineElement
         Set ArcTemplate = CreateBoundaryTemplate()
         Dim NewArcElement As ArcElement
         If lefthandCurve Then
            Set NewArcElement = CreateArcElement1(ArcTemplate, StartPointCopy, RadiusPointCopy, EndPointCopy)
         Else
            Set NewArcElement = CreateArcElement1(ArcTemplate, EndPointCopy, RadiusPointCopy, StartPointCopy)
            NewArcElement.Reverse
         End If
         MakePermanentCourse NewArcElement, TheIndex
'DRAW PERMANENT CHORD
         If DGNChordCheckBox.value = True Then
            Dim ChordTemplate As LineElement
            Set ChordTemplate = CreateChordTemplate()
            MakePermanentLineElement ChordTemplate, TheIndex, StartPointCopy, EndPointCopy
         End If
'DRAW PERMANENT RADIAL LINES
         If DGNRadialLinesCheckBox.value = True Then
            Dim RadialsTemplate As LineElement
            Set RadialsTemplate = CreateRadialsTemplate()
            MakePermanentLineElement RadialsTemplate, TheIndex, StartPointCopy, RadiusPointCopy
            MakePermanentLineElement RadialsTemplate, TheIndex, RadiusPointCopy, EndPointCopy
         End If
         DisplayElement TheIndex, theArcElement, Mode_Draw_Transient_Hilite_All, DrawMode
      Case Mode_Draw_Report
         DisplayElement TheIndex, theArcElement, Mode_Draw_Transient_Hilite_Sel
         DisplayElement TheIndex, RadialLine1, Mode_Draw_Transient_Hilite_Sel
         DisplayElement TheIndex, RadialLine2, Mode_Draw_Transient_Hilite_Sel
      Case Mode_Draw_Boundary_Report
      
      Case Mode_Draw_Export
         DisplayElement TheIndex, theArcElement, Mode_Draw_Transient_Hilite_Sel
         DisplayElement TheIndex, RadialLine1, Mode_Draw_Transient_Hilite_Sel
         DisplayElement TheIndex, RadialLine2, Mode_Draw_Transient_Hilite_Sel
      Case Mode_Draw_Transient_Blank_Sel
         DisplayElement TheIndex, theArcElement, CourseDrawMode, DrawMode
      Case Mode_Draw_Transient_Hilite_All
         DisplayElement TheIndex, theArcElement, Mode_Draw_Transient_Hilite_All
      Case Else
         DisplayElement TheIndex, theArcElement, CourseDrawMode, DrawMode
         DisplayElement TheIndex, RadialLine1, CourseDrawMode, DrawMode
         DisplayElement TheIndex, RadialLine2, CourseDrawMode, DrawMode
   End Select
End Sub



Public Sub DrawTheCourses(POB As Point3d, _
                          ByVal CourseDrawMode As Long, _
                          Optional DrawMode As MsdDrawingMode = msdDrawingModeNormal)
'INITIALIZE VARIABLES AND DISPLAYS
   Dim POBcopy As Point3d
   POBcopy = POB
   Dim CurrentPoint As Point3d
   CurrentPoint = POBcopy
   ClearTransients
   ClearCourseInfo
   ClearStatus
   ClearCurveArea
   ClearPerimeter
   ClearLength
   ZeroMaxPrec
   InitializeTransientContainers (CourseDrawMode)

'WRITE REPORT STUFF HERE
   If CourseDrawMode = Mode_Draw_Report Then
      Print #2, "Starting Point:"
      ReportCoordinateString POBcopy.Y, POBcopy.X
   End If

'DO EXPORT STUFF HERE
   If CourseDrawMode = Mode_Draw_Export Then
      PointnameTextBox.text = WriteExportLine(PointnameTextBox.text, CurrentPoint)
   End If

'INITIALIZE VARIABLES FOR AREA CALCULATION
   Dim DMD As Double
   DMD = 0
   Dim DoubleAreas As Double
   DoubleAreas = 0
   Dim BalancedLatitude As Double
   Dim BalancedDeparture As Double
   Dim PreviousBalancedDeparture As Double
   PreviousBalancedDeparture = 0
   Dim PreviousPoint As Point3d
   PreviousPoint = POBcopy

'LOOP THROUGH COURSES
   Dim i As Long
   For i = 0 To CoursesListBox.ListCount - 1
      Dim CourseType As String
      CourseType = CoursesListBox.List(i, Lot_Closure_Column_Leg_Type)
      Select Case CourseType
         Case Lot_Closure_List_Type_Line
            CurrentPoint = DrawLineCourse(i, _
                                          CurrentPoint, _
                                          CourseDrawMode, _
                                          BalancedLatitude, _
                                          BalancedDeparture, _
                                          DrawMode)
         Case Lot_Closure_List_Type_Curve
            CurrentPoint = DrawCurveCourse(i, _
                                           CurrentPoint, _
                                           CourseDrawMode, _
                                           BalancedLatitude, _
                                           BalancedDeparture, _
                                           DrawMode)
      End Select
'DMD CALCULATIONS
      DMD = DMD + PreviousBalancedDeparture + BalancedDeparture
      DoubleAreas = DoubleAreas + BalancedLatitude * DMD
      PreviousPoint = CurrentPoint
      PreviousBalancedDeparture = BalancedDeparture
'DO EXPORT STUFF HERE
      If CourseDrawMode = Mode_Draw_Export Then
         PointnameTextBox.text = WriteExportLine(PointnameTextBox.text, CurrentPoint)
      End If
   Next i

'FINISH EXPORT STUFF HERE
   If CourseDrawMode = Mode_Draw_Export Then
      PointNameTextBox_AfterUpdate
   End If

'CALCULATE AREA
   Dim TheDMDArea As Double
   TheDMDArea = Abs(DoubleAreas / 2#)
   Dim TheCurveArea As Double
   TheCurveArea = GetTheCurveArea()
   If DoubleAreas > 0 Then 'ENTERED COUNTERCLOCKWISE
      TheCurveArea = -TheCurveArea
   End If
   Dim TotalAreaInFeet As Double
   TotalAreaInFeet = Abs(TheDMDArea + TheCurveArea)

'MAKE CELL PART OF DRAWING
   Dim UsedCell As Boolean
   UsedCell = False
   If CourseDrawMode = Mode_Draw_Permanent Then
'CREATE THE COMPLEX CHAIN FIRST
      If AllCoursesCheckBox.value And ComplexCheckBox.value Then
         Dim TheLotComplexChain As ComplexStringElement
         Set TheLotComplexChain = CreateTheComplexChain()
'ADD COMPLEX CHAIN TO THE CELL
         If CreateAsCellCheckBox.value Then
            AddElementToCellArray TheLotComplexChain
         Else
'ADD COMPLEX CHAIN TO THE DRAWING
            ActiveModelReference.AddElement TheLotComplexChain
            TheLotComplexChain.Redraw
         End If
      End If
      
'CREATE THE CELL
      If AllCoursesCheckBox.value And CreateAsCellCheckBox.value Then
         Dim TheLotCell As CellElement
         Set TheLotCell = CreateTheCellAndAddIt(POBcopy)
         UsedCell = True
      End If
      
      If DGNDescriptionCheckBox.value Or DGNAreaCheckBox.value Then
'ADD THE TEXT TO DRAWING HERE, USE DYNAMICS
         Dim PlaceTool As New LotClosurePrimitive
         Me.Hide 'Hide the dialog box
         PlaceTool.POB = POBcopy
         PlaceTool.TheAreaInFeet = TotalAreaInFeet
         PlaceTool.UseCell = UsedCell
         If UsedCell Then
            PlaceTool.TheLotCell = TheLotCell
         End If
         CommandState.StartPrimitive PlaceTool
      End If
   End If

'FILL IN STATUS IF MORE THAN ONE COURSE ENTERED
   If CoursesListBox.ListCount > 2 Then
      UpdateStatus POBcopy, CurrentPoint, TotalAreaInFeet
   End If

'WRITE REPORT STUFF HERE
   ReportErrorAndArea CourseDrawMode, CurrentPoint, POBcopy, TotalAreaInFeet
   BoundaryReportEnd CourseDrawMode
End Sub



Private Sub MakePermanentCourse(theElement As Element, ByVal ListboxIndex As Long)
   If AllCoursesCheckBox.value = True Then
      AddCourseToFileOrCellOrComplex theElement
   Else
      If CoursesListBox.Selected(ListboxIndex) = False Then
         AddCourseToFileOrCellOrComplex theElement
      End If
   End If
End Sub



Private Sub MakePermanentLine(theElement As Element, ByVal ListboxIndex As Long)
   If AllCoursesCheckBox.value = True Then
      AddCourseToFileOrCell theElement
   Else
      If CoursesListBox.Selected(ListboxIndex) = False Then
         AddCourseToFileOrCell theElement
      End If
   End If
End Sub



Private Sub MakePermanentLineCourse(TemplateElement As Element, ByVal ListboxIndex As Long, beginPoint As Point3d, endPoint As Point3d)
   Dim theLineElement As LineElement
   Set theLineElement = CreateLineElement2(TemplateElement, beginPoint, endPoint)
   MakePermanentCourse theLineElement, ListboxIndex
End Sub



Private Sub MakePermanentLineElement(TemplateElement As Element, ByVal ListboxIndex As Long, beginPoint As Point3d, endPoint As Point3d)
   Dim theLineElement As LineElement
   Set theLineElement = CreateLineElement2(TemplateElement, beginPoint, endPoint)
   MakePermanentLine theLineElement, ListboxIndex
End Sub



'*************************************************************************************************************
'***************************************TRANSFORMATION SUBROUTINES********************************************
Public Function DirectionStringPlus(directionString As String, AngleString As String) As String
'USES THE HIGHER PRECISION OF THE TWO STRINGS

'CONVERT DIRECTION STRING TO SOUTH AZIMUTH
   Dim sAzimuth As Double
   Dim origPrecDir As Long
   Dim dirType As Integer
   Dim quad As Integer
   If Not DirStringToSAz(directionString, sAzimuth, origPrecDir, dirType, quad) Then
      Err.Raise ERROR_NUM_554
   End If
   
'CONVERT ANGLE STRING TO DOUBLE
   Dim origPrecAng As Long
   Dim degPart As Long
   Dim minPart As Long
   Dim secPart As Double
   Dim isNeg As Boolean
   If Not IsPlusMinusAngleString(AngleString, origPrecAng, degPart, minPart, secPart, isNeg) Then
      Err.Raise ERROR_NUM_555
   End If
   Dim angleDouble As Double
   angleDouble = DmsToDecSigned(degPart, minPart, secPart, isNeg)
   
'ADD THE ANGLE TO THE AZIMUTH
   Dim newSAzimuth As Double
   newSAzimuth = angleDouble + sAzimuth
   MakeSure360 newSAzimuth

'DETERMINE PRECISION
   Dim precision As Long
   precision = MaxLong(origPrecAng, origPrecDir)

'GENERATE NEW STRING
   DirectionStringPlus = SAzToDirectionStr(newSAzimuth, precision, dirType, PlotLotEntryAngleStyle)
End Function



Private Sub TransformAngles()
'LOOP THROUGH COURSES
   Dim i As Long
   For i = 0 To CoursesListBox.ListCount - 1
      Dim CourseType As String
      CourseType = CoursesListBox.List(i, Lot_Closure_Column_Leg_Type)
      Select Case CourseType
         Case Lot_Closure_List_Type_Line
            TransformLine i
         Case Lot_Closure_List_Type_Curve
            TransformArc i
      End Select
   Next i
End Sub



Private Sub TransformLine(ByVal TheIndex As Long)
   Dim wholeData1String As String
   wholeData1String = CoursesListBox.List(TheIndex, Lot_Closure_Column_Data_1)
   Dim dataTypeString As String
   Dim data1String As String
   SplitData wholeData1String, dataTypeString, data1String
   Dim newDirectionString As String
   newDirectionString = DirectionStringPlus(data1String, TransAngleTextBox.text)
   CoursesListBox.List(TheIndex, Lot_Closure_Column_Data_1) = Lot_Closure_Data_Prefix_Direction & newDirectionString
End Sub



Private Sub TransformArc(ByVal TheIndex As Long)
   Dim wholeData1String As String
   wholeData1String = CoursesListBox.List(TheIndex, Lot_Closure_Column_Data_1)
   Dim dataTypeString As String
   Dim data1String As String
   SplitData wholeData1String, dataTypeString, data1String
   Select Case dataTypeString
      Case Lot_Closure_Data_Prefix_Chord_Dr
         TransformChordAz data1String, TheIndex
      Case Lot_Closure_Data_Prefix_RadialIn
         TransformRadialAz data1String, TheIndex
      Case Lot_Closure_Data_Prefix_TangentIn
         TransformTangentAz data1String, TheIndex
   End Select
End Sub



Private Sub TransformChordAz(dataString As String, ByVal TheIndex As Long)
   Dim newDirectionString As String
   newDirectionString = DirectionStringPlus(dataString, TransAngleTextBox.text)
   CoursesListBox.List(TheIndex, Lot_Closure_Column_Data_1) = Lot_Closure_Data_Prefix_Chord_Dr & newDirectionString
End Sub



Private Sub TransformRadialAz(dataString As String, ByVal TheIndex As Long)
   TransformSub dataString, TheIndex, Lot_Closure_Data_Prefix_RadialIn, Lot_Closure_Data_Prefix_RadialOut
End Sub



Private Sub TransformTangentAz(dataString As String, ByVal TheIndex As Long)
   TransformSub dataString, TheIndex, Lot_Closure_Data_Prefix_TangentIn, Lot_Closure_Data_Prefix_TangentOut
End Sub



Private Sub TransformSub(dataString As String, ByVal TheIndex As Long, Prefix1 As String, Prefix2 As String)
   Dim newDirectionString1 As String
   newDirectionString1 = DirectionStringPlus(dataString, TransAngleTextBox.text)
   CoursesListBox.List(TheIndex, Lot_Closure_Column_Data_1) = Prefix1 & newDirectionString1

   Dim wholeData1String As String
   wholeData1String = CoursesListBox.List(TheIndex, Lot_Closure_Column_Data_3)
   Dim dataTypeString As String
   Dim data2String As String
   SplitData wholeData1String, dataTypeString, data2String

   Dim newDirectionString2 As String
   newDirectionString2 = DirectionStringPlus(data2String, TransAngleTextBox.text)
   CoursesListBox.List(TheIndex, Lot_Closure_Column_Data_3) = Prefix2 & newDirectionString2
End Sub



Private Sub TransformScaleCourses()
'LOOP THROUGH COURSES
   Dim ScaleFactor As Double
   ScaleFactor = CDbl(TransformScaleTextBox.text)
   Dim minPrec As Long
   minPrec = CLng(DisPrecComboBox.text)
   Dim i As Long
   For i = 0 To CoursesListBox.ListCount - 1
      Dim CourseType As String
      CourseType = CoursesListBox.List(i, Lot_Closure_Column_Leg_Type)
      Select Case CourseType
         Case Lot_Closure_List_Type_Line
            If Not ScaleLine(i, ScaleFactor, minPrec) Then
               scaleErrorEncountered = True
            End If
         Case Lot_Closure_List_Type_Curve
            If Not ScaleCurve(i, ScaleFactor, minPrec) Then
               scaleErrorEncountered = True
            End If
      End Select
   Next i
End Sub



Private Function ScaleLine(TheIndex As Long, ScaleFactor As Double, minPrec As Long) As Boolean
'RETURNS TRUE IF SUCCESSFUL
'INITIALIZE FLAG
   ScaleLine = False
   
'GET DISTANCE FIELD
   Dim wholeData1String As String
   wholeData1String = CoursesListBox.List(TheIndex, Lot_Closure_Column_Data_2)
   
'SPLIT THE FIELD INTO COMPONENTS
   Dim dataTypeString As String
   Dim data2String As String
   SplitData wholeData1String, dataTypeString, data2String
   
'TRY AND SCALE THE ENTRY
   Dim ScaledString As String
   If Not ScaledDistance(data2String, ScaleFactor, minPrec, ScaledString) Then
      Exit Function
   End If
   
'REPLACE WITH SCALED ENTRY
   CoursesListBox.List(TheIndex, Lot_Closure_Column_Data_2) = Lot_Closure_Data_Prefix_Distance & ScaledString

'SIGNAL SUCCESS
   ScaleLine = True
End Function



Private Function ScaledDistance(ByVal DistanceString As String, ByVal ScaleFactor As Double, minPrec As Long, ByRef ScaledString As String) As Boolean
'TAKES DISTANCE STRING AND SCALE FACTOR AND TRIES TO CREATE RESULTING DISTANCE STRING.  MINIMUM OF 2 DECIMAL PLACES.
'RETURNS TRUE IF SUCCESSFUL
'INIALIZE  FLAG
   ScaledDistance = False

'GET THE PRECISION TO USE FOR THE SCALED DISTANCE
   Dim value As Double
   Dim origPrec As Long
   If Not IsNonnegativeString(DistanceString, False, value, origPrec) Then
      Exit Function
   End If
   Dim finalPrecision As Long
   finalPrecision = MaxLong(origPrec, minPrec)
   
'CALCULATE THE SCALED DISTANCE
   Dim ScaledDistanceDouble As Double
   ScaledDistanceDouble = Round(CDbl(DistanceString) * ScaleFactor, finalPrecision)

'MAKE SURE IT IS NOT ZERO OR BELOW OR TOO BIG
   If ScaledDistanceDouble <= 0# Or ScaledDistanceDouble > MAX_DISTANCE Then
      Exit Function
   End If

'RETURN STRING
   ScaledString = FormatNumber(ScaledDistanceDouble, finalPrecision, vbTrue, vbFalse, vbTrue)

'SIGNAL SUCCESS
   ScaledDistance = True
End Function



Private Function ScaleCurve(ByVal TheIndex As Long, ByVal ScaleFactor As Double, minPrec As Long) As Boolean
'RETURNS TRUE IF SUCCESSFUL
'INITIALIZE FLAG
   ScaleCurve = False

'FIND OUT CURVE TYPE
   Dim wholeData1String As String
   wholeData1String = CoursesListBox.List(TheIndex, Lot_Closure_Column_Data_1)
   Dim dataTypeString As String
   Dim data1String As String
   SplitData wholeData1String, dataTypeString, data1String

'DETERMINE WHICH COLUMN HAS THE RADIUS
   Dim radiusColumn As Long
   Select Case dataTypeString
      Case Lot_Closure_Data_Prefix_Chord_Dr
         radiusColumn = Lot_Closure_Column_Data_3
      Case Lot_Closure_Data_Prefix_RadialIn
         radiusColumn = Lot_Closure_Column_Data_2
      Case Lot_Closure_Data_Prefix_TangentIn
         radiusColumn = Lot_Closure_Column_Data_2
   End Select

'GET THE RADIUS STRING
   Dim wholeRadiusString As String
   wholeRadiusString = CoursesListBox.List(TheIndex, radiusColumn)
   Dim radiusPrefixString As String
   Dim radiusDataString As String
   SplitData wholeRadiusString, radiusPrefixString, radiusDataString

'TRY AND SCALE THE RADIUS ENTRY
   Dim scaledRadiusString As String
   If Not ScaledDistance(radiusDataString, ScaleFactor, minPrec, scaledRadiusString) Then
      Exit Function
   End If

'HANDLE CHORD DEFINED CURVE, SCALE CHORD AND CHECK AGAINST SCALED RADIUS
   If dataTypeString = Lot_Closure_Data_Prefix_Chord_Dr Then
'GET THE CHORD DISTANCE STRING
      Dim wholeChordString As String
      wholeChordString = CoursesListBox.List(TheIndex, Lot_Closure_Column_Data_2)
      Dim chordPrefixString As String
      Dim chordDataString As String
      SplitData wholeChordString, chordPrefixString, chordDataString
'TRY AND SCALE THE CHORD ENTRY
      Dim scaledChordString As String
      If Not ScaledDistance(chordDataString, ScaleFactor, minPrec, scaledChordString) Then
         Exit Function
      End If
'MAKE SURE THE CHORD IS NOT TOO BIG
      If CDbl(scaledChordString) > CDbl(scaledRadiusString) + CDbl(scaledRadiusString) Then
         Exit Function
      End If
'REPLACE CHORD DISTANCE STRING
      CoursesListBox.List(TheIndex, Lot_Closure_Column_Data_2) = Lot_Closure_Data_Prefix_Chord & scaledChordString
   End If

'REPLACE THE RADIUS STRING
   CoursesListBox.List(TheIndex, radiusColumn) = Lot_Closure_Data_Prefix_Radius & scaledRadiusString

'SIGNAL SUCCESS
   ScaleCurve = True
End Function



'*************************************************************************************************************
'***************************************CLOSURE REPORT SUBROUTINES********************************************
Private Function AddSpaceAfterColon(InputString As String) As String
'REPLACES COLONS IN STRING WITH COLON AND SPACE
   AddSpaceAfterColon = Replace(InputString, ":", ": ")
End Function



Private Function ErrorPrecisionString(ByVal ErrorDistance As Double, ByVal thePerimeter As Double) As String
   If thePerimeter = 0 Then
      ErrorPrecisionString = "?"
   ElseIf ErrorDistance = 0 Then
      ErrorPrecisionString = "infinity"
   Else
      ErrorPrecisionString = FormatNumber(Round(1# / (ErrorDistance / thePerimeter), 0), 0)
   End If
End Function



Private Function PaddedAzimuthString(AzimuthString As String) As String
   Dim DegreesSymPos As Long
   DegreesSymPos = InStr(1, AzimuthString, Chr(176))
   If DegreesSymPos <> 0 Then
      AzimuthString = PadTheEnd(AzimuthString, 12 - (4 - DegreesSymPos))
   End If
   PaddedAzimuthString = PadLead(AzimuthString, 15)
End Function



Private Function PaddedCourseNum(ByVal CourseNum As Long) As String
   PaddedCourseNum = PadLead(FormatNumber(CourseNum, 0, vbTrue, vbFalse, vbFalse) & ") ", 5)
End Function



Private Function PaddedDistanceString(DistanceString As String) As String
   PaddedDistanceString = PadLead(DistanceString, 8)
End Function



Private Sub ReportCoordinateString(ByVal northing As Double, ByVal easting As Double)
'ADDS A COORDINATE STRING TO REPORT
   Print #2, "                                                " & _
                   PaddedNorthingString(northing, StartPointPrec) & " " & PaddedEastingString(easting, StartPointPrec)
End Sub



Private Sub ReportCurveData(ByVal theSegmentAreaInSqFt As Double, _
                            ByVal chordSAz As Double, _
                            ByVal chordDis As Double, _
                            ByVal IsLeftHand As Boolean, _
                            CenterCurve As Point3d, _
                            chordDirPrec As Long, _
                            chordDirType As Integer)
'ADDS TO THE REPORT THE CURVE DATA FOR CURVE COURSES NOT ENTERED BY CHORD AZIMUTH AND DISTANCE
   Dim chordAzString As String
   chordAzString = SAzToDirectionStr(chordSAz, chordDirPrec, chordDirType, PlotLotEntryAngleStyle)
   Dim ChordDisString As String
   ChordDisString = FormatNumber(chordDis, CLng(ChordPrecisionComboBox.text), vbTrue, vbFalse, vbTrue)
   Dim ReportString As String
   ReportString = "      Chord Dr.: " & chordAzString & " Chord Dis: " & ChordDisString
   Print #2, ReportString
   Dim RotationString As String
   If IsLeftHand Then
      RotationString = "Rot: Left  "
   Else
      RotationString = "Rot: Right  "
   End If
   Dim CCString As String
   CCString = "CC: " & DoubleToNorthingString(CenterCurve.Y, StartPointPrec) & "  " & DoubleToEastingString(CenterCurve.X, StartPointPrec)
   Print #2, "      " & RotationString & "  " & CCString
   Print #2, "      " & "Segment area: " & FormatNumber(Round(Abs(theSegmentAreaInSqFt), 3), 3, vbTrue, vbFalse, vbTrue) & " sq.ft"
End Sub



Private Sub ReportCurveData2(ByVal theSegmentAreaInSqFt As Double, _
                             ByVal dirType As Integer, _
                             ByVal radInSAz As Double, _
                             ByVal radOutSAz As Double, _
                             CenterCurve As Point3d, _
                             precision As Long)
'ADDS TO THE REPORT THE CURVE DATA FOR CURVE COURSES ENTERED BY CHORD AZIMUTH AND DISTANCE
   Dim radInString As String
   radInString = "RadIn: " & SAzToDirectionStr(radInSAz, precision, dirType, PlotLotEntryAngleStyle)
   Dim radOutString As String
   radOutString = "RadOut: " & SAzToDirectionStr(radOutSAz, precision, dirType, PlotLotEntryAngleStyle)
   Dim ReportString As String
   ReportString = "      " & radInString & " " & radOutString
   Print #2, ReportString
   Dim CCString As String
   CCString = "CC: " & DoubleToNorthingString(CenterCurve.Y, StartPointPrec) & "  " & DoubleToEastingString(CenterCurve.X, StartPointPrec)
   Print #2, "      " & CCString
   Print #2, "      Segment area: " & FormatNumber(Round(Abs(theSegmentAreaInSqFt), 3), 3, vbTrue, vbFalse, vbTrue) & " sq.ft"
End Sub



Private Sub ReportCurveData3(ByVal theSegmentAreaInSqFt As Double, _
                             ByVal chordDis As Double, _
                             ByVal IsLeftHand As Boolean, _
                             ByVal dirType As Integer, _
                             ByVal radInSAz As Double, _
                             ByVal radOutSAz As Double, _
                             CenterCurve As Point3d, _
                             precision As Long)
'ADDS TO THE REPORT THE CURVE DATA FOR CURVE COURSES ENTERED BY CHORD AZIMUTH AND TANGENT
   Dim ChordDisString As String
   ChordDisString = "Chord Dis: " & FormatNumber(chordDis, CLng(ChordPrecisionComboBox.text), vbTrue, vbFalse, vbTrue)
   Dim RotationString As String
   If IsLeftHand Then
      RotationString = "Rot: Left  "
   Else
      RotationString = "Rot: Right  "
   End If
   Dim radInString As String
   radInString = "RadIn: " & SAzToDirectionStr(radInSAz, precision, dirType, PlotLotEntryAngleStyle)
   Dim radOutString As String
   radOutString = "RadOut: " & SAzToDirectionStr(radOutSAz, precision, dirType, PlotLotEntryAngleStyle)
   Dim ReportString As String
   ReportString = "      " & RotationString & ChordDisString
   Print #2, ReportString
   ReportString = "      " & radInString & " " & radOutString
   Print #2, ReportString
   Dim CCString As String
   CCString = "CC: " & DoubleToNorthingString(CenterCurve.Y, StartPointPrec) & "  " & DoubleToEastingString(CenterCurve.X, StartPointPrec)
   Print #2, "      " & CCString
   Print #2, "      Segment area: " & FormatNumber(Round(Abs(theSegmentAreaInSqFt), 3), 3, vbTrue, vbFalse, vbTrue) & " sq.ft"
End Sub



Private Sub ReportCurveInput(ByVal TheIndex As Long, ByVal UseColumn6 As Boolean)
'ADDS THE CURVE COURSE INPUT TO THE REPORT
   Dim ReportEntryString As String
   ReportEntryString = PaddedCourseNum(TheIndex + 1) & " " & CoursesListBox.List(TheIndex, Lot_Closure_Column_Data_1) _
                       & "  " & CoursesListBox.List(TheIndex, Lot_Closure_Column_Data_2) & "  " & _
                       CoursesListBox.List(TheIndex, Lot_Closure_Column_Data_3) & ReportEntryString & "  " & _
                       CoursesListBox.List(TheIndex, Lot_Closure_Column_Data_4)
   If UseColumn6 Then
      ReportEntryString = ReportEntryString & "  " & CoursesListBox.List(TheIndex, Lot_Closure_Column_Data_5)
   End If
   ReportEntryString = AddSpaceAfterColon(ReportEntryString)
   Print #2, ReportEntryString
End Sub



Private Sub ReportCurveInputChdTanOut(ByVal TheIndex As Long)
'ADDS THE CURVE COURSE INPUT TO THE REPORT FOR CHORD DIRECTION, RADIUS,TANGENT OUT
   Dim ReportEntryString As String
   ReportEntryString = PaddedCourseNum(TheIndex + 1) & " " & CoursesListBox.List(TheIndex, Lot_Closure_Column_Data_3) _
                       & "  " & CoursesListBox.List(TheIndex, Lot_Closure_Column_Data_2) & "  " & _
                       CoursesListBox.List(TheIndex, Lot_Closure_Column_Data_1)
   ReportEntryString = AddSpaceAfterColon(ReportEntryString)
   Print #2, ReportEntryString
End Sub



Private Sub ReportCurveInputChdTanIn(ByVal TheIndex As Long)
'ADDS THE CURVE COURSE INPUT TO THE REPORT FOR CHORD DIRECTION, RADIUS,TANGENT OUT
   Dim ReportEntryString As String
   ReportEntryString = PaddedCourseNum(TheIndex + 1) & " " & CoursesListBox.List(TheIndex, Lot_Closure_Column_Data_2) _
                       & "  " & CoursesListBox.List(TheIndex, Lot_Closure_Column_Data_1) & "  " & _
                       CoursesListBox.List(TheIndex, Lot_Closure_Column_Data_3)
   ReportEntryString = AddSpaceAfterColon(ReportEntryString)
   Print #2, ReportEntryString
End Sub



Private Sub ReportErrorAndArea(ByVal CourseDrawMode As Long, CurrentPoint As Point3d, POB As Point3d, ByVal TotalAreaInFeet As Double)
'ADDS TO THE REPORT THE BOTTOM PART OF THE REPORT
   If CourseDrawMode = Mode_Draw_Report Then
      Dim NorthingError As Double
      NorthingError = CurrentPoint.Y - POB.Y
      Print #2,
      Dim EastingError As Double
      EastingError = CurrentPoint.X - POB.X
      Dim ErrorDistance As Double
      ErrorDistance = Round(InverseDistance(NorthingError, EastingError), 4)
      Print #2, "  Closure error: " & PadLead(DoubleToNorthingString(NorthingError, 4), 10) & " " & _
                PadLead(DoubleToEastingString(EastingError, 4), 10) & "  " & _
                PadLead(FormatNumber(ErrorDistance, 4, vbTrue, vbFalse, vbTrue), 10) & " dist."
      Dim ThePrecisionString As String
      ThePrecisionString = "Precision ratio: 1/" & ErrorPrecisionString(ErrorDistance, GetThePerimeter())
      Print #2, ThePrecisionString
      Dim AreaInAcres As Double
      AreaInAcres = Round(TotalAreaInFeet, 0) / Square_Feet_Per_Acre
      Print #2, "           Area: " & FormatNumber(TotalAreaInFeet, 0, vbFalse, vbFalse, vbTrue) & " sq.ft." & "  " & FormatNumber(AreaInAcres, 3); " acres"
      Print #2, " Generated with: " & APP_VERSION & APP_UPDATE
   End If
End Sub



Private Sub BoundaryReportEnd(ByVal CourseDrawMode As Long)
'ADDS TO THE REPORT THE BOTTOM PART OF THE REPORT
   If CourseDrawMode = Mode_Draw_Boundary_Report Then
      Print #2,
      Dim totalString As String
      totalString = FormatNumber(boundaryLength, maxBoundaryPrec, vbTrue, vbFalse, vbTrue)
      Print #2, " Total Length: " & totalString & "ft"
      Print #2,
      Print #2, " Generated with: " & APP_VERSION & APP_UPDATE
   End If
End Sub



Private Sub ReportTopPart()
'CREATES THE TOP PART OF THE REPORT FILE
   Print #2, "* * * * * * * * * * * * SURVEYOR TOOLS NEO CLOSURE REPORT * * * * * * * * * * * *"
   ReportTopPartSub
End Sub



Private Sub ReportBoundaryTopPart()
'CREATES THE TOP PART OF THE REPORT FILE
   Print #2, "* * * * * * * * * * * * SURVEYOR TOOLS NEO BOUNDARY REPORT * * * * * * * * * * * *"
   ReportTopPartSub
End Sub



Private Sub ReportBoundaryArcPart(TheIndex As Long, theArcElement As ArcElement, CourseDrawMode As Long, haveCol6 As Boolean)
   If CourseDrawMode = Mode_Draw_Boundary_Report Then
      If CoursesListBox.Selected(TheIndex) Then
         ReportCurveInput TheIndex, haveCol6
         Dim LenPrecision As Long
         LenPrecision = CLng(ChordPrecisionComboBox.text)
         MaxPrecUpd LenPrecision
         Dim arcLen As Double
         arcLen = Round(theArcElement.length, LenPrecision)
         boundaryLength = boundaryLength + arcLen
         Dim lenString As String
         lenString = "          Arc Length: " & FormatNumber(arcLen, LenPrecision, vbTrue, vbFalse, vbTrue)
         Print #2, lenString
      End If
   End If
End Sub



Private Sub ReportTopPartSub()
   Print #2, " "
   If ReportProjectCheckBox.value = True Then
      Print #2, " Proj. Name: " & ProjectTextBox.text
   End If
   If ProjectNumCheckBox.value Then
      Print #2, " Proj. Num.: " & ProjNumTextBox.text
   End If
   If ReportDateCheckBox.value = True Then
      Print #2, "       Date: " & DateTextBox.text
   End If
   If ReportDescriptionCheckBox.value = True Then
      Print #2, "Description: " & DescriptionTextBox.text
   End If
   If ReportAzimuthCheckBox.value = True Then
      Print #2, "    Azimuth: " & AzimuthTextBox.text
   End If
   If ReportCoordinateCheckBox.value = True Then
      Print #2, "Coordinates: " & CoordinateTextBox.text
   End If
   If NoteCheckBox.value = True Then
      Print #2, "       Note: " & NoteTextBox.text
   End If
   If NORTH_AZIMUTH_MODE Then
      Dim mode As String
      mode = "North"
   Else
      mode = "South"
   End If
   Print #2, "  Azi. mode: " & mode
   If ReportFilenameCheckBox.value = True Then
      Dim TheFilenameString As String
      TheFilenameString = GetSetting(APP_NAME, SECTION_LOT_CLOSURE, KEY_FILENAME, "C:\output" & Lot_Closure_File_Extension)
      If IncludePathCheckBox.value = False Then
         Dim xSplit2 As Variant
         xSplit2 = Split(TheFilenameString, "\")
         TheFilenameString = xSplit2(UBound(xSplit2))
      End If
      Print #2, "   Filename: " & TheFilenameString
   End If
   Print #2, " "
End Sub




'*************************************************************************************************************
'******************************************EXPORT SUBROUTINES*************************************************
Private Function WriteExportLine(ByVal pointName As String, ExportPoint As Point3d) As String
'CREATES COORDINATE FILE LINE, ADDS IT TO FILE
   Dim thePoint As Point3d
   thePoint = ExportPoint
   Dim NEprecision As Integer
   NEprecision = StartPointPrec
   Dim ElevationPrecision As Integer
   ElevationPrecision = 2
   Dim descriptionString As String
   If UseLotDescCheckBox.value = True Then
      descriptionString = DescriptionTextBox.text
   Else
      descriptionString = CoordDescTextBox.text
   End If
   Dim RecordString As String
   RecordString = pointName
   RecordString = RecordString & "," _
                  & FormatNumber(Round(thePoint.Y, NEprecision), NEprecision, vbTrue, vbFalse, vbFalse) & "," _
                  & FormatNumber(Round(thePoint.X, NEprecision), NEprecision, vbTrue, vbFalse, vbFalse) & "," _
                  & FormatNumber(Round(thePoint.z, ElevationPrecision), ElevationPrecision, vbTrue, vbFalse, vbFalse) & "," _
                  & descriptionString
   Print #7, RecordString
   
   WriteExportLine = IncPointName(pointName)
End Function



'*************************************************************************************************************
'**************************************ROLL UP AND DOWN SUBROUTINES*******************************************
Private Function OkToRoll() As Boolean
'RETURNS TRUE IF OK TO ROLL
   If CoursesListBox.ListCount >= 2 Then
      OkToRoll = True
   Else
      OkToRoll = False
   End If
End Function



Private Sub RollUp()
   If OkToRoll() Then
      Dim lastIndex As Long
      lastIndex = CoursesListBox.ListCount - 1
      Dim datum1 As String
      Dim datum2 As String
      Dim datum3 As String
      Dim datum4 As String
      Dim datum5 As String
      Dim datum6 As String
      CopyRecFromIndex 0, datum1, datum2, datum3, datum4, datum5, datum6
      Dim i As Long
      For i = 1 To lastIndex
         Dim dat1 As String
         Dim dat2 As String
         Dim dat3 As String
         Dim dat4 As String
         Dim dat5 As String
         Dim dat6 As String
         CopyRecFromIndex i, dat1, dat2, dat3, dat4, dat5, dat6
         CopyRecToIndex i - 1, dat1, dat2, dat3, dat4, dat5, dat6
      Next i
      CopyRecToIndex lastIndex, datum1, datum2, datum3, datum4, datum5, datum6
   End If
End Sub



Private Sub RollDown()
   If OkToRoll() Then
      Dim lastIndex As Long
      lastIndex = CoursesListBox.ListCount - 1
      Dim datum1 As String
      Dim datum2 As String
      Dim datum3 As String
      Dim datum4 As String
      Dim datum5 As String
      Dim datum6 As String
      CopyRecFromIndex lastIndex, datum1, datum2, datum3, datum4, datum5, datum6
      Dim i As Long
      For i = lastIndex To 1 Step -1
         Dim dat1 As String
         Dim dat2 As String
         Dim dat3 As String
         Dim dat4 As String
         Dim dat5 As String
         Dim dat6 As String
         CopyRecFromIndex i - 1, dat1, dat2, dat3, dat4, dat5, dat6
         CopyRecToIndex i, dat1, dat2, dat3, dat4, dat5, dat6
      Next i
      CopyRecToIndex 0, datum1, datum2, datum3, datum4, datum5, datum6
   End If
End Sub



Private Sub CopyRecFromIndex(ByVal index As Long, datum1 As String, datum2 As String, datum3 As String, datum4 As String, datum5 As String, datum6 As String)
   datum1 = CoursesListBox.List(index, Lot_Closure_Column_Leg_Type)
   datum2 = CoursesListBox.List(index, Lot_Closure_Column_Data_1)
   datum3 = CoursesListBox.List(index, Lot_Closure_Column_Data_2)
   If datum1 = Lot_Closure_List_Type_Curve Then
      datum4 = CoursesListBox.List(index, Lot_Closure_Column_Data_3)
      datum5 = CoursesListBox.List(index, Lot_Closure_Column_Data_4)
      Dim dataTypeString As String
      Dim data1String As String
      SplitData datum2, dataTypeString, data1String
      If dataTypeString = Lot_Closure_Data_Prefix_Chord_Dr Then
         datum6 = CoursesListBox.List(index, Lot_Closure_Column_Data_5)
      End If
   End If
End Sub



Private Sub CopyRecToIndex(ByVal index As Long, datum1 As String, datum2 As String, datum3 As String, datum4 As String, datum5 As String, datum6 As String)
   CoursesListBox.List(index, Lot_Closure_Column_Data_3) = ""
   CoursesListBox.List(index, Lot_Closure_Column_Data_4) = ""
   CoursesListBox.List(index, Lot_Closure_Column_Data_5) = ""

   CoursesListBox.List(index, Lot_Closure_Column_Leg_Type) = datum1
   CoursesListBox.List(index, Lot_Closure_Column_Data_1) = datum2
   CoursesListBox.List(index, Lot_Closure_Column_Data_2) = datum3
   If datum1 = Lot_Closure_List_Type_Curve Then
      CoursesListBox.List(index, Lot_Closure_Column_Data_3) = datum4
      CoursesListBox.List(index, Lot_Closure_Column_Data_4) = datum5
      Dim dataTypeString As String
      Dim data1String As String
      SplitData datum2, dataTypeString, data1String
      If dataTypeString = Lot_Closure_Data_Prefix_Chord_Dr Then
         CoursesListBox.List(index, Lot_Closure_Column_Data_5) = datum6
      End If
   End If
End Sub



'*************************************************************************************************************
'*************************************PICK COURSE CODE********************************************************
Public Sub SetLegPoint(LegPoint As Point3d)
'SEARCH FOR LEG HERE
   Dim legIndex As Long
   legIndex = LegSearch(LegPoint, startingPoint)
   If legIndex > -1 Then
      If CoursesListBox.MultiSelect = fmMultiSelectMulti Then
'NO FUNCTION FOR MULTI SELECT MODE YET.  TOO SLOW ANYWAY.
      Else
         CoursesListBox.listIndex = legIndex
      End If
   End If

End Sub



Private Function LegSearch(nearPoint As Point3d, POB As Point3d) As Long
'RETURNS INDEX OF LEG FOUND, -1 IF NOT FOUND
   LegSearch = -1

'INITIALIZE VARIABLES
   Dim CurrentPoint As Point3d
   CurrentPoint = POB

'LOOP THROUGH COURSES
   Dim i As Long
   For i = 0 To CoursesListBox.ListCount - 1
      Dim CourseType As String
      CourseType = CoursesListBox.List(i, Lot_Closure_Column_Leg_Type)
      Select Case CourseType
         Case Lot_Closure_List_Type_Line
            Dim lineEnd  As Point3d
            lineEnd = CalcLineEndFromIndex(i, CurrentPoint)
            Dim lenAlongLine As Double
            Dim offset As Double
            If IsWithinLineRange(nearPoint, CurrentPoint, lineEnd, lenAlongLine, offset) Then
               offset = Abs(offset)
               If LegSearch = -1 Then
                  LegSearch = i
                  Dim nearest As Double
                  nearest = offset
               ElseIf nearest > offset Then
                  nearest = offset
                  LegSearch = i
               End If
            End If
            CurrentPoint = lineEnd
         Case Lot_Closure_List_Type_Curve
            Dim theArc As ArcElement
            CurrentPoint = CalcCurveEndFromIndex(i, CurrentPoint, theArc)
            Dim LengthAlongLine As Double
            If IsWithinArcRange(nearPoint, theArc, LengthAlongLine, offset) Then
               offset = Abs(offset)
               If LegSearch = -1 Then
                  LegSearch = i
                  nearest = offset
               ElseIf nearest > offset Then
                  nearest = offset
                  LegSearch = i
               End If
            End If
      End Select
   Next i
End Function



Private Function CalcLineEndFromIndex(ByVal TheIndex As Long, beginPoint As Point3d) As Point3d
   Dim wholeString As String
   wholeString = CoursesListBox.List(TheIndex, Lot_Closure_Column_Data_1)
   Dim temp As String
   Dim directionString As String
   SplitData wholeString, temp, directionString
   Dim sAzimuth As Double
   Dim origPrec As Long
   Dim dirType As Integer
   Dim quad As Integer
   If Not DirStringToSAz(directionString, sAzimuth, origPrec, dirType, quad) Then
      Err.Raise ERROR_NUM_551
   End If
   Dim DistanceString As String
   wholeString = CoursesListBox.List(TheIndex, Lot_Closure_Column_Data_2)
   SplitData wholeString, temp, DistanceString
   If IsNumeric(DistanceString) Then
      Dim distance As Double
      distance = CDbl(DistanceString)
   Else
      Err.Raise ERROR_NUM_552
   End If
   CalcLineEndFromIndex = CoordFwdSAz(beginPoint, sAzimuth, distance)
End Function



Private Function CalcCurveEndFromIndex(ByVal TheIndex As Long, beginPoint As Point3d, ByRef theArc As ArcElement) As Point3d
   Dim workingPoint As Point3d
   workingPoint = beginPoint
   Dim wholeData1String As String
   wholeData1String = CoursesListBox.List(TheIndex, Lot_Closure_Column_Data_1)
   Dim dataTypeString As String
   Dim data1String As String
   SplitData wholeData1String, dataTypeString, data1String
   Select Case dataTypeString
      Case Lot_Closure_Data_Prefix_Chord_Dr
         Dim chordString As String
         Dim theChord As Double
         Dim theRadius As Double
         Dim endPoint As Point3d
         Dim radiusPoint As Point3d
         Dim lefthandCurve As Boolean
         Dim delta As Double
         Dim latitude As Double
         Dim departure As Double
         CurveByChordToElement data1String, _
                               TheIndex, _
                               beginPoint, _
                               latitude, _
                               departure, _
                               endPoint, _
                               chordString, _
                               theChord, _
                               theRadius, _
                               radiusPoint, _
                               lefthandCurve, _
                               delta, _
                               theArc
         CalcCurveEndFromIndex = endPoint
         
      Case Lot_Closure_Data_Prefix_RadialIn
         Dim origPrecIn As Long
         Dim origPrecOut As Long
         Dim radialInSAz As Double
         Dim dirInType As Integer
         CurveByRadialsToElement data1String, _
                                 TheIndex, _
                                 beginPoint, _
                                 latitude, _
                                 departure, _
                                 endPoint, _
                                 theRadius, _
                                 radiusPoint, _
                                 lefthandCurve, _
                                 delta, _
                                 theArc, _
                                 origPrecIn, _
                                 origPrecOut, _
                                 radialInSAz, _
                                 dirInType
        CalcCurveEndFromIndex = endPoint
         
      Case Lot_Closure_Data_Prefix_TangentIn
         Dim tanInSAz As Double
         CurveByTangentsToElement data1String, _
                                  TheIndex, _
                                  beginPoint, _
                                  latitude, _
                                  departure, _
                                  endPoint, _
                                  theRadius, _
                                  radiusPoint, _
                                  lefthandCurve, _
                                  delta, _
                                  theArc, _
                                  origPrecIn, _
                                  origPrecOut, _
                                  tanInSAz, _
                                  dirInType
         CalcCurveEndFromIndex = endPoint
         
      Case Lot_Closure_Data_Prefix_TangentOut
         Dim chdDirString As String
         Dim chdDirPrec As Long
         Dim tanOutPrec As Long
         Dim tanOutType As Integer
         Dim radialOutSAz As Double
         CurveByTanOutChrToElement data1String, _
                                   TheIndex, _
                                   beginPoint, _
                                   latitude, _
                                   departure, _
                                   endPoint, _
                                   theRadius, _
                                   radiusPoint, _
                                   lefthandCurve, _
                                   delta, _
                                   theArc, _
                                   chdDirString, _
                                   chdDirPrec, _
                                   tanOutPrec, _
                                   tanOutType, _
                                   radialInSAz, _
                                   radialOutSAz
         CalcCurveEndFromIndex = endPoint
                  
      Case Lot_Closure_Data_Prefix_Radius
         CurveByTanInChrToElement data1String, _
                                  TheIndex, _
                                  beginPoint, _
                                  latitude, _
                                  departure, _
                                  endPoint, _
                                  theRadius, _
                                  radiusPoint, _
                                  lefthandCurve, _
                                  delta, _
                                  theArc, _
                                  chdDirString, _
                                  chdDirPrec, _
                                  tanOutPrec, _
                                  tanOutType, _
                                  radialInSAz, _
                                  radialOutSAz
         CalcCurveEndFromIndex = endPoint
         
      Case Else
         Err.Raise ERROR_NUM_553
   End Select
End Function



'*************************************************************************************************************
'**********************************************REPORT/FILES TAB***********************************************
'NEW BUTTON (FILE)
Private Sub NewButton_Click()
'CREATE NEW LOT FILE
'DISABLE USERFORM
   Me.enabled = False

'CREATE NEW FILE
   If NewLotFile() Then
      SetFileIsLoaded
      EntryOnOff True
   End If

'ENABLE USERFORM
   Me.enabled = True
End Sub



'OPEN BUTTON (LOT CLOSURE FILE)
Private Sub OpenButton_Click()
'OPEN EXISTING LOT FILE
'DISABLE USERFORM
   Me.enabled = False

'GET FILE TO OPEN
   Dim OPENFILENAME As String
   If OpenLotFile(OPENFILENAME) Then
      InitializeForm
      ClearTextBoxes

'LOAD IT IF POSSIBLE
      If LoadLotFile(OPENFILENAME) Then
         SaveSetting APP_NAME, SECTION_LOT_CLOSURE, KEY_FILENAME, OPENFILENAME
         Dim XSplit As Variant
         XSplit = Split(OPENFILENAME, "\")
         FrmPlotLot.Caption = COMMAND_NAME_LOT_CLOSURE & " - " & XSplit(UBound(XSplit))
         SetFileIsLoaded
         EntryOnOff True
         SetTheSelect
         CalcAndDrawCourses
         OutputButtonsStates
         TransformationStates
         EditDelButtonsStates
         AddDGNButtonStates

'SHUT OFF CONTROLS IF NO CAN
      Else
         EntryOnOff False
         InitializeForm
         UnsetFileIsLoaded
         MsgBox "Problem with file"
      End If
   End If

'REENABLE USERFORM
   Me.enabled = True
End Sub



'SAVE AS BUTTON (FILE)
Private Sub SaveAsButton_Click()
'MAKE USER FORM MODAL
   Me.enabled = False

'SAVE CURRENT LOT FILE AS A DIFFERENT FILE
   If SaveAsLotFile() Then
      SetFileIsLoaded
      SetTheSelect
   End If

'RETURN USER FORM FROM MODAL
   Me.enabled = True
End Sub



'OPEN BUTTON (EXPORT TO ASCII)
Private Sub CoordFileOpenButton_Click()
'DISABLE USERFORM
   Me.enabled = False

'OPEN EXISTING COORDINATE FILE
   Dim CoordFilename As String
   Dim CurrentFullFileName As String
   CurrentFullFileName = GetSetting(APP_NAME, SECTION_LOT_CLOSURE, KEY_FILENAME_COORDINATE, "")
   If OpenCoordFilename(CurrentFullFileName, CoordFilename) Then
      SaveSetting APP_NAME, SECTION_LOT_CLOSURE, KEY_FILENAME_COORDINATE, CoordFilename
'UPDATE TEXT BOX
      Dim xSplit2 As Variant
      xSplit2 = Split(CoordFilename, "\")
      FilenameLabel.Caption = xSplit2(UBound(xSplit2))
   End If
   ExportStates
   
'REENABLE USERFORM
   Me.enabled = True
End Sub



'NEW BUTTON (EXPORT TO ASCII)
Private Sub CoordFileNewButton_Click()
'DISABLE USERFORM
   Me.enabled = False

'CREATE NEW COORDINATE FILE
   Dim CoordFilename As String
   Dim CurrentFullFileName As String
   CurrentFullFileName = GetSetting(APP_NAME, SECTION_LOT_CLOSURE, KEY_FILENAME_COORDINATE, "")
   If GetNewCoordFilename(CurrentFullFileName, CoordFilename) Then
      CreateNewCoordinateFile (CoordFilename)
      SaveSetting APP_NAME, SECTION_LOT_CLOSURE, KEY_FILENAME_COORDINATE, CoordFilename
'UPDATE TEXT BOX
      Dim xSplit2 As Variant
      xSplit2 = Split(CoordFilename, "\")
      FilenameLabel.Caption = xSplit2(UBound(xSplit2))
   End If
   ExportStates
   
'REENABLE USERFORM
   Me.enabled = True
End Sub



'POINTNAME TEXTBOX
Private Sub PointNameTextBox_AfterUpdate()
   SavePointNameEntry PointnameTextBox, SECTION_LOT_CLOSURE, KEY_POINTNAME
End Sub

Private Sub PointNameTextBox_Enter()
   SelectAllText PointnameTextBox
End Sub




'USE LOT DESCRIPTION CHECKBOX
Private Sub UseLotDescCheckBox_Click()
   SaveCheckBoxSetting UseLotDescCheckBox, SECTION_LOT_CLOSURE, KEY_OPTION_USE_LOT_DESC
   ExportDescriptionState
End Sub



'DESCRIPTION TEXTBOX (EXPORT TO ASCII)
Private Sub CoordDescTextBox_AfterUpdate()
   SavePointDescEntry CoordDescTextBox, SECTION_LOT_CLOSURE, KEY_POINT_DESC
End Sub

Private Sub CoordDescTextBox_Enter()
   SelectAllText CoordDescTextBox
End Sub



'GENERATE COORDINATES BUTTON
Private Sub GenerateCoordinatesButton_Click()
'EXPORTS COORDINATES TO COORDINATE FILE
   On Error GoTo errhdlr
   Dim CoordinateFilename As String
   CoordinateFilename = GetSetting(APP_NAME, SECTION_LOT_CLOSURE, KEY_FILENAME_COORDINATE, "")
   If CoordinateFilename <> "" Then
      Open CoordinateFilename For Append As #7
      DrawTheCourses GetStartPoint(), Mode_Draw_Export
      Close #7
      MsgBox "Done."
   End If
   Exit Sub
   
errhdlr:
   MsgBox "Error occured."
End Sub



'BATCH BUTTON
Private Sub BatchButton_Click()
   On Error GoTo errhdlr
   Me.enabled = False
   Dim Filenames() As String
   If GetFilesToBatch(Filenames, GetSuggestedLotPath()) Then
      Dim OutputFilename As String
      OutputFilename = GetSetting(APP_NAME, SECTION_LOT_CLOSURE, KEY_FILENAME_COORDINATE, "")
      Open OutputFilename For Append As #7
      
      If UBound(Filenames) = LBound(Filenames) Then 'ONLY ONE FILE CHOSEN
         If Not LoadAndExport(Filenames(0)) Then
            MsgBox "error occured"
         End If
      Else 'MORE THAN ONE FILE CHOSEN
         Dim pathString As String
         pathString = Filenames(0) & "\"
         Dim i As Long
         For i = LBound(Filenames) + 1 To UBound(Filenames)
            If Not LoadAndExport(pathString & Filenames(i)) Then
               MsgBox "error occured"
               Exit For
            End If
         Next i
      End If
      Close #7
      MsgBox "Done."
   End If
   EntryOnOff False
   InitializeForm
   ClearTextBoxes
   UnsetFileIsLoaded
   Me.enabled = True
   Exit Sub
   
errhdlr:
   MsgBox "Error occured."
End Sub



'CHORD PRECISION COMBO BOX
Private Sub ChordPrecisionComboBox_AfterUpdate()
   SaveSetting APP_NAME, SECTION_LOT_CLOSURE, KEY_PRECISION_CHORD, ChordPrecisionComboBox.text
End Sub



'CLOSURE REPORT BUTTON
Private Sub GenerateReportButton_Click()
'GENERATES REPORT FILE
   Dim TheNewFileName As String
   If CreateReportFile(TheNewFileName) Then
      Open TheNewFileName For Output As #2
      ReportTopPart
      DrawTheCourses GetStartPoint(), Mode_Draw_Report
      Close #2
      ShellExecuteNormal TheNewFileName
   End If
End Sub



'BOUNDARY REPORT BUTTON
Private Sub BoundaryReportButton_Click()
'TURN OFF ALL EXCEPT FOR COURSESLISTBOX
   ShutOffChanges
   OffOutputButtons
   OffExportState
   PickLegButton.enabled = False

'REVEAL CANCEL AND CONTINUE BUTTON
   OnOffBoundaryReport True

'CHANGE LISTBOX TO MULTISELECT
   CoursesListBox.MultiSelect = fmMultiSelectMulti

'SIGNAL THAT SELECTING FOR BOUNDARY REPORT
   selectingBoundary = True
      
'BRING PAGE WITH LISTBOX TO THE FOREGROUND
   Me.MultiPage1.value = 1

'INITIATE DRAWING
   DrawTheCourses GetStartPoint(), Mode_Draw_Transient_Hilite_Sel
End Sub



'PROJECT NAME CHECKBOX
Private Sub ReportProjectCheckBox_Click()
   SaveCheckBoxSetting ReportProjectCheckBox, SECTION_LOT_CLOSURE, KEY_OPTION_REPORT_PROJ_NAME
End Sub



'PROJECT NAME TEXTBOX
Private Sub ProjectTextBox_AfterUpdate()
   WriteLotFileIfLoaded
End Sub

Private Sub ProjectTextBox_Enter()
   SelectAllText ProjectTextBox
End Sub



'PROJECT NUMBER CHECKBOX
Private Sub ProjectNumCheckBox_Click()
   SaveCheckBoxSetting ReportProjectCheckBox, SECTION_LOT_CLOSURE, KEY_OPTION_REPORT_PROJ_NUM
End Sub



'PROJECT NUMBER TEXTBOX
Private Sub ProjNumTextBox_AfterUpdate()
   WriteLotFileIfLoaded
End Sub

Private Sub ProjNumTextBox_Enter()
   SelectAllText ProjNumTextBox
End Sub



'DATE CHECBOX
Private Sub ReportDateCheckBox_Click()
   SaveCheckBoxSetting ReportProjectCheckBox, SECTION_LOT_CLOSURE, KEY_OPTION_REPORT_DATE
End Sub



'DATE TEXTBOX
Private Sub DateTextBox_AfterUpdate()
   WriteLotFileIfLoaded
End Sub

Private Sub DateTextBox_Enter()
   SelectAllText DateTextBox
End Sub



'FILL DATE BUTTON
Private Sub DateButton_Click()
   DateTextBox.text = Now
   DateTextBox_AfterUpdate
End Sub



'DRAWING DESCRIPTION CHECKBOX
Private Sub DGNDescriptionCheckBox_Click()
   SaveCheckBoxSetting DGNDescriptionCheckBox, SECTION_LOT_CLOSURE, KEY_OPTION_DGN_DESCRIPTION
End Sub



'REPORT DESCRIPTION CHECKBOX
Private Sub ReportDescriptionCheckBox_Click()
   SaveCheckBoxSetting ReportDescriptionCheckBox, SECTION_LOT_CLOSURE, KEY_OPTION_REPORT_DESCRIPTION
End Sub



'DESCRIPTION TEXTBOX
Private Sub DescriptionTextBox_AfterUpdate()
   WriteLotFileIfLoaded
End Sub

Private Sub DescriptionTextBox_Enter()
   SelectAllText DescriptionTextBox
End Sub



'REPORT AZIMUTH CHECKBOX
Private Sub ReportAzimuthCheckBox_Click()
   SaveCheckBoxSetting ReportAzimuthCheckBox, SECTION_LOT_CLOSURE, KEY_OPTION_REPORT_AZIMUTH
End Sub



'AZIMUTH TEXTBOX
Private Sub AzimuthTextBox_AfterUpdate()
   WriteLotFileIfLoaded
End Sub

Private Sub AzimuthTextBox_Enter()
   SelectAllText AzimuthTextBox
End Sub



'REPORT COORDINATE CHECKBOX
Private Sub ReportCoordinateCheckBox_Click()
   SaveCheckBoxSetting ReportCoordinateCheckBox, SECTION_LOT_CLOSURE, KEY_OPTION_REPORT_COORDINATE
End Sub



'REPORT COORDINATE TEXTBOX
Private Sub CoordinateTextBox_AfterUpdate()
   WriteLotFileIfLoaded
End Sub

Private Sub CoordinateTextBox_Enter()
   SelectAllText CoordinateTextBox
End Sub



'REPORT NOTE CHECKBOX
Private Sub NoteCheckBox_Click()
   SaveCheckBoxSetting NoteCheckBox, SECTION_LOT_CLOSURE, KEY_OPTION_REPORT_NOTE
End Sub



'REPORT NOTE TEXTBOX
Private Sub NoteTextBox_AfterUpdate()
   WriteLotFileIfLoaded
End Sub



'REPORT FILENAME CHECKBOX
Private Sub ReportFilenameCheckBox_Click()
   SaveCheckBoxSetting ReportFilenameCheckBox, SECTION_LOT_CLOSURE, KEY_OPTION_REPORT_FILENAME
   IncludePathState
End Sub



'REPORT INCLUDE PATH CHECKBOX
Private Sub IncludePathCheckBox_Click()
   SaveCheckBoxSetting IncludePathCheckBox, SECTION_LOT_CLOSURE, KEY_OPTION_REPORT_PATH
End Sub



'DRAWING RADIAL LINES CHECKBOX
Private Sub DGNRadialLinesCheckBox_Click()
   SaveCheckBoxSetting DGNRadialLinesCheckBox, SECTION_LOT_CLOSURE, KEY_OPTION_DGN_RADIALS
End Sub



'DRAWING CHORD CHECKBOX
Private Sub DGNChordCheckBox_Click()
   SaveCheckBoxSetting DGNChordCheckBox, SECTION_LOT_CLOSURE, KEY_OPTION_DGN_CHORD
End Sub



'DRAWING AREA CHECKBOX
Private Sub DGNAreaCheckBox_Click()
   SaveCheckBoxSetting DGNAreaCheckBox, SECTION_LOT_CLOSURE, KEY_OPTION_DGN_AREA
   AreaChoicesState
End Sub



'DRAWING AREA SQUARE FEET OPTION BUTTON
Private Sub OptionFeet_Click()
   SaveSetting APP_NAME, SECTION_LOT_CLOSURE, KEY_OPTION_DGN_AREA_TYPE, OPTION_FEET
End Sub



'DRAWING AREA ACRES OPTION BUTTON
Private Sub OptionAcres_Click()
   SaveSetting APP_NAME, SECTION_LOT_CLOSURE, KEY_OPTION_DGN_AREA_TYPE, OPTION_ACRES
End Sub



'DRAWING AREA FEET AND ACRES OPTION BUTTON
Private Sub OptionAcresAndFeet_Click()
   SaveSetting APP_NAME, SECTION_LOT_CLOSURE, KEY_OPTION_DGN_AREA_TYPE, OPTION_FEET_AND_ACRES
End Sub



'*************************************************************************************************************
'***********************************************COURSES TAB***************************************************
'TRANSFORMATION ANGLE CHECKBOX
Private Sub TransformAngleCheckBox_Click()
   SaveCheckBoxSetting TransformAngleCheckBox, SECTION_LOT_CLOSURE, KEY_OPTION_TRANSFORM_ANGLE
   TransAngleTextBoxStates
   TransformationButtonStates
End Sub



'TRAANSFORMATION ANGLE TEXTBOX
Private Sub TransAngleTextBox_AfterUpdate()
   SavePlusMinusAngleEntry TransAngleTextBox, SECTION_LOT_CLOSURE, KEY_TRANSFORMATION_ANGLE, STYLE_ANGLE_LEAD Or STYLE_ANGLE_SPACE, 360#
End Sub

Private Sub TransAngleTextBox_Enter()
   SelectAllText TransAngleTextBox
End Sub



'TRANSFORMATION SCALE CHECKBOX
Private Sub TransformScaleCheckBox_Click()
   SaveCheckBoxSetting TransformScaleCheckBox, SECTION_LOT_CLOSURE, KEY_OPTION_TRANSFORM_SCALE
   TransScaleTextBoxStates
   TransformationButtonStates
End Sub



'TRANSFORMATION SCALE TEXTBOX
Private Sub TransformScaleTextBox_AfterUpdate()
   SaveNonnegativeEntry TransformScaleTextBox, SECTION_LOT_CLOSURE, KEY_TRANSFORMATION_SCALE, MAX_TRANSFORM_SCALE, MAX_PRECISION_TRANFORM_SCALE, False, 1.01
End Sub

Private Sub TransformScaleTextBox_Enter()
   SelectAllText TransformScaleTextBox
End Sub



'TRANSFORMATION SCALE DISTANCE MINIMUM PRECISION COMBOBOX
Private Sub DisPrecComboBox_AfterUpdate()
   SaveSetting APP_NAME, SECTION_LOT_CLOSURE, KEY_PRECISION_DIST, DisPrecComboBox.text
End Sub


'TRANSFORM BUTTON
Private Sub TransformButton_Click()
'TRANSFORMATION BUTTON
'GET USER VERIFICATION
   Dim MsgResp As VbMsgBoxResult
   MsgResp = MsgBox("Apply transformation to all courses?", vbOKCancel, COMMAND_NAME_LOT_CLOSURE)
   Select Case MsgResp
      Case VbMsgBoxResult.vbNo
'DO NOTHING
         Exit Sub
      Case VbMsgBoxResult.vbCancel
'DO NOTHING
         Exit Sub
      Case VbMsgBoxResult.vbOK
'CANCEL ERROR FLAGS
         scaleErrorEncountered = False
'LAUNCH TRANSFORMATION ROUTINES
         If TransformAngleCheckBox.value = True Then
            TransformAngles
         End If
         If TransformScaleCheckBox.value = True Then
            TransformScaleCourses
         End If
         
'IF ERROR IN SCALING, RELOAD FROM FILE
         If scaleErrorEncountered Then
            MsgBox "Error(s) Occured with Scaling"
            InitializeForm
            UnsetFileIsLoaded
            Dim DefaultFilename As String
            DefaultFilename = "C:\output" & Lot_Closure_File_Extension
            Dim fullFilename As String
            fullFilename = GetSetting(APP_NAME, SECTION_LOT_CLOSURE, KEY_FILENAME, DefaultFilename)
            If Not LoadLotFile(fullFilename) Then
               EntryOnOff False
               InitializeForm
               UnsetFileIsLoaded
               MsgBox "error loading file"
               Exit Sub
            End If
            Dim XSplit As Variant
            XSplit = Split(fullFilename, "\")
            FrmPlotLot.Caption = COMMAND_NAME_LOT_CLOSURE & " - " & XSplit(UBound(XSplit))
            SetFileIsLoaded
            EntryOnOff True
            SetTheSelect
            CalcAndDrawCourses
            OutputButtonsStates
            TransformationStates
            EditDelButtonsStates
            AddDGNButtonStates
            MsgBox "Reloaded file"
         End If
'UPDATE EVERYTHING
         UpdateAll
   End Select
End Sub



'USE ALL COURSES CHECHBOX
Private Sub AllCoursesCheckBox_Click()
   SaveCheckBoxSetting AllCoursesCheckBox, SECTION_LOT_CLOSURE, KEY_OPTION_ALL_COURSES
   CreateCellStates
End Sub



'CREATE AS CELL CHECKBOX
Private Sub CreateAsCellCheckBox_Click()
   SaveCheckBoxSetting CreateAsCellCheckBox, SECTION_LOT_CLOSURE, KEY_OPTION_CREATE_CELL
End Sub



'COMPLEX CHAIN CHECKBOX
Private Sub ComplexCheckBox_Click()
   SaveCheckBoxSetting ComplexCheckBox, SECTION_LOT_CLOSURE, KEY_OPTION_COMPLEX_CHAIN
End Sub



'STARTING POINT Z TEXTBOX
Private Sub ZTextbox_AfterUpdate()
   Dim z As Double
   Dim origPrec As Long
   If IsElevationString(ZTextbox.text, z, origPrec) Then
      startingPoint.z = Round(CDbl(ZTextbox.text), StartPointPrec)
      UpdateAll
   Else
      Beep
   End If
   ZTextbox.text = FormatNumber(startingPoint.z, StartPointPrec)
End Sub

Private Sub ZTextbox_Enter()
   SelectAllText ZTextbox
End Sub



'STARTING POINT NORTHING TEXTBOX
Private Sub NorthingTextbox_AfterUpdate()
   Dim northing As Double
   Dim origPrec As Long
   If IsNorthingString(NorthingTextBox.text, northing, origPrec) Then
      startingPoint.Y = Round(northing, StartPointPrec)
      UpdateAll
   Else
      Beep
   End If
   NorthingTextBox.text = DoubleToNorthingString(startingPoint.Y, StartPointPrec)
End Sub

Private Sub NorthingTextbox_Enter()
   SelectAllText NorthingTextBox
End Sub



'STARTING POINT EASTING TEXTBOX
Private Sub EastingTextbox_AfterUpdate()
   Dim easting As Double
   Dim origPrec As Long
   If IsEastingString(EastingTextBox.text, easting, origPrec) Then
      startingPoint.X = Round(easting, StartPointPrec)
      UpdateAll
   Else
      Beep
   End If
   EastingTextBox.text = DoubleToEastingString(startingPoint.X, StartPointPrec)
End Sub

Private Sub EastingTextbox_Enter()
   SelectAllText EastingTextBox
End Sub



'STARTING POINT PICK BUTTON
Private Sub StartPickButton_Click()
'PICK START POINT
   CommandState.StartPrimitive New PlotLotPickStartPrimitive
End Sub


'COURSES LISTBOX
Private Sub CoursesListBox_Change()
   If CoursesListBox.MultiSelect = fmMultiSelectMulti Then
      If selectingBoundary Then
         DrawTheCourses GetStartPoint(), Mode_Draw_Transient_Hilite_Sel
      Else
         DrawTheCourses GetStartPoint(), Mode_Draw_Transient_Blank_Sel
      End If
   End If
End Sub

Private Sub CoursesListBox_Click()
   If GetInsertingFlag = False Then
      If CoursesListBox.MultiSelect = fmMultiSelectMulti Then
         If selectingBoundary Then
            DrawTheCourses GetStartPoint(), Mode_Draw_Transient_Hilite_Sel
         Else
            DrawTheCourses GetStartPoint(), Mode_Draw_Transient_Blank_Sel
         End If
      Else
         CalcAndDrawCourses
      End If
   End If
End Sub

Private Sub CoursesListBox_DblClick(ByVal Cancel As MSForms.ReturnBoolean)
   If CoursesListBox.MultiSelect = fmMultiSelectSingle Then
      CalcAndDrawCourses
      EditCourse
   End If
End Sub



'PICK LEG BUTTON
Private Sub PickLegButton_Click()
'CHOOSE LEG TO MAKE CURRENT
   CommandState.StartPrimitive New LotClosurePickLegPrim
End Sub



'ADD TO DGN BUTTON
Private Sub DrawButton_Click()
'INITIATE PERMANENT GRAPHICS PROCESS, VERIFICATION SCREEN
   If CoursesListBox.ListCount <= 0 Then
      MsgBox "No courses to add!"
      Exit Sub
   End If

   If ActiveModelReference.IsReadOnly = True Then
'NO CAN WRITE TO FILE, GIVE ERROR
      ReadOnlyErrorMess
      Exit Sub
   End If

'REVEAL CANCEL AND ADD IT BUTTON
   CancelButton.Visible = True
   AddItButton.Visible = True

'TURN OFF ALL EXCEPT FOR COURSESLISTBOX
   ShutOffChanges
   OffOutputButtons
   OffExportState

'DISABLE LEG PICKING FUNCTION FOR SELECTING LEGS TO DRAW
   PickLegButtonState False

'CHOOSE COURSES TO EXCLUDE IF DESIRED
   If AllCoursesCheckBox.value = False Then
'SIGNAL THAT NOT SELECTING FOR BOUNDARY REPORT
      selectingBoundary = False
      CoursesListBox.MultiSelect = fmMultiSelectMulti
      DrawTheCourses GetStartPoint(), Mode_Draw_Transient_Blank_Sel
      InstructionLabel.Visible = True
   Else
'ELSE DRAW HIGHLIGHTED
      DrawTheCourses GetStartPoint(), Mode_Draw_Transient_Hilite_All
   End If
End Sub



'CANCEL BUTTON
Private Sub CancelButton_Click()
'CANCEL CREATING PERMANENT GRAPHICS
'HIDE CANCEL AND ADD IT BUTTON
   CancelButton.Visible = False
   AddItButton.Visible = False

'RETURN TO SINGLE SELECT
   CoursesListBox.MultiSelect = fmMultiSelectSingle
   SetTheSelect
   
'TURN CONTROLS BACK ON
   TurnOnChanges
   OutputButtonsStates
   TransformationStates
   EditDelButtonsStates
   AddDGNButtonStates
   OnExportState
   
'CLEAR MESSAGES
   ClearCommandPromptArea
   InstructionLabel.Visible = False
End Sub



'ADD IT BUTTON
Private Sub AddItButton_Click()
'CREATE PERMANENT GRAPHICS IN DRAWING
   If ActiveModelReference.IsReadOnly = True Then
'NO CAN WRITE TO FILE, GIVE ERROR
      ReadOnlyErrorMess
   Else
'ADD TO DGN HERE
      DrawTheCourses GetStartPoint(), Mode_Draw_Permanent
   End If
'CLEAR MESSAGES, GIVE FEEDBACK
   InstructionLabel.Visible = False
   ShowCommand COMMAND_NAME_LOT_CLOSURE
   ShowPrompt ""
   ShowStatus "Elements Added to DGN"

'HIDE CANCEL AND ADD IT BUTTON
   CancelButton.Visible = False
   AddItButton.Visible = False

'RETURN TO SINGLE SELECT
   CoursesListBox.MultiSelect = fmMultiSelectSingle
   SetTheSelect
   DrawTheCourses GetStartPoint(), Mode_Draw_Transient_Hilite_All

'TURN CONTROLS BACK ON
   TurnOnChanges
   OutputButtonsStates
   TransformationStates
   EditDelButtonsStates
   AddDGNButtonStates
   OnExportState
End Sub



'BOUNDARY REPORT CANCEL BUTTON
Private Sub BoundaryCancelButton_Click()
   EndBoundaryReportState
End Sub



'BOUNDARY REPORT CONTINUE BUTTON
Private Sub ContinueButton_Click()
'DISABLE CANCEL AND CONTINUE BUTTONS
   BoundaryCancelButton.enabled = False
   ContinueButton.enabled = False
   
'GET FILENAME FOR REPORT
   Dim TheNewFileName As String
   If CreateReportFile(TheNewFileName) Then
'WRITE REPORT HERE
      Open TheNewFileName For Output As #2
      ReportBoundaryTopPart
      DrawTheCourses GetStartPoint(), Mode_Draw_Boundary_Report
      Close #2
'OPEN REPORT FILE
      ShellExecuteNormal TheNewFileName
   End If
   
'RESTORE TO NORMAL
   EndBoundaryReportState
End Sub



'DELETE BUTTON
Private Sub DeleteButton_Click()
'DELETE COURSE
   If CoursesListBox.listIndex >= 0 Then
      CoursesListBox.RemoveItem CoursesListBox.listIndex
      RenumberCourses
      UpdateAll
   End If
End Sub



'EDIT BUTTON
Private Sub EditButton_Click()
'EDIT SELECTED COURSE
   EditCourse
End Sub



'INSERT COURSE BUTTON
Private Sub InsertButton_Click()
'INSERT COURSES
   SetModeIAmIn Mode_Insert
   SetInsertingFlag
   SetTheCurrentIndex CoursesListBox.listIndex + 1
   FrmEnterCourse.UserForm_Initialize
   FrmEnterCourse.Show
End Sub



'ROLL UP BUTTON
Private Sub RollUpButton_Click()
   RollUp
   UpdateAll
End Sub



'ROLL DOWN BUTTON
Private Sub RollDownButton_Click()
   RollDown
   UpdateAll
End Sub



'*************************************************************************************************************
'***********************************************SETTINGS TAB**************************************************
'BOUNDARY LINE LEVEL COMBOBOX
Private Sub BoundaryLevelComboBox_AfterUpdate()
   If Not LevelBoxOnUpdate(BoundaryLevelComboBox, SECTION_LOT_CLOSURE, KEY_BOUNDARY_LEVEL) Then
      PopulateBoundaryLevelBox
      Beep
   End If
End Sub

Private Sub PopulateBoundaryLevelBox()
   PopulateLevelBox BoundaryLevelComboBox, SECTION_LOT_CLOSURE, KEY_BOUNDARY_LEVEL
End Sub



'BOUNDARY LINE COLOR COMBOBOX
Private Sub BoundaryColorComboBox_AfterUpdate()
   ColorBoxOnUpdate BoundaryColorComboBox, SECTION_LOT_CLOSURE, KEY_BOUNDARY_COLOR
End Sub

Private Sub PopulateBoundaryColorBox()
   PopulateColorBox BoundaryColorComboBox, SECTION_LOT_CLOSURE, KEY_BOUNDARY_COLOR
End Sub



'BOUNDARY COLOR CHOOSER BUTTON
Private Sub BoundaryColorChooserButton_Click()
   Dim MyColor As String
   If ChooseMyTableColor(MyColor) Then
      BoundaryColorComboBox.text = MyColor
      BoundaryColorComboBox_AfterUpdate
   End If
End Sub



'BOUNDARY LINE LINESTYLE COMBOBOX
Private Sub BoundaryStyleComboBox_AfterUpdate()
   If Not LineStyleBoxOnUpdate(BoundaryStyleComboBox, SECTION_LOT_CLOSURE, KEY_BOUNDARY_STYLE) Then
      PopulateBoundaryStyleBox
      Beep
   End If
End Sub

Private Sub PopulateBoundaryStyleBox()
   PopulateLinestyleBox BoundaryStyleComboBox, SECTION_LOT_CLOSURE, KEY_BOUNDARY_STYLE
End Sub



'BOUNDARY LINE WEIGHT COMBOBOX
Private Sub BoundaryWeightComboBox_AfterUpdate()
   WeightBoxOnUpdate BoundaryWeightComboBox, SECTION_LOT_CLOSURE, KEY_BOUNDARY_WEIGHT
End Sub

Private Sub PopulateBoundaryWeightBox()
   PopulateWeightBox BoundaryWeightComboBox, SECTION_LOT_CLOSURE, KEY_BOUNDARY_WEIGHT
End Sub



'CHORD LEVEL COMBOBOX
Private Sub ChordLevelComboBox_AfterUpdate()
   If Not LevelBoxOnUpdate(ChordLevelComboBox, SECTION_LOT_CLOSURE, KEY_CHORD_LEVEL) Then
      PopulateChordLevelBox
      Beep
   End If
End Sub

Private Sub PopulateChordLevelBox()
   PopulateLevelBox ChordLevelComboBox, SECTION_LOT_CLOSURE, KEY_CHORD_LEVEL
End Sub



'CHORD COLOR COMBOBOX
Private Sub ChordColorComboBox_AfterUpdate()
   ColorBoxOnUpdate ChordColorComboBox, SECTION_LOT_CLOSURE, KEY_CHORD_COLOR
End Sub

Private Sub PopulateChordColorBox()
   PopulateColorBox ChordColorComboBox, SECTION_LOT_CLOSURE, KEY_CHORD_COLOR
End Sub



'CHORD COLOR CHOOSER BUTTON
Private Sub ChordColorChooserButton_Click()
   Dim MyColor As String
   If ChooseMyTableColor(MyColor) Then
      ChordColorComboBox.text = MyColor
      ChordColorComboBox_AfterUpdate
   End If
End Sub



'CHORD LINESTYLE COMBOBOX
Private Sub ChordStyleComboBox_AfterUpdate()
   If Not LineStyleBoxOnUpdate(ChordStyleComboBox, SECTION_LOT_CLOSURE, KEY_CHORD_STYLE) Then
      PopulateChordStyleBox
      Beep
   End If
End Sub

Private Sub PopulateChordStyleBox()
   PopulateLinestyleBox ChordStyleComboBox, SECTION_LOT_CLOSURE, KEY_CHORD_STYLE
End Sub



'CHORD WEIGHT COMBOBOX
Private Sub ChordWeightComboBox_AfterUpdate()
   WeightBoxOnUpdate ChordWeightComboBox, SECTION_LOT_CLOSURE, KEY_CHORD_WEIGHT
End Sub

Private Sub PopulateChordWeightBox()
   PopulateWeightBox ChordWeightComboBox, SECTION_LOT_CLOSURE, KEY_CHORD_WEIGHT
End Sub



'RADIAL LINES LEVEL COMBOBOX
Private Sub RadialsLevelComboBox_AfterUpdate()
   If Not LevelBoxOnUpdate(RadialsLevelComboBox, SECTION_LOT_CLOSURE, KEY_RADIALS_LEVEL) Then
      PopulateRadialsLevelBox
      Beep
   End If
End Sub

Private Sub PopulateRadialsLevelBox()
   PopulateLevelBox RadialsLevelComboBox, SECTION_LOT_CLOSURE, KEY_RADIALS_LEVEL
End Sub



'RADIAL LINES COLOR COMBOBOX
Private Sub RadialsColorComboBox_AfterUpdate()
   ColorBoxOnUpdate RadialsColorComboBox, SECTION_LOT_CLOSURE, KEY_RADIALS_COLOR
End Sub

Private Sub PopulateRadialsColorBox()
   PopulateColorBox RadialsColorComboBox, SECTION_LOT_CLOSURE, KEY_RADIALS_COLOR
End Sub



'RADIAL LINES COLOR CHOOSER BUTTON
Private Sub RadialsColorChooserButton_Click()
   Dim MyColor As String
   If ChooseMyTableColor(MyColor) Then
      RadialsColorComboBox.text = MyColor
      RadialsColorComboBox_AfterUpdate
   End If
End Sub



'RADIAL LINES LINESTYLE COMBOBOX
Private Sub RadialsStyleComboBox_AfterUpdate()
   If Not LineStyleBoxOnUpdate(RadialsStyleComboBox, SECTION_LOT_CLOSURE, KEY_RADIALS_STYLE) Then
      PopulateRadialsStyleBox
      Beep
   End If
End Sub

Private Sub PopulateRadialsStyleBox()
   PopulateLinestyleBox RadialsStyleComboBox, SECTION_LOT_CLOSURE, KEY_RADIALS_STYLE
End Sub



'RADIAL LINES WEIGHT COMBOBOX
Private Sub RadialsWeightComboBox_AfterUpdate()
   WeightBoxOnUpdate RadialsWeightComboBox, SECTION_LOT_CLOSURE, KEY_RADIALS_WEIGHT
End Sub

Private Sub PopulateRadialsWeightBox()
   PopulateWeightBox RadialsWeightComboBox, SECTION_LOT_CLOSURE, KEY_RADIALS_WEIGHT
End Sub




'DESCRIPTION TEXT LEVEL COMBOBOX
Private Sub DescriptionLevelComboBox_AfterUpdate()
   If Not LevelBoxOnUpdate(DescriptionLevelComboBox, SECTION_LOT_CLOSURE, KEY_DESCRIPTION_LEVEL) Then
      PopulateDescriptionLevelComboBox
      Beep
   End If
End Sub

Private Sub PopulateDescriptionLevelComboBox()
   PopulateLevelBox DescriptionLevelComboBox, SECTION_LOT_CLOSURE, KEY_DESCRIPTION_LEVEL
End Sub



'DESCRIPTION TEXT COLOR COMBOBOX
Private Sub DescriptionColorComboBox_AfterUpdate()
   ColorBoxOnUpdate DescriptionColorComboBox, SECTION_LOT_CLOSURE, KEY_DESCRIPTION_COLOR
End Sub

Private Sub PopulateDescriptionColorComboBox()
   PopulateColorBox DescriptionColorComboBox, SECTION_LOT_CLOSURE, KEY_DESCRIPTION_COLOR
End Sub



'DESCRIPTION TEXT COLOR CHOOSER BUTTON
Private Sub DescColorChooserButton_Click()
   Dim MyColor As String
   If ChooseMyTableColor(MyColor) Then
      DescriptionColorComboBox.text = MyColor
      DescriptionColorComboBox_AfterUpdate
   End If
End Sub



'DESCRIPTION TEXT LINESTYLE COMBOBOX
Private Sub DescriptionStyleComboBox_AfterUpdate()
   If Not LineStyleBoxOnUpdate(DescriptionStyleComboBox, SECTION_LOT_CLOSURE, KEY_DESCRIPTION_STYLE) Then
      PopulateDescriptionStyleComboBox
      Beep
   End If
End Sub

Private Sub PopulateDescriptionStyleComboBox()
   PopulateLinestyleBox DescriptionStyleComboBox, SECTION_LOT_CLOSURE, KEY_DESCRIPTION_STYLE
End Sub



'DESCRIPTION TEXT WEIGHT COMBOBOX
Private Sub DescriptionWeightComboBox_AfterUpdate()
   WeightBoxOnUpdate DescriptionWeightComboBox, SECTION_LOT_CLOSURE, KEY_DESCRIPTION_WEIGHT
End Sub

Private Sub PopulateDescriptionWeightComboBox()
   PopulateWeightBox DescriptionWeightComboBox, SECTION_LOT_CLOSURE, KEY_DESCRIPTION_WEIGHT
End Sub



'DESCRIPTION TEXT FONT COMBOBOX
Private Sub DescriptionFontComboBox_AfterUpdate()
   If Not FontBoxOnUpdate(DescriptionFontComboBox, SECTION_LOT_CLOSURE, KEY_DESCRIPTION_FONT) Then
      PopulateDescriptionFontComboBox
      Beep
   End If
End Sub

Private Sub PopulateDescriptionFontComboBox()
   PopulateFontBox DescriptionFontComboBox, SECTION_LOT_CLOSURE, KEY_DESCRIPTION_FONT
End Sub



'DESCRIPTION TEXT FONT SCALE TEXTBOX
Private Sub DescriptionFontScaleTextBox_AfterUpdate()
   SaveNonnegativeEntry DescriptionFontScaleTextBox, SECTION_LOT_CLOSURE, KEY_DESCRIPTION_FONT_SCALE, MAX_FONT_SCALE, MAX_PRECISION_FONT_SCALE, False, 1#
End Sub

Private Sub DescriptionFontScaleTextBox_Enter()
   SelectAllText DescriptionFontScaleTextBox
End Sub



'AREA TEXT LEVEL COMBOBOX
Private Sub AreaLevelComboBox_AfterUpdate()
   If Not LevelBoxOnUpdate(AreaLevelComboBox, SECTION_LOT_CLOSURE, KEY_AREA_LEVEL) Then
      PopulateAreaLevelComboBox
      Beep
   End If
End Sub

Private Sub PopulateAreaLevelComboBox()
   PopulateLevelBox AreaLevelComboBox, SECTION_LOT_CLOSURE, KEY_AREA_LEVEL
End Sub



'AREA TEXT COLOR COMBOBOX
Private Sub AreaColorComboBox_AfterUpdate()
   ColorBoxOnUpdate AreaColorComboBox, SECTION_LOT_CLOSURE, KEY_AREA_COLOR
End Sub

Private Sub PopulateAreaColorComboBox()
   PopulateColorBox AreaColorComboBox, SECTION_LOT_CLOSURE, KEY_AREA_COLOR
End Sub



'AREA TEXT COLOR CHOOSER BUTTON
Private Sub AreaColorChooserButton_Click()
   Dim MyColor As String
   If ChooseMyTableColor(MyColor) Then
      AreaColorComboBox.text = MyColor
      AreaColorComboBox_AfterUpdate
   End If
End Sub



'AREA TEXT LINESTYLE COMBOBOX
Private Sub AreaStyleComboBox_AfterUpdate()
   If Not LineStyleBoxOnUpdate(AreaStyleComboBox, SECTION_LOT_CLOSURE, KEY_AREA_STYLE) Then
      PopulateAreaStyleComboBox
      Beep
   End If
End Sub

Private Sub PopulateAreaStyleComboBox()
   PopulateLinestyleBox AreaStyleComboBox, SECTION_LOT_CLOSURE, KEY_AREA_STYLE
End Sub



'AREA TEXT WEIGHT COMBOBOX
Private Sub AreaWeightComboBox_AfterUpdate()
   WeightBoxOnUpdate AreaWeightComboBox, SECTION_LOT_CLOSURE, KEY_AREA_WEIGHT
End Sub

Private Sub PopulateAreaWeightComboBox()
   PopulateWeightBox AreaWeightComboBox, SECTION_LOT_CLOSURE, KEY_AREA_WEIGHT
End Sub



'AREA TEXT FONT COMBOBOX
Private Sub AreaFontComboBox_AfterUpdate()
   If Not FontBoxOnUpdate(AreaFontComboBox, SECTION_LOT_CLOSURE, KEY_AREA_FONT) Then
      PopulateAreaFontComboBox
      Beep
   End If
End Sub

Private Sub PopulateAreaFontComboBox()
   PopulateFontBox AreaFontComboBox, SECTION_LOT_CLOSURE, KEY_AREA_FONT
End Sub



'AREA TEXT FONT SCALE TEXTBOX
Private Sub AreaFontScaleTextBox_AfterUpdate()
   SaveNonnegativeEntry AreaFontScaleTextBox, SECTION_LOT_CLOSURE, KEY_AREA_FONT_SCALE, MAX_FONT_SCALE, MAX_PRECISION_FONT_SCALE, False, 1#
End Sub

Private Sub AreaFontScaleTextBox_Enter()
   SelectAllText AreaFontScaleTextBox
End Sub



'BIG/SMALL TOGGLE BUTTON
Private Sub BigSmallButton_Click()
   If Me.Zoom = 100 Then
      SaveSetting APP_NAME, SECTION_LOT_CLOSURE, KEY_BIG, OPTION_TRUE
      dialogBig True
   Else
      SaveSetting APP_NAME, SECTION_LOT_CLOSURE, KEY_BIG, OPTION_FALSE
      dialogBig False
   End If
End Sub



Private Sub dialogBig(big As Boolean)
   If big Then
      Me.Zoom = 140
      Me.Height = 369.75 * 1.4
      Me.Width = 497.25 * 1.4
   Else
      Me.Zoom = 100
      Me.Height = 369.75
      Me.Width = 497.25
   End If
End Sub


'CLEAR TEXT BOXES WITH NEW FILE CHECKBOX
Private Sub ClearTexBoxesCheckBox_Click()
   SaveCheckBoxSetting ClearTexBoxesCheckBox, SECTION_LOT_CLOSURE, KEY_OPTION_CLEAR_TEXT
End Sub



'SETTINGS BUTTON
Private Sub SettingsButton_Click()
   Setting
End Sub



'*************************************************************************************************************
'**********************************************CONTROLS STATE*************************************************
Private Sub AddDGNButtonStates()
   DrawButton.enabled = IsFileLoaded() And CoursesListBox.ListCount >= 1
   UseAllStates
End Sub



Private Sub AreaChoicesState()
   Dim enabledState As Boolean
   enabledState = DGNAreaCheckBox.value

   OptionFeet.enabled = enabledState
   OptionAcres.enabled = enabledState
   OptionAcresAndFeet.enabled = enabledState
End Sub



Private Sub CoursesBoxOnOff(ByVal enabledState As Boolean)
   CoursesListBox.enabled = enabledState
   CoursesListBox.BackColor = BackOLE_COLOR(enabledState)
End Sub



Private Sub CourseDataOnOff(ByVal enabledState As Boolean)
   CourseFrame.enabled = enabledState
   CourseNumberLabel.enabled = enabledState
   CourseTypeLabel.enabled = enabledState
   ChrodAzLabel.enabled = enabledState
   ChordDisLabel.enabled = enabledState
   BeginCoordLabel.enabled = enabledState
   EndCoordLabel.enabled = enabledState
   RadiusPointLabel.enabled = enabledState
   SegmentAreaLabel.enabled = enabledState
   CourseNumberDispLabel.enabled = enabledState
   CourseTypeDispLabel.enabled = enabledState
   ChordAzDispLabel.enabled = enabledState
   ChordDistDispLabel.enabled = enabledState
   BeginPointNorDispLabel.enabled = enabledState
   BeginPointEastDispLabel.enabled = enabledState
   SegmentAreaDispLabel.enabled = enabledState
   EndPointNorDispLabel.enabled = enabledState
   EndPointEastDispLabel.enabled = enabledState
   RadPointNorDispLabel.enabled = enabledState
   RadPointEastDispLabel.enabled = enabledState
End Sub



Private Sub CreateCellStates()
   CreateAsCellCheckBox.enabled = AllCoursesCheckBox.enabled And AllCoursesCheckBox.value
   ComplexCheckBox.enabled = CreateAsCellCheckBox.enabled
End Sub



Private Sub EastingOnOff(ByVal enabledState As Boolean)
   EastingTextBox.enabled = enabledState
   EastingTextBox.BackColor = BackOLE_COLOR(enabledState)
   LabelEasting.enabled = enabledState
End Sub



Private Sub EditDelButtonsStates()
   Dim enabledState As Boolean
   enabledState = IsFileLoaded() And CoursesListBox.ListCount >= 1 And CoursesListBox.listIndex <> -1

   DeleteButton.enabled = enabledState
   EditButton.enabled = enabledState
   PickLegButtonState enabledState
   RollStates
End Sub



Private Sub ElevationOnOff(ByVal enabledState As Boolean)
   ZTextbox.enabled = enabledState
   ZTextbox.BackColor = BackOLE_COLOR(enabledState)
   LabelEl.enabled = enabledState
End Sub



Private Sub EntryOnOff(ByVal enabledState As Boolean)
   FrameCourses.enabled = enabledState
   CoursesBoxOnOff enabledState
   DeleteButton.enabled = enabledState
   EditButton.enabled = enabledState
   InsertButton.enabled = enabledState
   NorthingOnOff enabledState
   EastingOnOff enabledState
   ElevationOnOff enabledState
   StartPickButton.enabled = enabledState
   FrameStart.enabled = enabledState
   DrawButton.enabled = enabledState
   TransformationFrame.enabled = enabledState
   StatusOnOff enabledState
   CourseDataOnOff enabledState
   PickLegButtonState enabledState
End Sub



Private Sub ExportDescriptionState()
   Dim enabledState As Boolean
   enabledState = (Not UseLotDescCheckBox.value) And UseLotDescCheckBox.enabled

   DescLabel.enabled = enabledState
   CoordDescTextBox.enabled = enabledState
   CoordDescTextBox.BackColor = BackOLE_COLOR(enabledState)
End Sub



Private Sub ExportStates()
   If Trim(FilenameLabel.Caption) = "" Then
      Dim enabledState As Boolean
      enabledState = False
   Else
      enabledState = True
   End If
   PointLabel.enabled = enabledState
   PointnameTextBox.enabled = enabledState
   PointnameTextBox.BackColor = BackOLE_COLOR(enabledState)
   UseLotDescCheckBox.enabled = enabledState
   ExportDescriptionState
   BatchButton.enabled = Trim(FilenameLabel.Caption) <> ""
   enabledState = enabledState And fileIsLoaded
   GenerateCoordinatesButton.enabled = enabledState
End Sub



Private Sub OffExportState()
   PointLabel.enabled = False
   PointnameTextBox.enabled = False
   PointnameTextBox.BackColor = BackOLE_COLOR(False)
   UseLotDescCheckBox.enabled = False
   ExportDescriptionState
   BatchButton.enabled = False
   GenerateCoordinatesButton.enabled = False
   CoordFileOpenButton.enabled = False
   CoordFileNewButton.enabled = False
   CoordFileLabel.enabled = False
   FilenameLabel.enabled = False
   ExportFrame.enabled = False
End Sub

Private Sub OnExportState()
   CoordFileOpenButton.enabled = True
   CoordFileNewButton.enabled = True
   CoordFileLabel.enabled = True
   FilenameLabel.enabled = True
   ExportFrame.enabled = True
   ExportStates
End Sub


Private Sub OnOffBoundaryReport(state As Boolean)
   BoundaryCancelButton.Visible = state
   ContinueButton.Visible = state
   BoundaryInstructionLabel.Visible = state
   BoundaryCancelButton.enabled = state
   ContinueButton.enabled = state
End Sub


Private Sub EndBoundaryReportState()
'HIDE CONTROLS
   OnOffBoundaryReport False

'CHANGE LISTBOX BACK TO NORMAL
   CoursesListBox.MultiSelect = fmMultiSelectSingle
   CoursesListBox.listIndex = 0
   DrawTheCourses GetStartPoint(), Mode_Draw_Transient_Hilite_Sel

'TURN CONTROLS BACK ON
   TurnOnChanges
   OutputButtonsStates
   TransformationStates
   EditDelButtonsStates
   AddDGNButtonStates
   OnExportState

'RETURN TO FIRST PAGE
   Me.MultiPage1.value = 0
End Sub



Private Sub IncludePathState()
   IncludePathCheckBox.enabled = ReportFilenameCheckBox.value
End Sub



Private Sub NorthingOnOff(ByVal enabledState As Boolean)
   NorthingTextBox.enabled = enabledState
   NorthingTextBox.BackColor = BackOLE_COLOR(enabledState)
   LabelNorthing.enabled = enabledState
End Sub



Public Sub OffOutputButtons()
   ChordPrecisionLabel.enabled = False
   ChordPrecisionComboBox.enabled = False
   ChordPrecisionComboBox.BackColor = backgroundGrey
   GenerateReportButton.enabled = False
   BoundaryReportButton.enabled = False
   ExportStates
   DrawButton.enabled = False
   ReportFrame.enabled = False
End Sub



Public Sub OutputButtonsStates()
   If IsFileLoaded() And CoursesListBox.ListCount >= 1 Then
      ChordPrecisionLabel.enabled = True
      ChordPrecisionComboBox.enabled = True
      ChordPrecisionComboBox.BackColor = backgroundWhite
      GenerateReportButton.enabled = True
      BoundaryReportButton.enabled = True
      ReportFrame.enabled = True
      ExportStates
   Else
      OffOutputButtons
   End If
End Sub



Private Sub PickLegButtonState(editstate As Boolean)
   If CoursesListBox.ListCount < 2 Then
      PickLegButton.enabled = False
   ElseIf CoursesListBox.MultiSelect = fmMultiSelectMulti Then
      PickLegButton.enabled = False
   Else
      PickLegButton.enabled = editstate
   End If
End Sub



Private Sub RollStates()
   SetRollState OkToRoll()
End Sub



Private Sub SetRollState(state As Boolean)
   RollUpButton.enabled = state
   RollDownButton.enabled = state
   RollUpButton.Visible = state
   RollDownButton.Visible = state
End Sub



Private Sub ShutOffChanges()
   DeleteButton.enabled = False
   EditButton.enabled = False
   InsertButton.enabled = False
   NorthingOnOff False
   EastingOnOff False
   ElevationOnOff False
   StartPickButton.enabled = False
   FrameStart.enabled = False
   DrawButton.enabled = False
   StatusOnOff False
   CourseDataOnOff False
   CourseFrame.enabled = False
   OpenButton.enabled = False
   NewButton.enabled = False
   FilesFrame.enabled = False
   SaveAsButton.enabled = False
   AddDGNButtonStates
   TransformationFrame.enabled = False
   TransformationStates
   AllCoursesCheckBox.enabled = False
   CreateCellStates
   SetRollState False
End Sub



Private Sub StatusOnOff(ByVal enabledState As Boolean)
   FrameStatus.enabled = enabledState
   NorthingErrorLabel.enabled = enabledState
   EastingErrorLabel.enabled = enabledState
   MiscloseDirectionLabel.enabled = enabledState
   MiscloseDistanceLabel.enabled = enabledState
   DMDLabel.enabled = enabledState
   NorthErrorDispLabel.enabled = enabledState
   EastErrorDispLabel.enabled = enabledState
   CloseAzimuthDispLabel.enabled = enabledState
   CloseDistanceDispLabel.enabled = enabledState
   TotalAreaDispLabel.enabled = enabledState
   TotalAcresLabel.enabled = enabledState
End Sub



Private Sub TransformationStates()
   Dim enabledState As Boolean
   enabledState = IsFileLoaded() And CoursesListBox.ListCount >= 1 And TransformationFrame.enabled

   TransformAngleCheckBox.enabled = enabledState
   TransformScaleCheckBox.enabled = enabledState
   TransAngleTextBoxStates
   TransScaleTextBoxStates
   TransformationButtonStates
End Sub


Private Sub TransAngleTextBoxStates()
   Dim enabledState As Boolean
   enabledState = TransformAngleCheckBox.enabled And TransformAngleCheckBox.value

   TransAngleTextBox.enabled = enabledState
   TransAngleTextBox.BackColor = BackOLE_COLOR(enabledState)
End Sub



Private Sub TransScaleTextBoxStates()
   Dim enabledState As Boolean
   enabledState = TransformScaleCheckBox.enabled And TransformScaleCheckBox.value

   TransformScaleTextBox.enabled = enabledState
   TransformScaleTextBox.BackColor = BackOLE_COLOR(enabledState)
   DisPrecComboBox.enabled = enabledState
   DisPrecComboBox.BackColor = BackOLE_COLOR(enabledState)
   distPrecLabel.enabled = enabledState
End Sub



Private Sub TransformationButtonStates()
   TransformButton.enabled = (TransformAngleCheckBox.enabled And (TransformAngleCheckBox.value Or TransformScaleCheckBox.value))
End Sub



Private Sub TurnOnChanges()
   DeleteButton.enabled = True
   EditButton.enabled = True
   InsertButton.enabled = True
   NorthingOnOff True
   EastingOnOff True
   ElevationOnOff True
   StartPickButton.enabled = True
   FrameStart.enabled = True
   DrawButton.enabled = True
   CourseFrame.enabled = True
   StatusOnOff True
   CourseDataOnOff True
   OpenButton.enabled = True
   NewButton.enabled = True
   FilesFrame.enabled = True
   SaveAsButton.enabled = True
   AddDGNButtonStates
   TransformationFrame.enabled = True
   TransformationStates
   EditDelButtonsStates
   UseAllStates
   RollStates
End Sub



Private Sub UseAllStates()
   AllCoursesCheckBox.enabled = DrawButton.enabled
   CreateCellStates
End Sub



'*************************************************************************************************************
'*************************************************************************************************************
Public Sub ClearTextBoxes()
'CLEARS OUT THE REPORT TEXT BOXES
   ProjectTextBox.text = ""
   ProjNumTextBox.text = ""
   DateTextBox.text = ""
   AzimuthTextBox.text = ""
   CoordinateTextBox.text = ""
   DescriptionTextBox.text = ""
   NoteTextBox.text = ""
End Sub



Private Sub ClearTransients()
'CLEAR OUT TEMPORARY GRAPHICS CONTAINERS
   Set tecNormal = Nothing
   Set tecHilite = Nothing
End Sub



Private Sub EditCourse()
'LAUNCHES COURSE EDIT DIALOG BOX
   If CoursesListBox.ListCount < 1 Then
      MsgBox "Nothing to edit"
   ElseIf CoursesListBox.listIndex >= 0 Then
      SetModeIAmIn Mode_Edit
      SetTheCurrentIndex CoursesListBox.listIndex
      FrmEnterCourse.UserForm_Initialize
      FrmEnterCourse.Show
   End If
End Sub



Public Sub InitializeForm()
'INITIALIZE STARTING POINT
   IntializeStartPoint
   UpdateStartPointText
   CreateNormalTransientContainer
   CreateHiliteTransientContainer

'RESET LIST BOX
   CoursesListBox.Clear

'RESET TITLE BAR
   FrmPlotLot.Caption = COMMAND_NAME_LOT_CLOSURE & " - "
End Sub



Private Sub IntializeStartPoint()
   SetStartPoint Point3dFromXYZ(0, 0, 0)
End Sub



Private Sub InitializeTransientContainers(ByVal CourseDrawMode As Long)
'INITIALIZE CONTAINERS FOR TEMPORARY GRAPHICS AND CELL
   Select Case CourseDrawMode
      Case Mode_Draw_Transient_Hilite_Sel
         CreateNormalTransientContainer
         CreateHiliteTransientContainer
      Case Mode_Draw_Transient_Blank_Sel
         CreateHiliteTransientContainer
      Case Mode_Draw_Transient_Hilite_All
         CreateHiliteTransientContainer
      Case Mode_Draw_Report
         CreateNormalTransientContainer
         CreateHiliteTransientContainer
      Case Mode_Draw_Permanent
         CreateHiliteTransientContainer
'INITIALIZE CELL ARRAY IF NEEDED
         If AllCoursesCheckBox.value And CreateAsCellCheckBox.value Then
            ResetCellArray
         End If
'INITIALIZE COMPLEX ARRAY IF NEEDED
         If AllCoursesCheckBox.value And ComplexCheckBox.value Then
            ResetComplexArray
         End If
      Case Mode_Draw_Export
         CreateNormalTransientContainer
         CreateHiliteTransientContainer
   End Select
End Sub



Private Function LoadAndExport(ByVal filename As String) As Boolean
   LoadAndExport = False
   InitializeForm
   ClearTextBoxes
   If LoadLotFile(filename) Then
      Dim XSplit As Variant
      XSplit = Split(filename, "\")
      FrmPlotLot.Caption = COMMAND_NAME_LOT_CLOSURE & " - " & XSplit(UBound(XSplit))
      DrawTheCourses GetStartPoint(), Mode_Draw_Export
      LoadAndExport = True
   End If
End Function



Private Function LoadLotFile(filename As String) As Boolean
'LOAD LOT FILE INTO USERFORM, RETURNS TRUE IF SUCCESSFUL

'INITIALIZE RETURN VALUE
   LoadLotFile = True
   
'JUMP ON ERROR
   On Error GoTo errhnd

'OPEN FILE
   Dim FFILE As Long
   FFILE = FreeFile
   Open filename For Input As #FFILE

'READ FILE ONE LINE AT A TIME
   Dim LineNum As Long
   LineNum = 1
   Dim TextLine As String
   Dim OpenFileErrors As Long
   OpenFileErrors = 0
   Do While EOF(FFILE) = False
      Line Input #FFILE, TextLine
      Select Case LineNum
         Case 1 'HEADER
            If StrComp(TextLine, Lot_Closure_File_Header, vbBinaryCompare) <> 0 Then
               LoadLotFile = False
               Exit Do
            End If
         
         Case 2 'FORMAT NUMBER
            If Not IsNumeric(TextLine) Then
               LoadLotFile = False
               Exit Do
            End If
            Dim FormatNumber As Double
            FormatNumber = CDbl(TextLine)
            If FormatNumber > Lot_Closure_Format_Number Then
               LoadLotFile = False
               MsgBox "Format version too high."
               Exit Do
            End If
            
         Case Else 'ALL OTHER RECORDS
            Dim RecordTypeString As String
            Dim RecordDataString As String
            If SplitRecord(TextLine, RecordTypeString, RecordDataString) Then
               LoadLotFile = DistributeRecord(RecordTypeString, RecordDataString)
            Else
               LoadLotFile = False
            End If
        
      End Select
      LineNum = LineNum + 1
      If Not LoadLotFile Then
         Exit Do
      End If
   Loop
   
'CLOSE FILE
   Close #FFILE
      
'JUMP PAST ERROR CODE
   Exit Function

'ERROR HANDLING
errhnd:
   LoadLotFile = False
   ErrorMess Err.Number
   Err.Clear
End Function



Public Sub RenumberCourses()
'RENUMBERS THE FIRST COLUMN IN THE COURSES LISTBOX
   Dim lastIndex As Long
   lastIndex = CoursesListBox.ListCount - 1
   If CoursesListBox.ListCount > 0 Then
      Dim index As Long
      For index = 0 To lastIndex
         CoursesListBox.List(index, Lot_Closure_Column_Leg_Num) = FormatNumber(index + 1, 0)
      Next index
   End If
End Sub



Private Sub SetTheSelect()
'IF THERE ARE ITEMS IN THE LISTBOX, THEN SELECT FIRST ITEM
   If CoursesListBox.ListCount > 0 Then
      CoursesListBox.listIndex = -1
      CoursesListBox.listIndex = 0
   End If
End Sub



Public Sub UpdatePlotLotOnFileOpen()
   If IsFileLoaded() And Not GetInsertingFlag Then
      CalcAndDrawCourses
   End If
End Sub



'*************************************************************************************************************
'*************************************************MATH********************************************************
Private Function ArcLength(ByVal deltaInDegrees As Double, ByVal theRadius As Double) As Double
'CALCULATES THE ARC LENGTH
   If theRadius > 0# And deltaInDegrees > 0# Then
      ArcLength = (deltaInDegrees / 360#) * (2# * theRadius) * Pi
   Else
      ArcLength = 0#
   End If
End Function



Private Function AreaOfTriangle(ByVal a As Double, ByVal b As Double, ByVal c As Double) As Double
'CALCULATES AREA OF SIDE SIDE SIDE TRIANGLE
   If a + b <= c Or b + c <= a Or c + a <= b Then
      AreaOfTriangle = 0
      Exit Function
   End If
   If a = 0# Or b = 0# Or c = 0# Then
      AreaOfTriangle = 0#
      Exit Function
   End If
   Dim s As Double
   s = (a + b + c) / 2#
   AreaOfTriangle = Sqr(s * (s - a) * (s - b) * (s - c))
End Function



Private Function Calc_a(ByVal radius As Double, ByVal chord As Double) As Double
'CALCULATES MISSING SIDE OF TRIANGLE FOR RADIUS POINT, DISTANCE FROM MIDDLE OF CHORD TO RADIUS POINT
'ASSUMES VALID CURVE, SQUARE ROOT OF NEGATIVE NUMBER WILL CAUSE CRASH
   Calc_a = Sqr(Abs(radius ^ 2# - (chord / 2#) ^ 2#))
End Function



Private Function chordAz(tangentInDeg As Double, DeltaDeg As Double, lefthandCurve As Boolean) As Double
      Dim halfDelta As Double
      halfDelta = DeltaDeg / 2#
      If lefthandCurve Then
         halfDelta = -halfDelta
      End If
      chordAz = tangentInDeg + halfDelta
      MakeSure360 chordAz
End Function



Private Function SegmentArea(ByVal deltaInDegrees As Double, _
                             ByVal theChord As Double, _
                             ByVal theRadius As Double, _
                             ByVal lefthandCurve As Boolean) As Double
'CALCULATES SEGMENT AREA
'RETURNS NEGATIVE VALUE FOR LEFT HAND CURVE
   Dim TheSegmentArea As Double
   Dim TheTriangleArea As Double
   TheTriangleArea = AreaOfTriangle(theRadius, theRadius, theChord)
   Dim AreaOfCircle As Double
   AreaOfCircle = Pi * theRadius * theRadius
   TheSegmentArea = AreaOfCircle * (deltaInDegrees / 360#) - TheTriangleArea
   If lefthandCurve Then
      TheSegmentArea = -TheSegmentArea
   End If
   SegmentArea = TheSegmentArea
End Function



'*************************************************************************************************************
'**************************************************TEMPLATES**************************************************
Public Function CreateAreaTextTemplate() As TextElement
   Dim ScaledCharSize As Double
   ScaledCharSize = GetCharSize() * Abs(CDbl(AreaFontScaleTextBox.text))
   Set CreateAreaTextTemplate = CreateTextTemplate(SECTION_LOT_CLOSURE, _
                                                   AreaFontComboBox, _
                                                   KEY_AREA_FONT, _
                                                   AreaLevelComboBox, _
                                                   KEY_AREA_LEVEL, _
                                                   AreaWeightComboBox, _
                                                   AreaColorComboBox, _
                                                   AreaStyleComboBox, _
                                                   KEY_AREA_STYLE, _
                                                   ScaledCharSize, _
                                                   msdTextJustificationCenterCenter)
   
End Function



Private Function CreateBoundaryTemplate() As LineElement
   Set CreateBoundaryTemplate = CreateLineTemplate(SECTION_LOT_CLOSURE, _
                                                   BoundaryLevelComboBox, _
                                                   KEY_BOUNDARY_LEVEL, _
                                                   BoundaryWeightComboBox, _
                                                   BoundaryColorComboBox, _
                                                   BoundaryStyleComboBox, _
                                                   KEY_BOUNDARY_STYLE)
End Function



Private Function CreateChordTemplate() As LineElement
   Set CreateChordTemplate = CreateLineTemplate(SECTION_LOT_CLOSURE, _
                                                ChordLevelComboBox, _
                                                KEY_CHORD_LEVEL, _
                                                ChordWeightComboBox, _
                                                ChordColorComboBox, _
                                                ChordStyleComboBox, _
                                                KEY_CHORD_STYLE)
End Function



Public Function CreateDescriptionTextTemplate() As TextElement
   Dim ScaledCharSize As Double
   ScaledCharSize = GetCharSize() * Abs(CDbl(DescriptionFontScaleTextBox.text))
   Set CreateDescriptionTextTemplate = CreateTextTemplate(SECTION_LOT_CLOSURE, _
                                                          DescriptionFontComboBox, _
                                                          KEY_DESCRIPTION_FONT, _
                                                          DescriptionLevelComboBox, _
                                                          KEY_DESCRIPTION_LEVEL, _
                                                          DescriptionWeightComboBox, _
                                                          DescriptionColorComboBox, _
                                                          DescriptionStyleComboBox, _
                                                          KEY_DESCRIPTION_STYLE, _
                                                          ScaledCharSize, _
                                                          msdTextJustificationCenterCenter)
      
End Function



Private Function CreateRadialsTemplate() As LineElement
   Set CreateRadialsTemplate = CreateLineTemplate(SECTION_LOT_CLOSURE, _
                                                  RadialsLevelComboBox, _
                                                  KEY_RADIALS_LEVEL, _
                                                  RadialsWeightComboBox, _
                                                  RadialsColorComboBox, _
                                                  RadialsStyleComboBox, _
                                                  KEY_RADIALS_STYLE)
End Function



'*************************************************************************************************************
'**********************************************USERFORM EVENTS************************************************
Private Sub UserForm_Initialize()
   Dim Options As String

'INITIALIZE ANGLE STYLE FOR ENTRIES IN LISTBOX
   PlotLotFileCode.PlotLotEntryAngleStyle = STYLE_ANGLE_SPACE Or STYLE_ANGLE_LEAD
   
'WAIT FOR FILE OPEN AND CLOSE EVENTS
   Set openCloseHandler = New ClsOpenClosePlotLot

'SET SIZE OF COURSES LISTBOX COLUMNS
   CoursesListBox.ColumnCount = 7
   Dim ColumnWidthString As String
   ColumnWidthString = FormatNumber(0.3 * Column_Width_Multiplier, 2) & " in; " & _
                       FormatNumber(0.45 * Column_Width_Multiplier, 2) & " in; " & _
                       FormatNumber(1.4 * Column_Width_Multiplier, 2) & " in; " & _
                       FormatNumber(1.4 * Column_Width_Multiplier, 2) & " in; " & _
                       FormatNumber(1.4 * Column_Width_Multiplier, 2) & " in; " & _
                       FormatNumber(0.6 * Column_Width_Multiplier, 2) & " in; " & _
                       FormatNumber(0.5 * Column_Width_Multiplier, 2) & " in"
   CoursesListBox.ColumnWidths = ColumnWidthString

'HIDE BUTTONS AND LABEL FOR BOUNDARY REPORT
   OnOffBoundaryReport False

'INITIALIZE POINT NAME
   PointnameTextBox.MaxLength = MAX_LEN_POINT_NAME
   PointnameTextBox.text = GetSetting(APP_NAME, SECTION_LOT_CLOSURE, KEY_POINTNAME, "1")

'INITIALIZE USE LOT DESCRIPTION CHECKBOX
   InitializeCheckBox UseLotDescCheckBox, SECTION_LOT_CLOSURE, KEY_OPTION_USE_LOT_DESC
   ExportDescriptionState

'INITIALIZE DESCRIPTION TEXTBOX
   CoordDescTextBox.MaxLength = MAX_LEN_POINT_DESC
   CoordDescTextBox.text = GetSetting(APP_NAME, SECTION_LOT_CLOSURE, KEY_POINT_DESC, "")

'INITIALIZE CHORD PRECISION COMBOBOX
   ChordPrecisionComboBox.AddItem "2"
   ChordPrecisionComboBox.AddItem "3"
   ChordPrecisionComboBox.AddItem "4"
   ChordPrecisionComboBox.text = GetSetting(APP_NAME, SECTION_LOT_CLOSURE, KEY_PRECISION_CHORD, "2")

'INITIALIZE REPORT PROJECT NAME CHECKBOX
   InitializeCheckBox ReportProjectCheckBox, SECTION_LOT_CLOSURE, KEY_OPTION_REPORT_PROJ_NAME

'INITIALIZE REPORT PROJECT NUMBER CHECKBOX
   InitializeCheckBox ProjectNumCheckBox, SECTION_LOT_CLOSURE, KEY_OPTION_REPORT_PROJ_NUM

'INITIALIZE REPORT DATE CHECKBOX
   InitializeCheckBox ReportDateCheckBox, SECTION_LOT_CLOSURE, KEY_OPTION_REPORT_DATE

'INITIALIZE DRAWING DESCRIPTION CHECKBOX
   InitializeCheckBox DGNDescriptionCheckBox, SECTION_LOT_CLOSURE, KEY_OPTION_DGN_DESCRIPTION

'INITIALIZE REPORT DESCRIPTION CHECKBOX
   InitializeCheckBox ReportDescriptionCheckBox, SECTION_LOT_CLOSURE, KEY_OPTION_REPORT_DESCRIPTION

'INITIALIZE REPORT AZIMUTH CHECKBOX
   InitializeCheckBox ReportAzimuthCheckBox, SECTION_LOT_CLOSURE, KEY_OPTION_REPORT_AZIMUTH

'INITIALIZE REPORT COORDINATE CHECKBOX
   InitializeCheckBox ReportCoordinateCheckBox, SECTION_LOT_CLOSURE, KEY_OPTION_REPORT_COORDINATE

'INITIALIZE NOTE CHECKBOX
   InitializeCheckBox NoteCheckBox, SECTION_LOT_CLOSURE, KEY_OPTION_REPORT_NOTE

'INITIALIZE REPORT FILENAME CHECKBOX
   InitializeCheckBox ReportFilenameCheckBox, SECTION_LOT_CLOSURE, KEY_OPTION_REPORT_FILENAME
   IncludePathState

'INITIALIZE INCLUDE PATH CHECKBOX
   InitializeCheckBox IncludePathCheckBox, SECTION_LOT_CLOSURE, KEY_OPTION_REPORT_PATH, False

'INITIALIZE DGN RADIAL LINES CHECK BOX
   InitializeCheckBox DGNRadialLinesCheckBox, SECTION_LOT_CLOSURE, KEY_OPTION_DGN_RADIALS, True

'INITIALIZE DGN CHORD CHECKBOX
   InitializeCheckBox DGNChordCheckBox, SECTION_LOT_CLOSURE, KEY_OPTION_DGN_CHORD, False

'INITIALIZE DGN AREA CHECKBOX
   InitializeCheckBox DGNAreaCheckBox, SECTION_LOT_CLOSURE, KEY_OPTION_DGN_AREA, False

'INITIALIZE DGN AREA OPTIONS
   Options = GetSetting(APP_NAME, SECTION_LOT_CLOSURE, KEY_OPTION_DGN_AREA_TYPE, OPTION_FEET)
   Select Case Options
      Case OPTION_FEET
         OptionFeet.value = True
      Case OPTION_ACRES
         OptionAcres.value = True
      Case Else
         OptionAcresAndFeet.value = True
   End Select
   AreaChoicesState
   
'INITIALIZE COORDINATE FILENAME
   Dim strFName As String
   strFName = GetSetting(APP_NAME, SECTION_LOT_CLOSURE, KEY_FILENAME_COORDINATE, "")
   strFName = Trim(strFName)
   If strFName = "" Then
      FilenameLabel.Caption = ""
   Else
      Dim XSplit As Variant
      XSplit = Split(strFName, "\")
      FilenameLabel.Caption = XSplit(UBound(XSplit))
   End If



'INITIALIZE TRANSFORMATION ANGLE CHECKBOX
   InitializeCheckBox TransformAngleCheckBox, SECTION_LOT_CLOSURE, KEY_OPTION_TRANSFORM_ANGLE

'INITIALIZE TRANSFORMATION ANGLE TEXTBOX
   TransAngleTextBox.text = GetSetting(APP_NAME, SECTION_LOT_CLOSURE, KEY_TRANSFORMATION_ANGLE, "0.00")
   TransAngleTextBox_AfterUpdate
   TransAngleTextBox.MaxLength = MAX_LEN_DIR_STRING

'INITIALIZE TRANSFORMATION SCALE CHECKBOX
   InitializeCheckBox TransformScaleCheckBox, SECTION_LOT_CLOSURE, KEY_OPTION_TRANSFORM_SCALE, False

'INITIALIZE TRANSFORMATION SCALE TEXTBOX
   TransformScaleTextBox.text = GetSetting(APP_NAME, SECTION_LOT_CLOSURE, KEY_TRANSFORMATION_SCALE, "1")
   TransformScaleTextBox.MaxLength = MAX_LEN_TRANSFORM_SCALE_STRING

'INITIALIZE TRANSFORMATION SCALE DISTANCE PRECISION COMBOBOX
   DisPrecComboBox.AddItem "2"
   DisPrecComboBox.AddItem "3"
   DisPrecComboBox.AddItem "4"
   DisPrecComboBox.text = GetSetting(APP_NAME, SECTION_LOT_CLOSURE, KEY_PRECISION_DIST, "2")


'INITIALIZE ALL COURSES CHECKBOX
   InitializeCheckBox AllCoursesCheckBox, SECTION_LOT_CLOSURE, KEY_OPTION_ALL_COURSES, False

'INITIALIZE CREATE AS CELL CHECKBOX
   InitializeCheckBox CreateAsCellCheckBox, SECTION_LOT_CLOSURE, KEY_OPTION_CREATE_CELL, False

'INITIALIZE CREATE AS CELL CHECKBOX
   InitializeCheckBox ComplexCheckBox, SECTION_LOT_CLOSURE, KEY_OPTION_COMPLEX_CHAIN, False



'POPULATE BOUNDARY SETTINGS COMBOBOXES
   PopulateBoundaryLevelBox
   PopulateBoundaryColorBox
   PopulateBoundaryStyleBox
   PopulateBoundaryWeightBox

'POPULATE CHORD SETTINGS COMBOBOXES
   PopulateChordLevelBox
   PopulateChordColorBox
   PopulateChordStyleBox
   PopulateChordWeightBox

'POPULATE RADIAL LINES SETTINGS COMBOBOXES
   PopulateRadialsLevelBox
   PopulateRadialsColorBox
   PopulateRadialsStyleBox
   PopulateRadialsWeightBox

'POPULATE DESCRIPTION SETTINGS COMBO BOXES
   PopulateDescriptionLevelComboBox
   PopulateDescriptionColorComboBox
   PopulateDescriptionStyleComboBox
   PopulateDescriptionWeightComboBox
   PopulateDescriptionFontComboBox
   DescriptionFontScaleTextBox.MaxLength = MAX_LEN_FONT_SCALE_STRING
   DescriptionFontScaleTextBox.text = GetSetting(APP_NAME, SECTION_LOT_CLOSURE, KEY_DESCRIPTION_FONT_SCALE, "1")

'POPULATE AREA SETTINGS COMBO BOXES
   PopulateAreaLevelComboBox
   PopulateAreaColorComboBox
   PopulateAreaStyleComboBox
   PopulateAreaWeightComboBox
   PopulateAreaFontComboBox
   AreaFontScaleTextBox.MaxLength = MAX_LEN_FONT_SCALE_STRING
   AreaFontScaleTextBox.text = GetSetting(APP_NAME, SECTION_LOT_CLOSURE, KEY_AREA_FONT_SCALE, "1")

'INITIALIZE CLEAR TEXT BOXES CHECK BOX
   InitializeCheckBox ClearTexBoxesCheckBox, SECTION_LOT_CLOSURE, KEY_OPTION_CLEAR_TEXT, False
   



'INITIALIZE FOR NO FILE LOADED
   UnsetFileIsLoaded
   EntryOnOff False
   OutputButtonsStates
   TransformationStates
   EditDelButtonsStates
   AddDGNButtonStates
   ExportStates
   CreateCellStates
   
'MOVE INTO LAST POSITION
   If GetSetting(APP_NAME, SECTION_LOT_CLOSURE, KEY_START_TOP, "") = "" Then
      Me.StartUpPosition = 1
   Else
      Me.StartUpPosition = 0
      Me.Top = CDbl(GetSetting(APP_NAME, SECTION_LOT_CLOSURE, KEY_START_TOP, WINDOW_DEFAULT_TOP))
      Me.Left = CDbl(GetSetting(APP_NAME, SECTION_LOT_CLOSURE, KEY_START_LEFT, WINDOW_DEFAULT_LEFT))
   End If
   
'INITIALIZE THE FORM, RESET VALUES
   InitializeForm
   ClearInsertingFlag

'MAKE SURE CAPTION IS CORRECT
   Me.Caption = COMMAND_NAME_LOT_CLOSURE

'INITIALIZE DIALOGBOX SIZE
   Options = GetSetting(APP_NAME, SECTION_LOT_CLOSURE, KEY_BIG, OPTION_FALSE)
   If Options = OPTION_TRUE Then
      dialogBig True
   Else
      dialogBig False
   End If
   
'BRING FILE PAGE TO FOREGROUND
   Me.MultiPage1.value = 0
End Sub



Private Sub UserForm_QueryClose(Cancel As Integer, CloseMode As Integer)
'SAVE USERFORM POSITION
   SaveSetting APP_NAME, SECTION_LOT_CLOSURE, KEY_START_TOP, FormatNumber(Me.Top, 0)
   SaveSetting APP_NAME, SECTION_LOT_CLOSURE, KEY_START_LEFT, FormatNumber(Me.Left, 0)
End Sub



'*************************************************************************************************************

Attribute VB_Name = "FrmSample"
Attribute VB_Base = "0{8EACE8D2-2936-4A63-993C-3F125F648C4E}{AC96AFBC-F7B7-44FE-A274-41E9F86696AC}"
Attribute VB_GlobalNameSpace = False
Attribute VB_Creatable = False
Attribute VB_PredeclaredId = True
Attribute VB_Exposed = False
Attribute VB_TemplateDerived = False
Attribute VB_Customizable = False
















'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit
'SAMPLE DIALOG BOX TO REMIND ME HOW TO DO USER INTERFACE

Private Const TEXTBOX_ELEVATION     As Integer = 1
Private Const TEXTBOX_POINT_DESC    As Integer = 2

Private textBoxNumber As Integer

'DIRECTION FIELD
Private Sub DirectionTextBox_AfterUpdate()
   SaveDirEntry DirectionTextBox, SECTION_SAMPLE, KEY_DIRECTION, STYLE_ANGLE_SPACE Or STYLE_ANGLE_LEAD
End Sub

Private Sub DirectionTextBox_Enter()
   SelectAllText DirectionTextBox
End Sub





'+180 BUTTON
Private Sub Plus180Button_Click()
   Plus180 DirectionTextBox
   DirectionTextBox_AfterUpdate
End Sub









'DELTA FIELD
Private Sub DeltaTextBox_AfterUpdate()
   SaveDeltaEntry DeltaTextBox, SECTION_SAMPLE, KEY_DELTA, STYLE_ANGLE_SPACE Or STYLE_ANGLE_LEAD, 4
   Dim degPart As Long
   Dim minPart As Long
   Dim secPart As Double
   Dim prec    As Long
   Dim deltaOver2 As Double
   If halfDelta(DeltaTextBox.text, degPart, minPart, secPart, prec, deltaOver2) Then
      Label3.Caption = DirString(degPart, minPart, secPart, prec, DIR_TYPE_AZIMUTH, STYLE_ANGLE_LEAD Or STYLE_ANGLE_SPACE)
   End If
End Sub

Private Sub DeltaTextBox_Enter()
   SelectAllText DeltaTextBox
End Sub







'STATION FIELD
Private Sub StationTextBox_AfterUpdate()
   SaveStationEntry StationTextBox, SECTION_SAMPLE, KEY_STATION, 0, 2
End Sub

Private Sub StationTextBox_Enter()
   SelectAllText StationTextBox
End Sub





'NORTHING FIELD
Private Sub NorthingTextbox_AfterUpdate()
   SaveNorthingEntry NorthingTextBox, SECTION_SAMPLE, KEY_NORTHING, 4
End Sub

Private Sub NorthingTextbox_Enter()
   SelectAllText NorthingTextBox
End Sub



'EASTING FIELD
Private Sub EastingTextbox_AfterUpdate()
   SaveEastingEntry EastingTextBox, SECTION_SAMPLE, KEY_EASTING, 4
End Sub

Private Sub EastingTextbox_Enter()
   SelectAllText EastingTextBox
End Sub






'DISTANCE FIELD
Private Sub DistanceTextBox_AfterUpdate()
   SaveNonnegativeEntry DistanceTextBox, SECTION_SAMPLE, KEY_DISTANCE, MAX_DISTANCE, MAX_PRECISION_DISTANCE, True, 100#, 2
End Sub

Private Sub DistanceTextBox_Enter()
   SelectAllText DistanceTextBox
End Sub





'POINTNAME FIELD
Private Sub PointNameTextBox_AfterUpdate()
   SavePointNameEntry PointnameTextBox, SECTION_SAMPLE, KEY_POINTNAME
End Sub

Private Sub PointNameTextBox_Enter()
   SelectAllText PointnameTextBox
End Sub




'INCREMENT BUTTON
Private Sub incrementButton_Click()
   PointnameTextBox.text = IncPointName(PointnameTextBox.text)
   PointNameTextBox_AfterUpdate
End Sub





'ELEVATION FIELD
Private Sub ElevationTextBox_AfterUpdate()
   SaveElevationEntry ElevationTextBox, SECTION_SAMPLE, KEY_ELEVATION
End Sub

Private Sub ElevationTextBox_Enter()
   SelectAllText ElevationTextBox
End Sub







'OFFSET FIELD
Private Sub OffsetTextBox_AfterUpdate()
   SaveOffsetEntry OffsetTextBox, LeftOptionButton, RightOptionButton, SECTION_SAMPLE, KEY_OFFSET, 1000, 0
End Sub

Private Sub OffsetTextBox_Enter()
   SelectAllText OffsetTextBox
End Sub



'LEFT OPTION BUTTON
Private Sub LeftOptionButton_Click()
   SaveSetting APP_NAME, SECTION_SAMPLE, KEY_SIDE, OPTION_LEFT
End Sub



'RIGHT OPTION BUTTON
Private Sub RightOptionButton_Click()
   SaveSetting APP_NAME, SECTION_SAMPLE, KEY_SIDE, OPTION_RIGHT
End Sub




'POINT DESC FIELD
Private Sub PointDescTextBox_AfterUpdate()
   SavePointDescEntry PointDescTextBox, SECTION_SAMPLE, KEY_POINT_DESC
End Sub

Private Sub PointDescTextBox_Enter()
   SelectAllText PointDescTextBox
End Sub




'RADIUS FIELD
Private Sub RadiusTextBox_AfterUpdate()
   SaveNonnegativeEntry RadiusTextBox, SECTION_SAMPLE, KEY_RADIUS, MAX_RADIUS, MAX_PRECISION_RADIUS, False, 100.2
End Sub

Private Sub RadiusTextBox_Enter()
   SelectAllText RadiusTextBox
End Sub



'+/- ANGLE FIELD
Private Sub PlusMinusAngleTextBox_AfterUpdate()
   SavePlusMinusAngleEntry PlusMinusAngleTextBox, SECTION_SAMPLE, KEY_PLUS_MINUS_ANGLE, STYLE_ANGLE_LEAD Or STYLE_ANGLE_SPACE, 180#
End Sub

Private Sub PlusMinusAngleTextBox_Enter()
   SelectAllText RadiusTextBox
End Sub




Private Sub UserForm_Initialize()
'SET TITLE
   Me.Caption = COMMAND_NAME_SAMPLE

'MOVE INTO LAST POSITION
   If GetSetting(APP_NAME, SECTION_SAMPLE, KEY_START_TOP, "") = "" Then
      Me.StartUpPosition = 1
   Else
      Me.StartUpPosition = 0
      Me.Top = CDbl(GetSetting(APP_NAME, SECTION_SAMPLE, KEY_START_TOP, WINDOW_DEFAULT_TOP))
      Me.Left = CDbl(GetSetting(APP_NAME, SECTION_SAMPLE, KEY_START_LEFT, WINDOW_DEFAULT_LEFT))
   End If
   
'DIRECTION FIELD
   LoadDirEntry DirectionTextBox, SECTION_SAMPLE, KEY_DIRECTION
   DirectionTextBox.MaxLength = MAX_LEN_DIR_STRING
'DELTA FIELD
   LoadDirEntry DeltaTextBox, SECTION_SAMPLE, KEY_DELTA
   DeltaTextBox.MaxLength = MAX_LEN_DIR_STRING
'STATION FIELD
   LoadStaEntry StationTextBox, SECTION_SAMPLE, KEY_STATION, 0
   StationTextBox.MaxLength = MAX_LEN_STA_STRING
'NORTHING FIELD
   LoadNorthingEntry NorthingTextBox, SECTION_SAMPLE, KEY_NORTHING, 4, True
   NorthingTextBox.MaxLength = MAX_LEN_COORDINATE_STRING
'EASTING FIELD
   LoadEastingEntry EastingTextBox, SECTION_SAMPLE, KEY_EASTING, 4, True
   EastingTextBox.MaxLength = MAX_LEN_COORDINATE_STRING
'DISTANCE FIELD
   LoadNonnegativeEntry DistanceTextBox, SECTION_SAMPLE, KEY_DISTANCE, 100#
   DistanceTextBox.MaxLength = MAX_LEN_DIST_STRING
'POINTNAME FIELD
   LoadPointName PointnameTextBox, SECTION_SAMPLE, KEY_POINTNAME
   PointnameTextBox.MaxLength = MAX_LEN_POINT_NAME
'ELEVATION FIELD
   LoadElevationEntry ElevationTextBox, SECTION_SAMPLE, KEY_ELEVATION
   ElevationTextBox.MaxLength = MAX_LEN_ELEV_STRING
'OFFSET FIELD
   LoadNonnegativeEntry OffsetTextBox, SECTION_SAMPLE, KEY_OFFSET, 0
   OffsetTextBox.MaxLength = 6 'max length depends on specific case
'SIDE OPTION BUTTONS
   Dim opt As String
   opt = GetSetting(APP_NAME, SECTION_SAMPLE, KEY_SIDE, OPTION_LEFT)
   If opt = OPTION_LEFT Then
      LeftOptionButton.value = True
   Else
      RightOptionButton.value = True
   End If
'POINT DESC FIELD
   LoadPointDescEntry PointDescTextBox, SECTION_SAMPLE, KEY_POINT_DESC
   PointDescTextBox.MaxLength = MAX_LEN_POINT_DESC
'RADIUS FIELD
   LoadRadiusEntry RadiusTextBox, SECTION_SAMPLE, KEY_RADIUS
   RadiusTextBox.MaxLength = MAX_LEN_RADIUS_STRING
'+/- ANGLE FIELD
   LoadPlusMinusEntry PlusMinusAngleTextBox, SECTION_SAMPLE, KEY_PLUS_MINUS_ANGLE, STYLE_ANGLE_LEAD Or STYLE_ANGLE_SPACE, 4
   PlusMinusAngleTextBox.MaxLength = MAX_LEN_DIR_STRING

'TEXT ATTRIBUTES
'LEVEL COMBOBOX
   PopulateLevelBox LevelComboBox, SECTION_SAMPLE, KEY_LEVEL
'COLOR COMBOBOX
   PopulateColorBox ColorComboBox, SECTION_SAMPLE, KEY_COLOR
'STYLE COMBOBOX
   PopulateLinestyleBox StyleComboBox, SECTION_SAMPLE, KEY_STYLE
'WEIGHT COMBOBOX
   PopulateWeightBox WeightComboBox, SECTION_SAMPLE, KEY_WEIGHT
'FONT COMBOBOX
   PopulateFontBox FontComboBox, SECTION_SAMPLE, KEY_FONT
   
'LINE ATTRIBUTES
'LEVEL COMBOBOX
   PopulateLevelBox LevelComboBox2, SECTION_SAMPLE, KEY_LEVEL2
'COLOR COMBOBOX
   PopulateColorBox ColorComboBox2, SECTION_SAMPLE, KEY_COLOR2
'STYLE COMBOBOX
   PopulateLinestyleBox StyleComboBox2, SECTION_SAMPLE, KEY_STYLE2
'WEIGHT COMBOBOX
   PopulateWeightBox WeightComboBox2, SECTION_SAMPLE, KEY_WEIGHT2


'USE O/S CHECKBOX
   InitializeCheckBox UseOffsetCheckBox, SECTION_SAMPLE, KEY_CHECKBOX

'SET CONTROL STATES
   ControlStates
End Sub




'INTERFACE FOR PICKING TEXT ROUTINE
Public Sub EnterText(ByVal Entry As String)
   Select Case textBoxNumber
      Case TEXTBOX_ELEVATION
         Dim floatString As String
         If StrToFloatStr(Entry, floatString) Then
            ElevationTextBox.text = floatString
            ElevationTextBox_AfterUpdate
         End If
      Case TEXTBOX_POINT_DESC
         If Len(Entry) > MAX_LEN_POINT_DESC Then
            Entry = Mid(Entry, 1, MAX_LEN_POINT_DESC)
         End If
         PointDescTextBox.text = Entry
   End Select
End Sub


'PICK ELEVATION FROM TEXT BUTTON
Private Sub PickElevTextButton_Click()
   textBoxNumber = TEXTBOX_ELEVATION
   Dim myTool As New LocateText
   Set myTool.hostForm = Me
   CommandState.StartLocate myTool
End Sub

'PICK DECRIPTION FROM TEXT BUTTON
Private Sub PickDescTextButton_Click()
   textBoxNumber = TEXTBOX_POINT_DESC
   Dim myTool As New LocateText
   Set myTool.hostForm = Me
   CommandState.StartLocate myTool
End Sub






'TEXT ATTRIBUTES
'COLOR COMBOBOX
Private Sub ColorComboBox_AfterUpdate()
   ColorBoxOnUpdate ColorComboBox, SECTION_SAMPLE, KEY_COLOR
End Sub

'COLOR PICKER
Private Sub ChooseColorButton_Click()
   Dim MyColor As String
   If ChooseMyTableColor(MyColor) Then
      ColorComboBox.text = MyColor
      ColorComboBox_AfterUpdate
   End If
End Sub



'LEVEL COMBOBOX
Private Sub LevelComboBox_AfterUpdate()
   If Not LevelBoxOnUpdate(LevelComboBox, SECTION_SAMPLE, KEY_LEVEL) Then
      PopulateLevelBox LevelComboBox, SECTION_SAMPLE, KEY_LEVEL
      Beep
   End If
End Sub

'STYLE COMBOBOX
Private Sub StyleComboBox_AfterUpdate()
   If Not LineStyleBoxOnUpdate(StyleComboBox, SECTION_SAMPLE, KEY_STYLE) Then
      PopulateLinestyleBox StyleComboBox, SECTION_SAMPLE, KEY_STYLE
      Beep
   End If
End Sub

'WEIGHT COMBOBOX
Private Sub WeightComboBox_AfterUpdate()
   WeightBoxOnUpdate WeightComboBox, SECTION_SAMPLE, KEY_WEIGHT
End Sub

'FONT COMBOBOX
Private Sub FontComboBox_AfterUpdate()
   If Not FontBoxOnUpdate(FontComboBox, SECTION_SAMPLE, KEY_FONT) Then
      PopulateFontBox FontComboBox, SECTION_SAMPLE, KEY_FONT
      Beep
   End If
End Sub





'PLACE TEXT BUTTON
Private Sub PlaceTextButton_Click()
   CommandState.StartPrimitive New PlaceTextPrimitive
End Sub


Public Function GetTextTemp() As TextElement
'TO INTERFACE WITH TEXT PLACING ROUTINE
   Set GetTextTemp = CreateTextTemplate(SECTION_SAMPLE, _
                                        FontComboBox, _
                                        KEY_FONT, _
                                        LevelComboBox, _
                                        KEY_LEVEL, _
                                        WeightComboBox, _
                                        ColorComboBox, _
                                        StyleComboBox, _
                                        KEY_STYLE, , _
                                        msdTextJustificationLeftCenter)
End Function








'LINE ATTRIBUTES
'COLOR COMBOBOX
Private Sub ColorComboBox2_AfterUpdate()
   ColorBoxOnUpdate ColorComboBox2, SECTION_SAMPLE, KEY_COLOR2
End Sub

'COLOR PICKER
Private Sub ChooseColorButton2_Click()
   Dim MyColor As String
   If ChooseMyTableColor(MyColor) Then
      ColorComboBox2.text = MyColor
      ColorComboBox2_AfterUpdate
   End If
End Sub

'LEVEL COMBOBOX
Private Sub LevelComboBox2_AfterUpdate()
   If Not LevelBoxOnUpdate(LevelComboBox2, SECTION_SAMPLE, KEY_LEVEL2) Then
      PopulateLevelBox LevelComboBox2, SECTION_SAMPLE, KEY_LEVEL2
      Beep
   End If
End Sub


'STYLE COMBOBOX
Private Sub StyleComboBox2_AfterUpdate()
   If Not LineStyleBoxOnUpdate(StyleComboBox2, SECTION_SAMPLE, KEY_STYLE2) Then
      PopulateLinestyleBox StyleComboBox2, SECTION_SAMPLE, KEY_STYLE2
      Beep
   End If
End Sub

'WEIGHT COMBOBOX
Private Sub WeightComboBox2_AfterUpdate()
   WeightBoxOnUpdate WeightComboBox2, SECTION_SAMPLE, KEY_WEIGHT2
End Sub





'PLACE LINE BUTTON
Private Sub PlaceLineButton_Click()
   CommandState.StartPrimitive New PlaceLinePrimitive
End Sub

Public Function GetLineTemp() As LineElement
'TO INTERFACE WITH LINE PLACING ROUTINE
   Set GetLineTemp = CreateLineTemplate(SECTION_SAMPLE, _
                                        LevelComboBox2, _
                                        KEY_LEVEL2, _
                                        WeightComboBox2, _
                                        ColorComboBox2, _
                                        StyleComboBox2, _
                                        KEY_STYLE2)
End Function


'USE O/S CHECKBOX
Private Sub UseOffsetCheckbox_Click()
   ControlStates
   SaveCheckBoxSetting UseOffsetCheckBox, SECTION_SAMPLE, KEY_CHECKBOX
End Sub



'SETTINGS BUTTON
Private Sub SettingsButton_Click()
   Setting
End Sub






Private Sub UserForm_QueryClose(Cancel As Integer, CloseMode As Integer)
'SAVE USERFORM POSITION
   SaveSetting APP_NAME, SECTION_SAMPLE, KEY_START_TOP, FormatNumber(Me.Top, 2)
   SaveSetting APP_NAME, SECTION_SAMPLE, KEY_START_LEFT, FormatNumber(Me.Left, 2)
End Sub

Private Sub UserForm_Terminate()
   CommandState.StartDefaultCommand
End Sub


Private Sub ControlStates()
   Dim state As Boolean
   state = UseOffsetCheckBox.value
   OffsetTextBox.enabled = state
   LeftOptionButton.enabled = state
   RightOptionButton.enabled = state
End Sub

Attribute VB_Name = "FrmSetting"
Attribute VB_Base = "0{C4FCB4AA-5025-49BF-A149-6260F826D190}{78D53768-223C-40E9-8F19-1D5A7B257D85}"
Attribute VB_GlobalNameSpace = False
Attribute VB_Creatable = False
Attribute VB_PredeclaredId = True
Attribute VB_Exposed = False
Attribute VB_TemplateDerived = False
Attribute VB_Customizable = False
















'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

'GENERAL NOTES:
'PROGRAM ASSUMES MASTER UNIT IS FOOT OR SURVEY FOOT, SOME KIND OF FOOT

Option Explicit

Private Sub UserForm_Initialize()
'SET TITLE BAR
   Me.Caption = COMMAND_NAME_SETTINGS

'INITIALIZE NORTH AZIMUTH CHECKBOX
   NorthModeCheckBox = NORTH_AZIMUTH_MODE

'INITIALIZE PLOTSCALE TEXT BOX
   PlotScaleTextBox.TabIndex = 0
   LoadPlotScaleEntry PlotScaleTextBox, SECTION_SETTINGS, KEY_PLOT_SCALE
   PlotScaleTextBox.MaxLength = MAX_LEN_PLOT_SCALE_STRING

'COLOR COMBOBOX
   Dim previousColor As String
   previousColor = GetSetting(APP_NAME, SECTION_SETTINGS, KEY_COLOR, "")
   If previousColor = "" Then
      SaveSetting APP_NAME, SECTION_SETTINGS, KEY_COLOR, "3"
   End If
   PopulateColorBox ColorComboBox, SECTION_SETTINGS, KEY_COLOR

'INITIALIZE FONT SIZE DROP DOWN BOX
   fontSizeComboBox.TabIndex = 1
   fontSizeComboBox.style = fmStyleDropDownList
   fontSizeComboBox.AddItem "0.07 inch"
   fontSizeComboBox.AddItem "0.08 inch"
   fontSizeComboBox.AddItem "0.09 inch"
   fontSizeComboBox.AddItem "0.10 inch"
   fontSizeComboBox.AddItem "0.11 inch"
   fontSizeComboBox.text = GetSetting(APP_NAME, SECTION_SETTINGS, KEY_FONT_SIZE_INCH, SETTING_DEFAULT_FONT_SIZE_INCH)
   
   PlotScaleTextBox.TabIndex = 0
   closeButton.TabIndex = 1
   fontSizeComboBox.TabIndex = 2
End Sub



'NORTH AZIMUTH CHECKBOX
Private Sub NorthModeCheckBox_Click()
   SaveCheckBoxSetting NorthModeCheckBox, SECTION_SETTINGS, KEY_NORTH_MODE
   NORTH_AZIMUTH_MODE = NorthModeCheckBox.value
   If FrmOpener.enabled Then
      FrmOpener.AzModeIndicator
   End If
End Sub



'COLOR COMBOBOX
Private Sub ColorComboBox_AfterUpdate()
   ColorBoxOnUpdate ColorComboBox, SECTION_SETTINGS, KEY_COLOR
End Sub



'COLOR PICKER
Private Sub ChooseColorButton_Click()
   Dim MyColor As String
   If ChooseMyTableColor(MyColor) Then
      ColorComboBox.text = MyColor
      ColorComboBox_AfterUpdate
   End If
End Sub



'FONT SIZE COMBO BOX
Private Sub FontSizeComboBox_AfterUpdate()
   SaveSetting APP_NAME, SECTION_SETTINGS, KEY_FONT_SIZE_INCH, fontSizeComboBox.text
End Sub



'PLOT SCALE TEXTBOX
Private Sub PlotScaleTextBox_AfterUpdate()
   SaveNonnegativeEntry PlotScaleTextBox, SECTION_SETTINGS, KEY_PLOT_SCALE, MAX_PLOT_SCALE, MAX_PRECISION_PLOT_SCALE, False, 20
End Sub

Private Sub PlotScaleTextBox_Enter()
   SelectAllText PlotScaleTextBox
End Sub



'CLEAR STORAGE BUTTON
Private Sub ClearButton_Click()
   DeleteSetting APP_NAME
   MsgBox "Done."
End Sub



'CLOSE BUTTON
Private Sub CloseButton_Click()
   Unload Me
End Sub

Attribute VB_Name = "FrmStationInverse"
Attribute VB_Base = "0{D5111646-BF45-4F02-848A-146144034140}{9067387B-DBF2-41D1-8545-E83F3FFBC2E9}"
Attribute VB_GlobalNameSpace = False
Attribute VB_Creatable = False
Attribute VB_PredeclaredId = True
Attribute VB_Exposed = False
Attribute VB_TemplateDerived = False
Attribute VB_Customizable = False
















'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.



'GENERAL NOTES:
'ALL THESE ROUTINES WERE WRITTEN BY JASON LOOK.  THEY ARE NOT
'WRITTEN IN THE STYLE COMMONLY USED BY PROFESSIONAL PROGRAMMERS.
'THEY ARE WRITTEN IN THE STYLE PREFERRED BY JASON.  JASON IS NOT
'A PROFESSIONAL PROGRAMMER!

'PROGRAM ASSUMES MASTER UNIT IS FOOT OR SURVEY FOOT, SOME KIND OF FOOT

Option Explicit

'ELEMENT IDENTIFICATION
Private thePickedElement         As Element

'ELEMENT METRICS
Private thePickedLength          As Double
Private theStartPoint            As Point3d
Private theEndPoint              As Point3d
Private theRadiusPoint           As Point3d
Private theBeginStation          As String
Private theSweepAngle            As Double

'VALID ELEMENT SELECTED FLAG
Private isValidElement           As Boolean

'DON'T CLOSE YET FLAG
'TRUE IF DON'T CLOSE YET, FALSE IF OK TO CLOSE
Private doNotCloseYet            As Boolean

'SET TO TRUE IF NEED TO CALL    CommandState.StartDefaultCommand
Private needToEndCommand         As Boolean

Private stationStyleGlobal       As Integer


Public Sub CommandIsClosing()
'IF COMMAND IS CLOSING BUT NOT STARTING A NEW COMMAND THEN UNLOAD
   If Not doNotCloseYet Then
      needToEndCommand = False
      Unload Me
   End If
End Sub



Private Sub FlagInvalidElement()
'SETS FLAG TO INVALID ELELMENT, UPDATES DISPLAY
   isValidElement = False
   updateStatusDisplay thePickedElement, thePickedLength
End Sub



Private Sub FlagValidElement()
'SETS FLAG TO VALID ELEMENT, UPDATES DISPLAY, ENABLES "NEW ELEMENT" BUTTON
   isValidElement = True
   updateStatusDisplay thePickedElement, thePickedLength
End Sub



Public Sub PickNewSegment()
'CLEAR OUT PREVIOUS
   FlagInvalidElement

'START UP LOCATE COMMAND FOR PICKING BASELINE SEGMENTS
   DoNotClose = True 'DON'T CLOSE THE DIALOG BOX FOR THIS
   CommandState.StartLocate New StationInverseLocate
End Sub



'TEXT TEMPLATE
Public Function GetTextTemp() As TextElement
   Set GetTextTemp = CreateTextTemplate(SECTION_STATION_INVERSE, _
                                        FontComboBox, _
                                        KEY_FONT, _
                                        LevelComboBox, _
                                        KEY_LEVEL, _
                                        WeightComboBox, _
                                        ColorComboBox, _
                                        StyleComboBox, _
                                        KEY_STYLE, , _
                                        msdTextJustificationRightCenter)
End Function



'*************************************************************************************************************
'************************************************PROPERTIES***************************************************
'STORES PICKED ELEMENT
Property Let PickedElement(ByVal TheChosenElement As Element)
   Set thePickedElement = TheChosenElement
   If GetElementMetrics(TheChosenElement) Then
      FlagValidElement
      updateStatusDisplay thePickedElement, thePickedLength
   Else
      FlagInvalidElement
'START UP LOCATE COMMAND FOR PICKING BASELINE SEGMENTS
      CommandState.StartLocate New StationInverseLocate
   End If
End Property



'LET FLAG GET SET EXTERNALLY
Property Let DoNotClose(ByVal DoNotCloseFlag As Boolean)
   doNotCloseYet = DoNotCloseFlag
End Property



'GET PREFIX STRING
Property Get prefixString() As String
   If PrefixCheckBox.value = True Then
      prefixString = PrefixTextBox.text
   Else
      prefixString = ""
   End If
End Property



'*************************************************************************************************************
'*************************************************METRICS*****************************************************
Private Function GetElementMetrics(ByVal TheChosenElement As Element) As Boolean
'TRUE IF NO PROBLEM
'INITIALIZE FLAG
   GetElementMetrics = False

'GET THE BASELINE INFO
   Dim theValue As Variant
   If Not GetSurveyorToolsTagValue(TheChosenElement, TAG_NAME_BEGIN_STATION, theValue) Then
      Exit Function
   End If
   theBeginStation = theValue

'GET TREATED AS AN ARC
   If TheChosenElement.IsArcElement Then
      Dim TempArc As ArcElement
      Set TempArc = thePickedElement
      thePickedLength = TempArc.length
      theStartPoint = TempArc.startPoint
      theEndPoint = TempArc.endPoint
      theRadiusPoint = TempArc.CenterPoint
      theSweepAngle = TempArc.SweepAngle
   End If

   If TheChosenElement.IsLineElement Then
      If TheChosenElement.Type = msdElementTypeLineString Then
'GET TREATED AS A SPIRAL
         Dim spiralLengthString As String
         If Not GetSurveyorToolsTagValue(TheChosenElement, TAG_NAME_LENGTH, spiralLengthString) Then
            Exit Function
         End If
         thePickedLength = CDbl(spiralLengthString)
      Else
'GET TREATED AS A LINE
         thePickedLength = TheChosenElement.AsLineElement.length
      End If
      theStartPoint = TheChosenElement.AsLineElement.startPoint
      theEndPoint = TheChosenElement.AsLineElement.endPoint
   End If
   
'SUCCESS, RETURN TRUE
   GetElementMetrics = True
End Function



'*************************************************************************************************************
'**********************************************STATUS DISPLAY*************************************************
Private Sub updateStatusDisplay(ByVal theElement As Element, ByVal length As Double)
'CLEAR STATUS
   initializeStatus
   
'CHECK IF FLAGGED INVALID
   If Not isValidElement Then
      Exit Sub
   End If

'DISPLAY ELEMENT TYPE
   If theElement.Type = msdElementTypeLineString Then
      ElementTypeDisplayLabel.Caption = "spiral"
   ElseIf theElement.Type = msdElementTypeLine Then
      ElementTypeDisplayLabel.Caption = "line"
   ElseIf theElement.IsArcElement Then
      ElementTypeDisplayLabel.Caption = "curve"
   End If

'DISPLAY THE REST OF THE METRICS
   ElementLengthDisplayLabel.Caption = FormatNumber(length, DEFAULT_STATION_PRECISION)
   BeginStationDisplayLabel.Caption = theBeginStation
   Dim EndingStation As Double
   If Not calcEndStationOfElement(EndingStation) Then
      FlagInvalidElement
      Exit Sub
   End If
   EndStationDisplayLabel.Caption = StationToString(EndingStation, DEFAULT_STATION_PRECISION, stationStyleGlobal)
End Sub



Private Sub initializeStatus()
'BLANK OUT STATUS FIELDS
   ElementTypeDisplayLabel.Caption = ""
   ElementLengthDisplayLabel.Caption = ""
   BeginStationDisplayLabel.Caption = ""
   EndStationDisplayLabel.Caption = ""
End Sub



Private Function calcEndStationOfElement(ByRef EndingStation As Double) As Boolean
'CALCULATE THE ENDING STATION OF THE BASELINE
'RETURNS TRUE IF SUCESSFUL,
'INITIALIZE FLAG
   calcEndStationOfElement = False
   
'CONVERT BEGINNING STATION STRING TO DOUBLE, EXIT IF CANNOT
   Dim BeginStationDouble As Double
   Dim origPrec As Long
   If Not IsStationString(theBeginStation, BeginStationDouble, origPrec, stationStyleGlobal) Then
      Exit Function
   End If
   EndingStation = Round(thePickedLength, DEFAULT_STATION_PRECISION) + Round(BeginStationDouble, DEFAULT_STATION_PRECISION)
   calcEndStationOfElement = True
End Function



'*************************************************************************************************************
'**************************************************STATES*****************************************************
Private Sub PrefixTextBoxStates()
   PrefixTextBox.enabled = PrefixCheckBox.value
   PrefixTextBox.BackColor = BackOLE_COLOR(PrefixCheckBox.value)
End Sub




'*************************************************************************************************************
'*******************************************CONTROLS MAIN PAGE************************************************
'PREFIX CHECKBOX
Private Sub PrefixCheckBox_Click()
   PrefixTextBoxStates
   SaveCheckBoxSetting PrefixCheckBox, SECTION_STATION_INVERSE, KEY_OPTION_PREFIX
End Sub



'PREFIX TEXTBOX
Private Sub PrefixTextBox_AfterUpdate()
   SaveSetting APP_NAME, SECTION_STATION_INVERSE, KEY_PREFIX, PrefixTextBox.text
End Sub



'SETTINGS BUTTON
Private Sub SettingsButton_Click()
   Setting
End Sub



'*************************************************************************************************************
'*****************************************CONTROLS ATTRIBUTES PAGE********************************************
'COLOR COMBOBOX
Private Sub ColorComboBox_AfterUpdate()
   ColorBoxOnUpdate ColorComboBox, SECTION_STATION_INVERSE, KEY_COLOR
End Sub

'COLOR PICKER
Private Sub ChooseColorButton_Click()
   Dim MyColor As String
   If ChooseMyTableColor(MyColor) Then
      ColorComboBox.text = MyColor
      ColorComboBox_AfterUpdate
   End If
End Sub



'LEVEL COMBOBOX
Private Sub LevelComboBox_AfterUpdate()
   If Not LevelBoxOnUpdate(LevelComboBox, SECTION_STATION_INVERSE, KEY_LEVEL) Then
      PopulateLevelBox LevelComboBox, SECTION_STATION_INVERSE, KEY_LEVEL
      Beep
   End If
End Sub

'STYLE COMBOBOX
Private Sub StyleComboBox_AfterUpdate()
   If Not LineStyleBoxOnUpdate(StyleComboBox, SECTION_STATION_INVERSE, KEY_STYLE) Then
      PopulateLinestyleBox StyleComboBox, SECTION_STATION_INVERSE, KEY_STYLE
      Beep
   End If
End Sub

'WEIGHT COMBOBOX
Private Sub WeightComboBox_AfterUpdate()
   WeightBoxOnUpdate WeightComboBox, SECTION_STATION_INVERSE, KEY_WEIGHT
End Sub

'FONT COMBOBOX
Private Sub FontComboBox_AfterUpdate()
   If Not FontBoxOnUpdate(FontComboBox, SECTION_STATION_INVERSE, KEY_FONT) Then
      PopulateFontBox FontComboBox, SECTION_STATION_INVERSE, KEY_FONT
      Beep
   End If
End Sub



'*************************************************************************************************************
'**********************************************USERFORM EVENTS************************************************
Private Sub UserForm_Initialize()
'SET STATION STYLE
   stationStyleGlobal = 0

'INITIALIZE PREFIX CHECK BOX
   InitializeCheckBox PrefixCheckBox, SECTION_STATION_INVERSE, KEY_OPTION_PREFIX

'INITIALIZE PREFIX TEXT BOX
   PrefixTextBox.text = GetSetting(APP_NAME, SECTION_STATION_INVERSE, KEY_PREFIX, "")

'LEVEL COMBOBOX
   PopulateLevelBox LevelComboBox, SECTION_STATION_INVERSE, KEY_LEVEL
'COLOR COMBOBOX
   PopulateColorBox ColorComboBox, SECTION_STATION_INVERSE, KEY_COLOR
'STYLE COMBOBOX
   PopulateLinestyleBox StyleComboBox, SECTION_STATION_INVERSE, KEY_STYLE
'WEIGHT COMBOBOX
   PopulateWeightBox WeightComboBox, SECTION_STATION_INVERSE, KEY_WEIGHT
'FONT COMBOBOX
   PopulateFontBox FontComboBox, SECTION_STATION_INVERSE, KEY_FONT

'INITIALIZE STATUS AREA
   initializeStatus

'INITIALIZE GLOBAL VARIABLE
   theBeginStation = ""
   FlagInvalidElement
   DoNotClose = False
   needToEndCommand = True

'INITIALIZE PREFIX TEXT BOX STATE
   PrefixTextBoxStates

'MOVE INTO LAST POSITION
   If GetSetting(APP_NAME, SECTION_STATION_INVERSE, KEY_START_TOP, "") = "" Then
      Me.StartUpPosition = 1
   Else
      Me.StartUpPosition = 0
      Me.Top = CDbl(GetSetting(APP_NAME, SECTION_STATION_INVERSE, KEY_START_TOP, WINDOW_DEFAULT_TOP))
      Me.Left = CDbl(GetSetting(APP_NAME, SECTION_STATION_INVERSE, KEY_START_LEFT, WINDOW_DEFAULT_LEFT))
   End If
   
'MAKE SURE COMMAND NAME IS CORRECT
   Me.Caption = COMMAND_NAME_STATION_INVERSE

'START ON MAIN PAGE
   MultiPage1.value = 0

'START UP LOCATE COMMAND FOR PICKING BASELINE SEGMENTS
   CommandState.StartLocate New StationInverseLocate
End Sub



Private Sub UserForm_QueryClose(Cancel As Integer, CloseMode As Integer)
'SAVE USERFORM POSITION
   SaveSetting APP_NAME, SECTION_STATION_INVERSE, KEY_START_TOP, FormatNumber(Me.Top, 2)
   SaveSetting APP_NAME, SECTION_STATION_INVERSE, KEY_START_LEFT, FormatNumber(Me.Left, 2)
End Sub



Private Sub UserForm_Terminate()
'END COMMAND IF NEED TO
   If needToEndCommand Then
      CommandState.StartDefaultCommand
   End If
End Sub

Attribute VB_Name = "FrmStationPlot"
Attribute VB_Base = "0{65184E03-9CE6-441A-A116-E279DD75BEB6}{0F9630A8-7F75-4789-AD5C-0FDB9C7F1EA5}"
Attribute VB_GlobalNameSpace = False
Attribute VB_Creatable = False
Attribute VB_PredeclaredId = True
Attribute VB_Exposed = False
Attribute VB_TemplateDerived = False
Attribute VB_Customizable = False











'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.



'GENERAL NOTES:
'ALL THESE ROUTINES WERE WRITTEN BY JASON LOOK.  THEY ARE NOT
'WRITTEN IN THE STYLE COMMONLY USED BY PROFESSIONAL PROGRAMMERS.
'THEY ARE WRITTEN IN THE STYLE PREFERRED BY JASON.  JASON IS NOT
'A PROFESSIONAL PROGRAMMER!

'PROGRAM ASSUMES MASTER UNIT IS FOOT OR SURVEY FOOT, SOME KIND OF FOOT


Option Explicit

'ELEMENT IDENTIFICATION
Private thePickedElement         As Element

'ELEMENT METRICS
Private thePickedLength          As Double
Private theStartPoint            As Point3d
Private theEndPoint              As Point3d
Private theRadiusPoint           As Point3d
Private theBeginStation          As String
Private theSweepAngle            As Double

'TEMP GRAPHIC
Dim tecNormal As TransientElementContainer 'CONTAINER FOR TEMPORARY UNHIGHLIGHTED GRAPHICS

'VALID ELEMENT SELECTED FLAG
Private isValidElement           As Boolean

'DO NOT QUIT FLAG
Private okayToQuit               As Boolean


Private stationStyleGlobal       As Integer

'*************************************************************************************************************
'*******************************************TEMPORARY GRAPHICS************************************************
Private Sub CreateNormalTransientContainer()
'CREATE TEMPORARY GRAPHICS CONTAINER FOR REGULARLY DISPLAYED ELEMENTS
   Dim flags As MsdTransientFlags
   flags = msdTransientFlagsOverlay + msdTransientFlagsSnappable
   Set tecNormal = CreateTransientElementContainer1(Nothing, flags, msdViewAll - msdViewMask8 - msdViewMask7, msdDrawingModeNormal)
End Sub



'*************************************************************************************************************
'************************************************PROPERTIES***************************************************
'STORES PICKED ELEMENT
Property Let PickedElement(ByVal TheChosenElement As Element)
   Set thePickedElement = TheChosenElement
   If GetElementMetrics(TheChosenElement) Then
      FlagValidElement
   Else
      FlagInvalidElement
   End If
   updateStatusDisplay thePickedElement, thePickedLength
   UpdateButtonState
   okayToQuit = False
   CommandState.StartLocate New StationPlotLocate
End Property



'*************************************************************************************************************
'*************************************************************************************************************
Public Sub NotifyOfQuit()
   If okayToQuit Then
      Unload Me
   End If
End Sub



Public Sub NotifyOfOpen()
   okayToQuit = True
End Sub



Private Sub FlagInvalidElement()
   isValidElement = False
End Sub



Private Sub FlagValidElement()
   isValidElement = True
End Sub



Private Function IsValidBaseline() As Boolean
   IsValidBaseline = isValidElement
End Function



'*************************************************************************************************************
'*************************************************METRICS*****************************************************
Private Function GetElementMetrics(ByVal TheChosenElement As Element) As Boolean
'TRUE IF NO PROBLEM
'INITIALIZE FLAG
   GetElementMetrics = False

'GET THE BASELINE INFO
   Dim theValue As Variant
   If Not GetSurveyorToolsTagValue(TheChosenElement, TAG_NAME_BEGIN_STATION, theValue) Then
      Exit Function
   End If
   theBeginStation = theValue

'GET TREATED AS AN ARC
   If TheChosenElement.IsArcElement Then
      Dim TempArc As ArcElement
      Set TempArc = thePickedElement
      thePickedLength = TempArc.length
      theStartPoint = TempArc.startPoint
      theEndPoint = TempArc.endPoint
      theRadiusPoint = TempArc.CenterPoint
      theSweepAngle = TempArc.SweepAngle
   End If

   If TheChosenElement.IsLineElement Then
      If TheChosenElement.Type = msdElementTypeLineString Then
'GET TREATED AS A SPIRAL
'GET THE LENGTH
         Dim spiralLengthString As String
         If Not GetSurveyorToolsTagValue(TheChosenElement, TAG_NAME_LENGTH, spiralLengthString) Then
            Exit Function
         End If
         thePickedLength = CDbl(spiralLengthString)
      Else
'GET TREATED AS A LINE
         thePickedLength = TheChosenElement.AsLineElement.length
      End If
      theStartPoint = TheChosenElement.AsLineElement.startPoint
      theEndPoint = TheChosenElement.AsLineElement.endPoint
   End If
   
'SUCCESS, RETURN TRUE
   GetElementMetrics = True
End Function



'*************************************************************************************************************
'**********************************************STATUS DISPLAY*************************************************
Private Sub updateStatusDisplay(ByVal theElement As Element, ByVal length As Double)
'CLEAR STATUS
   initializeStatus
   
'CHECK IF FLAGGED INVALID
   If Not IsValidBaseline Then
      Exit Sub
   End If

'DISPLAY ELEMENT ID
   Dim ID As DLong
   Dim IDstring As String
   If Not GetTheElementID(thePickedElement, ID, IDstring) Then
      Exit Sub
   End If
   ElemantIDDisplayLabel.Caption = IDstring

'DISPLAY ELEMENT TYPE
   If theElement.IsLineElement Then
      If theElement.Type = msdElementTypeLineString Then
         ElementTypeDisplayLabel.Caption = "spiral"
      Else
         ElementTypeDisplayLabel.Caption = "line"
      End If
   ElseIf theElement.IsArcElement Then
      ElementTypeDisplayLabel.Caption = "curve"
   End If

'DISPLAY THE REST OF THE METRICS
   ElementLengthDisplayLabel.Caption = FormatNumber(length, 2)
   BeginStationDisplayLabel.Caption = theBeginStation
   Dim EndingStation As Double
   If Not calcEndStationOfElement(EndingStation) Then
      FlagInvalidElement
      Exit Sub
   End If
   EndStationDisplayLabel.Caption = StationToString(EndingStation, DEFAULT_STATION_PRECISION, stationStyleGlobal)
End Sub



Private Sub initializeStatus()
'BLANK OUT STATUS FIELDS
   ElementTypeDisplayLabel.Caption = ""
   ElementLengthDisplayLabel.Caption = ""
   BeginStationDisplayLabel.Caption = ""
   EndStationDisplayLabel.Caption = ""
   ElemantIDDisplayLabel.Caption = ""
End Sub



Private Function calcEndStationOfElement(ByRef EndingStation As Double) As Boolean
'CALCULATE THE ENDING STATION OF THE BASELINE
'RETURNS TRUE IF SUCESSFUL,
'INITIALIZE FLAG
   calcEndStationOfElement = False
   
'CONVERT BEGINNING STATION STRING TO DOUBLE, EXIT IF CANNOT
   Dim BeginStationDouble As Double
   Dim origPrec As Long
   If Not IsStationString(theBeginStation, BeginStationDouble, origPrec, stationStyleGlobal) Then
      Exit Function
   End If
   EndingStation = Round(thePickedLength, DEFAULT_STATION_PRECISION) + Round(BeginStationDouble, DEFAULT_STATION_PRECISION)
   calcEndStationOfElement = True
End Function



'*************************************************************************************************************
'***********************************************BUTTON STATE**************************************************
Private Sub UpdateButtonState()
   PlotButton.enabled = IsValidBaseline
End Sub



'*************************************************************************************************************
'************************************************CONTROLS*****************************************************
'HOLD PT AZIMUTH FOR PT STATION CHECKBOX
Private Sub HoldPTCheckBox_Click()
   SaveCheckBoxSetting HoldPTCheckBox, SECTION_STATION_PLOT_POINT, KEY_OPTION_HOLD_PT
End Sub



'ELEVATION TEXTBOX
Private Sub ElevationTextBox_AfterUpdate()
   SaveElevationEntry ElevationTextBox, SECTION_STATION_PLOT_POINT, KEY_ELEVATION
End Sub

Private Sub ElevationTextBox_Enter()
   SelectAllText ElevationTextBox
End Sub



'RESTURN HERE CHECKBOX
Private Sub returnCheckBox_Click()
   SaveCheckBoxSetting returnCheckBox, SECTION_STATION_PLOT_POINT, KEY_RETURN_HERE
End Sub



'STATION TEXTBOX
Private Sub StationTextBox_AfterUpdate()
   SaveStationEntry StationTextBox, SECTION_STATION_PLOT_POINT, KEY_STATION, stationStyleGlobal, DEFAULT_STATION_PRECISION
End Sub

Private Sub StationTextBox_Enter()
   SelectAllText StationTextBox
End Sub



'OFFSET TEXTBOX
Private Sub OffsetTextBox_AfterUpdate()
   SaveOffsetEntry OffsetTextBox, OptionLeft, OptionRight, SECTION_STATION_PLOT_POINT, KEY_OFFSET, 1000, 0
End Sub

Private Sub OffsetTextBox_Enter()
   SelectAllText OffsetTextBox
End Sub



'LEFT OPTION BUTTON
Private Sub OptionLeft_Click()
   saveJust
End Sub



'RIGHT OPTION BUTTON
Private Sub OptionRight_Click()
   saveJust
End Sub



Private Sub saveJust()
   Dim just As String
   If OptionLeft.value Then
      just = OPTION_LEFT
   Else
      just = OPTION_RIGHT
   End If
   SaveSetting APP_NAME, SECTION_STATION_PLOT_POINT, KEY_JUSTIFICATION, just
End Sub




'PLOT BUTTON
Private Sub PlotButton_Click()
'CONVERT STATION AND OFFSET TO DOUBLE
   Dim stationDouble As Double
   Dim origPrec As Long
   If Not IsStationString(StationTextBox, stationDouble, origPrec, stationStyleGlobal) Then
      Exit Sub
   End If
   
'CHECK BOUNDS
   Dim StartStationDouble As Double
   If Not IsStationString(BeginStationDisplayLabel.Caption, StartStationDouble, origPrec, stationStyleGlobal) Then
      Exit Sub
   End If
   Dim EndStationDouble As Double
   If Not IsStationString(EndStationDisplayLabel.Caption, EndStationDouble, origPrec, stationStyleGlobal) Then
      Exit Sub
   End If
   If stationDouble < StartStationDouble Or stationDouble > EndStationDouble Then
      MsgBox "Station out of range"
      Exit Sub
   End If

'CALC BASELINE POINT AND OFFSET POINT
   Dim offset As Double
   offset = Abs(CDbl(OffsetTextBox.text))
   If OptionLeft.value Then
      offset = -offset
   End If
   If thePickedElement.IsLineElement Then
      If thePickedElement.Type = msdElementTypeLineString Then
         Dim BaselinePoint As Point3d
         Dim fwdSAz As Double
         GetBasePntFwdAzSpiral stationDouble, thePickedElement, BaselinePoint, fwdSAz
         Dim OffsetPoint As Point3d
         OffsetPoint = CoordFwdSAz(BaselinePoint, fwdSAz + 90, offset)
      Else
         Dim lineAz As Double
         lineAz = InverseAzimuth(theStartPoint, theEndPoint)
         BaselinePoint = CoordFwdSAz(theStartPoint, lineAz, stationDouble - StartStationDouble)
         OffsetPoint = CoordFwdSAz(BaselinePoint, lineAz + 90, offset)
      End If
   End If
   If thePickedElement.IsArcElement Then
      Dim PCAz As Double
      PCAz = InverseAzimuth(theRadiusPoint, theStartPoint)
      Dim shortAngle As Double
      shortAngle = (180 * (stationDouble - StartStationDouble)) / (thePickedElement.AsArcElement.PrimaryRadius * Pi)
      If theSweepAngle > 0 Then
         shortAngle = -shortAngle
      End If
      Dim BaselinePointAz As Double
      BaselinePointAz = PCAz + shortAngle
      If HoldPTCheckBox.value And stationDouble = EndStationDouble Then
         BaselinePointAz = InverseAzimuth(theRadiusPoint, theEndPoint)
      End If
      Dim theRadius As Double
      theRadius = thePickedElement.AsArcElement.PrimaryRadius
      BaselinePoint = CoordFwdSAz(theRadiusPoint, BaselinePointAz, theRadius)
      Dim offsetDouble As Double
      offsetDouble = offset
      If theSweepAngle < 0 Then
         offsetDouble = -offsetDouble
      End If
      OffsetPoint = CoordFwdSAz(theRadiusPoint, BaselinePointAz, theRadius + offsetDouble)
   End If
   OffsetPoint.z = CDbl(ElevationTextBox.text)

'GET ACTIVE VIEW IF ANY
   Dim mySelectedView As view
   Set mySelectedView = GetSelectedView()

'IF THERE IS NO OPEN VIEW, THEN QUIT
   If mySelectedView Is Nothing Then
      Beep
      Exit Sub
   End If

'CALCULATE ROATATION TO MATCH VIEW
   Dim rotateViewAboutZAngle As Double
   rotateViewAboutZAngle = TheViewRotRadians(mySelectedView)

'DRAW POINT
   Dim SymbolCell As CellElement
   Set SymbolCell = CreateSymbol2Cell(Nothing, OffsetPoint, GetCharSize(), rotateViewAboutZAngle)
   ActiveModelReference.AddElement SymbolCell
   SymbolCell.Redraw
   
'DRAW TEMPORARY GRAPHIC
   CreateNormalTransientContainer
   Dim oLineStyle As LineStyle
   Set oLineStyle = ActiveDesignFile.LineStyles.Find("0")
   Dim tetherline As LineElement
   Set tetherline = CreateLineElement2(Nothing, BaselinePoint, OffsetPoint)
   Set tetherline.LineStyle = oLineStyle
   tetherline.color = GetTetherColor()
   tecNormal.AppendCopyOfElement tetherline
   
'CLOSE UP, SET UNDO
   CommandState.CommandName = COMMAND_NAME_STATION_PLOT
   okayToQuit = False
   CommandState.StartLocate New StationPlotLocate
   If returnCheckBox.value Then
      ElevationTextBox.SetFocus
   Else
      StationTextBox.SetFocus
   End If
End Sub



'SETTINGS BUTTON
Private Sub SettingsButton_Click()
   Setting
End Sub



'*************************************************************************************************************
'**********************************************USERFORM EVENTS************************************************
Private Sub UserForm_Initialize()
'SET STATION STYLE
   stationStyleGlobal = 0
   
'INITIALIZE JUSTIFICATION
   Select Case GetSetting(APP_NAME, SECTION_STATION_PLOT_POINT, KEY_JUSTIFICATION, OPTION_RIGHT)
      Case OPTION_LEFT
         Dim myOption As String
         OptionLeft.value = True
      Case OPTION_RIGHT
         OptionRight.value = True
      Case Else
         OptionRight.value = True
   End Select

'INITIALIZE CHECK BOXES
   InitializeCheckBox HoldPTCheckBox, SECTION_STATION_PLOT_POINT, KEY_OPTION_HOLD_PT
   InitializeCheckBox returnCheckBox, SECTION_STATION_PLOT_POINT, KEY_RETURN_HERE

'INITIALIZE TEXT BOXES
   ElevationTextBox.text = GetSetting(APP_NAME, SECTION_STATION_PLOT_POINT, KEY_ELEVATION, "10")
   ElevationTextBox.MaxLength = MAX_LEN_ELEV_STRING
   
   StationTextBox.text = GetSetting(APP_NAME, SECTION_STATION_PLOT_POINT, KEY_STATION, "10+00")
   StationTextBox.MaxLength = MAX_LEN_STA_STRING
   
   OffsetTextBox.text = GetSetting(APP_NAME, SECTION_STATION_PLOT_POINT, KEY_OFFSET, "0")
   If Not IsNumeric(OffsetTextBox.text) Then
      OffsetTextBox.text = "10"
   End If

'INITIALIZE STATUS AREA
   initializeStatus

'INITIALIZE GLOBAL VARIABLE
   okayToQuit = True
   theBeginStation = ""
   FlagInvalidElement
   
'INITIALIZE BUTTON
   UpdateButtonState
   
'MAKE SURE COMMAND NAME IS CORRECT
   Me.Caption = COMMAND_NAME_STATION_PLOT

'MOVE INTO LAST POSITION
   If GetSetting(APP_NAME, SECTION_STATION_PLOT_POINT, KEY_START_TOP, "") = "" Then
      Me.StartUpPosition = 1
   Else
      Me.StartUpPosition = 0
      Me.Top = CDbl(GetSetting(APP_NAME, SECTION_STATION_PLOT_POINT, KEY_START_TOP, WINDOW_DEFAULT_TOP))
      Me.Left = CDbl(GetSetting(APP_NAME, SECTION_STATION_PLOT_POINT, KEY_START_LEFT, WINDOW_DEFAULT_LEFT))
   End If
   
'8START UP LOCATE COMMAND FOR PICKING BASELINE SEGMENTS
   CommandState.StartLocate New StationPlotLocate
End Sub



Private Sub UserForm_QueryClose(Cancel As Integer, CloseMode As Integer)
'SAVE USERFORM POSITION
   SaveSetting APP_NAME, SECTION_STATION_PLOT_POINT, KEY_START_TOP, FormatNumber(Me.Top, 2)
   SaveSetting APP_NAME, SECTION_STATION_PLOT_POINT, KEY_START_LEFT, FormatNumber(Me.Left, 2)
End Sub



Private Sub UserForm_Terminate()
   CommandState.StartDefaultCommand
End Sub

Attribute VB_Name = "FrmStationText"
Attribute VB_Base = "0{668C1380-88CE-4EDF-B55C-7D4A9544E539}{7886C1EA-A2A0-4A59-BE99-008453B41596}"
Attribute VB_GlobalNameSpace = False
Attribute VB_Creatable = False
Attribute VB_PredeclaredId = True
Attribute VB_Exposed = False
Attribute VB_TemplateDerived = False
Attribute VB_Customizable = False











'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.



'GENERAL NOTES:
'ALL THESE ROUTINES WERE WRITTEN BY JASON LOOK.  THEY ARE NOT
'WRITTEN IN THE STYLE COMMONLY USED BY PROFESSIONAL PROGRAMMERS.
'THEY ARE WRITTEN IN THE STYLE PREFERRED BY JASON.  JASON IS NOT
'A PROFESSIONAL PROGRAMMER!

'PROGRAM ASSUMES MASTER UNIT IS FOOT OR SURVEY FOOT, SOME KIND OF FOOT

Option Explicit

'ELEMENT IDENTIFICATION
Private thePickedElement   As Element
Private ThePickedID        As DLong
Private ThePickedIDString  As String

'ELEMENT METRICS
Private thePickedLength    As Double
Private theStartPoint      As Point3d
Private theEndPoint        As Point3d
Private theRadiusPoint     As Point3d
Private theBeginStation    As String
Private theSweepAngle      As Double

'VALID ELEMENT SELECTED FLAG
Private isValidElement     As Boolean

'DO NOT CLOSE FLAG
Private doNotCloseYet      As Boolean

'FILE OPERATIONS CONSTANTS
Private Const FILE_STATION_TEXT_FILE_HEADER                    As String = "FMT Station Settings"
Private Const FILE_STATION_TEXT_FILE_EXTENSION                 As String = ".jss"
Private Const FILE_STATION_TEXT_REC_FONT_SCALE                 As String = "FS:"
Private Const FILE_STATION_TEXT_REC_OFFSET_TRANSVERSE          As String = "OST:"
Private Const FILE_STATION_TEXT_REC_OFFSET_TRANSVERSE_OPTION   As String = "OSTO:"
Private Const FILE_OPTION_OFFSET_TRANSVERSE_LEFT               As String = "Left"
Private Const FILE_OPTION_OFFSET_TRANSVERSE_RIGHT              As String = "Right"
Private Const FILE_STATION_TEXT_REC_OFFSET_LONGITUDINAL        As String = "OSL:"
Private Const FILE_STATION_TEXT_REC_OFFSET_LONGITUDINAL_OPTION As String = "OSLO:"
Private Const FILE_OPTION_OFFSET_LONGITUDINAL_AHEAD            As String = "Ahead"
Private Const FILE_OPTION_OFFSET_LONGITUDINAL_BACK             As String = "Back"
Private Const FILE_STATION_TEXT_REC_PLUS_ZERO_ZERO             As String = "PZZ:"
Private Const FILE_OPTION_IS_CHECKED                           As String = "Checked"
Private Const FILE_OPTION_NOT_CHECKED                          As String = "NotChecked"
Private Const FILE_STATION_TEXT_REC_ORIENTATION                As String = "OR:"
Private Const FILE_OPTION_ORIENTATION_LEFT                     As String = "Left"
Private Const FILE_OPTION_ORIENTATION_RIGHT                    As String = "Right"
Private Const FILE_OPTION_ORIENTATION_FORWARD                  As String = "Forward"
Private Const FILE_OPTION_ORIENTATION_BACK                     As String = "Back"
Private Const FILE_STATION_TEXT_REC_INTERVAL                   As String = "IN:"
Private Const FILE_OPTION_INTERVAL_100                         As String = "100"
Private Const FILE_OPTION_INTERVAL_500                         As String = "500"
Private Const FILE_STATION_TEXT_REC_JUSTIFICATION              As String = "JUS:"
Private Const FILE_OPTION_JUSTIFICATION_RIGHT                  As String = "Right"
Private Const FILE_OPTION_JUSTIFICATION_CENTER                 As String = "Center"
Private Const FILE_OPTION_JUSTIFICATION_LEFT                   As String = "Left"
Private Const FILE_STATION_TEXT_REC_TICKS_LEFT                 As String = "TKL:"
Private Const FILE_STATION_TEXT_REC_TICKS_RIGHT                As String = "TKR:"
Private Const FILE_STATION_TEXT_REC_SCALE_LEFT                 As String = "TSL:"
Private Const FILE_STATION_TEXT_REC_SCALE_RIGHT                As String = "TSR:"
Private Const FILE_STATION_TEXT_SETTING_LEVEL                  As String = "S11:"
Private Const FILE_STATION_TEXT_SETTING_COLOR                  As String = "S12:"
Private Const FILE_STATION_TEXT_SETTING_STYLE                  As String = "S13:"
Private Const FILE_STATION_TEXT_SETTING_WEIGHT                 As String = "S14:"
Private Const FILE_STATION_TEXT_SETTING_FONT                   As String = "S15:"
Private Const FILE_STATION_TICK_SETTING_LEVEL                  As String = "S21:"
Private Const FILE_STATION_TICK_SETTING_COLOR                  As String = "S22:"
Private Const FILE_STATION_TICK_SETTING_STYLE                  As String = "S23:"
Private Const FILE_STATION_TICK_SETTING_WEIGHT                 As String = "S24:"

Private Const MAX_FONT_SCALE              As Double = 10
Private Const MAX_PRECISION_FONT_SCALE    As Long = 4
Private Const MAX_OFFSET                  As Double = 300#
Private Const DEFAULT_OFFSET              As Double = 0#

Private linearPrecisionGlobal             As Long
Private entryStationStyleGlobal           As Integer




'*************************************************************************************************************
'************************************************PROPERTIES***************************************************
'STORES PICKED ELEMENT
Property Let PickedElement(TheChosenElement As Element)
   Set thePickedElement = TheChosenElement
   If Not IsValidBaselineSegment(TheChosenElement) Then
      FlagInvalidElement
   ElseIf GetElementMetrics(thePickedElement) Then
      FlagValidElement
      updateStatusDisplay thePickedElement, ThePickedIDString, thePickedLength
      SuggestBeginStation
      SuggestEndStation
   Else
      FlagInvalidElement
   End If
End Property



'*************************************************************************************************************
'**********************************************CONTROL STATES*************************************************
Private Sub TickScaleLeftStates()
'SET THE ENABLED STATE OF TEXT WINDOW AND LABEL FOR LEFT TICK SCALE
   Dim enabledState As Boolean
   enabledState = CheckBoxLeft.value
      
   ScaleLabelLeft.enabled = enabledState
   TickScaleLeftTextBox.enabled = enabledState
   TickScaleLeftTextBox.BackColor = BackOLE_COLOR(enabledState)
End Sub



Private Sub TickScaleRightStates()
'SET THE ENABLED STATE OF TEXT WINDOW AND LABEL FOR RIGHT TICK SCALE
   Dim enabledState As Boolean
   enabledState = CheckBoxRight.value
   
   ScaleLabelRight.enabled = enabledState
   TickScaleRightTextBox.enabled = enabledState
   TickScaleRightTextBox.BackColor = BackOLE_COLOR(enabledState)
End Sub



'*************************************************************************************************************
'**************************************************MAIN TAB***************************************************
'FONT SCALE TEXTBOX
Private Sub FontScaleTextBox_AfterUpdate()
   SaveNonnegativeEntry FontScaleTextBox, SECTION_SETTINGS, KEY_FONT_SCALE, MAX_FONT_SCALE, MAX_PRECISION_FONT_SCALE, False, 1#
End Sub

Private Sub FontScaleTextBox_Enter()
   SelectAllText FontScaleTextBox
End Sub



'PLUS ZERO ZERO CHECKBOX
Private Sub Plus00CheckBox_Click()
   SaveCheckBoxSetting Plus00CheckBox, SECTION_STATION_TEXT, KEY_OPTION_INCLUDE_PLUS00
End Sub



'TRANSVERSE OPTION BUTTONS, LEFT
Private Sub OptionLeft_Click()
   SaveTransverseOptions
End Sub



'TRANSVERSE OPTION BUTTONS, RIGHT
Private Sub OptionRight_Click()
   SaveTransverseOptions
End Sub



'SAVE TRANSVERSE OFFSET OPTION SETTING
Private Sub SaveTransverseOptions()
   If OptionLeft.value = True Then
      SaveSetting APP_NAME, SECTION_STATION_TEXT, KEY_OPTION_TRANSVERSE, OPTION_LEFT
   Else
      SaveSetting APP_NAME, SECTION_STATION_TEXT, KEY_OPTION_TRANSVERSE, OPTION_RIGHT
   End If
End Sub



'TRANSVERSE OFFSET TEXTBOX
Private Sub TransverseTextBox_AfterUpdate()
   SaveOffsetEntry TransverseTextBox, OptionLeft, OptionRight, SECTION_STATION_TEXT, KEY_OFFSET, MAX_OFFSET, DEFAULT_OFFSET
End Sub

Private Sub TransverseTextBox_Enter()
   SelectAllText TransverseTextBox
End Sub



'LONGITUDINAL OPTION BUTTONS, AHEAD
Private Sub OptionAhead_Click()
   SaveLogitudinalOptions
End Sub



'LONGITUDINAL OPTION BUTTONS, BACK
Private Sub OptionBack_Click()
   SaveLogitudinalOptions
End Sub



'LONGITUDINAL OFFSET TEXTBOX
Private Sub LongitudinalTextBox_AfterUpdate()
   SaveOffsetEntry LongitudinalTextBox, OptionBack, OptionAhead, SECTION_STATION_TEXT, KEY_OFFSET_LONGITUDINAL, MAX_OFFSET, DEFAULT_OFFSET
End Sub

Private Sub LongitudinalTextBox_Enter()
   SelectAllText LongitudinalTextBox
End Sub



'SAVE LONGITUDINAL OFFSET OPTION SETTING
Private Sub SaveLogitudinalOptions()
   If OptionAhead.value = True Then
      SaveSetting APP_NAME, SECTION_STATION_TEXT, KEY_OPTION_LONGITUDINAL, OPTION_AHEAD
   Else
      SaveSetting APP_NAME, SECTION_STATION_TEXT, KEY_OPTION_LONGITUDINAL, OPTION_BACK
   End If
End Sub



'SAVE SETTINGS BUTTON
Private Sub SaveSettingsButton_Click()
'GO MODAL
   Me.enabled = False

'SAVE FILE AS
   SaveAsStationTextFile

'GO UNMODAL
   Me.enabled = True
End Sub



'LOAD BUTTON
Private Sub LoadSettingsButton_Click()
'GO MODAL
   Me.enabled = False

'LOAD SETTINGS BUTTON
   Dim filename As String
   If LoadStationTextFile(filename) Then
'SAVE FULL PATH
      SaveSetting APP_NAME, SECTION_STATION_TEXT, KEY_FILENAME, filename
      
'LOAD SETTINGS FROM FILE
      LoadSettingsFromFile filename
   End If

'GO UNMODAL
   Me.enabled = True
End Sub



'START AT STATION TEXTBOX
Private Sub StartTextBox_AfterUpdate()
   SaveStationEntry StartTextBox, SECTION_STATION_TEXT, KEY_STATION_START, entryStationStyleGlobal, linearPrecisionGlobal
End Sub

Private Sub StartTextBox_Enter()
   SelectAllText StartTextBox
End Sub



'END AT STATION TEXTBOX
Private Sub EndTextBox_AfterUpdate()
   SaveStationEntry EndTextBox, SECTION_STATION_TEXT, KEY_STATION_END, entryStationStyleGlobal, linearPrecisionGlobal
End Sub

Private Sub EndTextBox_Enter()
   SelectAllText EndTextBox
End Sub



'**********ORIENTATION OPTION BUTTONS***********
'ORIENTATION TOP FACES LEFT RADIO BUTTON
Private Sub OptionTopToLeft_Click()
   SaveOrientationOptions
End Sub



'ORIENTATION TOP FACES RIGHT RADIO BUTTON
Private Sub OptionTopToRight_Click()
   SaveOrientationOptions
End Sub



'ORIENTATION TOP FACES FORWARD RADIO BUTTON
Private Sub OptionTopForward_Click()
   SaveOrientationOptions
End Sub



'ORIENTATION TOP FACES BACK RADIO BUTTON
Private Sub OptionTopBack_Click()
   SaveOrientationOptions
End Sub



'SAVE ORIENTATION OPTION BUTTON SETTINGS
Private Sub SaveOrientationOptions()
   If OptionTopToLeft.value = True Then
      SaveSetting APP_NAME, SECTION_STATION_TEXT, KEY_ORIENTATION, OPTION_TOP_TO_LEFT
   ElseIf OptionTopToRight.value = True Then
      SaveSetting APP_NAME, SECTION_STATION_TEXT, KEY_ORIENTATION, OPTION_TOP_TO_RIGHT
   ElseIf OptionTopForward.value = True Then
      SaveSetting APP_NAME, SECTION_STATION_TEXT, KEY_ORIENTATION, OPTION_TOP_FORWARD
   ElseIf OptionTopBack.value = True Then
      SaveSetting APP_NAME, SECTION_STATION_TEXT, KEY_ORIENTATION, OPTION_TOP_BACK
   End If
End Sub



'INTERVAL, EVEN 100S RADIO BUTTON
Private Sub Option100foot_Click()
   SaveIntervalOptions
End Sub



'INTERVAL, EVEN 500S RADIO BUTTON
Private Sub Option500foot_Click()
   SaveIntervalOptions
End Sub



'SAVE INTERVAL OPTION BUTTON SETTINGS
Private Sub SaveIntervalOptions()
   If Option100foot.value = True Then
      SaveSetting APP_NAME, SECTION_STATION_TEXT, KEY_INTERVAL, OPTION_100S
   ElseIf Option500foot.value = True Then
      SaveSetting APP_NAME, SECTION_STATION_TEXT, KEY_INTERVAL, OPTION_500S
   End If
End Sub



'JUSTIFICATION, LEFT RADIO BUTTON
Private Sub OptionLeftJustified_Click()
   SaveJustificationOptions
End Sub



'JUSTIFICATION, CENTER RADIO BUTTON
Private Sub OptionCenterJustified_Click()
   SaveJustificationOptions
End Sub



'JUSTIFICATION, RIGHT RADIO BUTTON
Private Sub OptionRightJustified_Click()
   SaveJustificationOptions
End Sub



'SAVE JUSTIFICATION OPTION BUTTON SETTINGS
Private Sub SaveJustificationOptions()
   If OptionRightJustified.value = True Then
      SaveSetting APP_NAME, SECTION_STATION_TEXT, KEY_JUSTIFICATION, OPTION_JUSTIFIED_RIGHT
   ElseIf OptionCenterJustified.value = True Then
      SaveSetting APP_NAME, SECTION_STATION_TEXT, KEY_JUSTIFICATION, OPTION_JUSTIFIED_CENTER
   ElseIf OptionLeftJustified.value = True Then
      SaveSetting APP_NAME, SECTION_STATION_TEXT, KEY_JUSTIFICATION, OPTION_JUSTIFIED_LEFT
   End If
End Sub



'TICK MARK LEFT CHECKBOX
Private Sub CheckBoxLeft_Click()
   SaveCheckBoxSetting CheckBoxLeft, SECTION_STATION_TEXT, KEY_TICKS_LEFT
   TickScaleLeftStates
End Sub



'TICK MARK RIGHT CHECKBOX
Private Sub CheckBoxRight_Click()
   SaveCheckBoxSetting CheckBoxRight, SECTION_STATION_TEXT, KEY_TICKS_RIGHT
   TickScaleRightStates
End Sub



'TICK SCALE LEFT TEXTBOX
Private Sub TickScaleLeftTextBox_AfterUpdate()
   SaveNonnegativeEntry TickScaleLeftTextBox, SECTION_STATION_TEXT, KEY_TICKS_SCALE_LEFT, 300, 4, False, 0.5
End Sub

Private Sub TickScaleLeftTextBox_Enter()
   SelectAllText TickScaleLeftTextBox
End Sub



'TICK SCALE RIGHT TEXTBOX
Private Sub TickScaleRightTextBox_AfterUpdate()
   SaveNonnegativeEntry TickScaleRightTextBox, SECTION_STATION_TEXT, KEY_TICKS_SCALE_RIGHT, 300, 4, False, 0.5
End Sub

Private Sub TickScaleRightTextBox_Enter()
   SelectAllText TickScaleRightTextBox
End Sub



'DO THE STATION TEXTING, "APPLY BUTTON"
Private Sub GObutton_Click()
   DoTheTextingAndTicks thePickedElement
End Sub



'*************************************************************************************************************
'************************************************SETTINGS TAB*************************************************
'STATION TEXT LEVEL COMBOBOX
Private Sub OtherTextLevelComboBox_AfterUpdate()
   If Not LevelBoxOnUpdate(OtherTextLevelComboBox, SECTION_STATION_TEXT, KEY_LEVEL) Then
      PopulateLevelBox OtherTextLevelComboBox, SECTION_STATION_TEXT, KEY_LEVEL
      Beep
   End If
End Sub



'STATION TEXT COLOR COMBOBOX
Private Sub OtherTextColorComboBox_AfterUpdate()
   ColorBoxOnUpdate OtherTextColorComboBox, SECTION_STATION_TEXT, KEY_COLOR
End Sub



'COLOR CHOOSER BUTTON FOR STATION TEXT
Private Sub TextColorChooserButton_Click()
   Dim MyColor As String
   If ChooseMyTableColor(MyColor) Then
      OtherTextColorComboBox.text = MyColor
      OtherTextColorComboBox_AfterUpdate
   End If
End Sub



'STATION TEXT STYLE COMBOBOX
Private Sub OtherTextStyleComboBox_AfterUpdate()
   If Not LineStyleBoxOnUpdate(OtherTextStyleComboBox, SECTION_STATION_TEXT, KEY_STYLE) Then
      PopulateLinestyleBox OtherTextStyleComboBox, SECTION_STATION_TEXT, KEY_STYLE
      Beep
   End If
End Sub



'STATION TEXT WEIGHT COMBOBOX
Private Sub OtherTextWeightComboBox_AfterUpdate()
   WeightBoxOnUpdate OtherTextWeightComboBox, SECTION_STATION_TEXT, KEY_WEIGHT
End Sub



'STATION TEXT FONT COMBOBOX
Private Sub OtherTextFontComboBox_AfterUpdate()
   If Not FontBoxOnUpdate(OtherTextFontComboBox, SECTION_STATION_TEXT, KEY_FONT) Then
      PopulateFontBox OtherTextFontComboBox, SECTION_STATION_TEXT, KEY_FONT
      Beep
   End If
End Sub



'STATION TICK MARK LEVEL COMBOBOX
Private Sub SymbolsLevelComboBox_AfterUpdate()
   If Not LevelBoxOnUpdate(SymbolsLevelComboBox, SECTION_STATION_TEXT, KEY_LEVEL2) Then
      PopulateLevelBox SymbolsLevelComboBox, SECTION_STATION_TEXT, KEY_LEVEL2
      Beep
   End If
End Sub



'STATION TICK MARK COLOR COMBOBOX
Private Sub SymbolsColorComboBox_AfterUpdate()
   ColorBoxOnUpdate SymbolsColorComboBox, SECTION_STATION_TEXT, KEY_COLOR2
End Sub



'COLOR CHOOSER BUTTON FOR TICK MARKS
Private Sub SymbolColorChooserButton_Click()
   Dim MyColor As String
   If ChooseMyTableColor(MyColor) Then
      SymbolsColorComboBox.text = MyColor
      SymbolsColorComboBox_AfterUpdate
   End If
End Sub



'STATION TICK MARK STYLE COMBOBOX
Private Sub SymbolsStyleComboBox_AfterUpdate()
   If Not LineStyleBoxOnUpdate(SymbolsStyleComboBox, SECTION_STATION_TEXT, KEY_STYLE2) Then
      PopulateLinestyleBox SymbolsStyleComboBox, SECTION_STATION_TEXT, KEY_STYLE2
      Beep
   End If
End Sub



'STATION TICK MARK WEIGHT COMBOBOX
Private Sub SymbolsWeightComboBox_AfterUpdate()
   WeightBoxOnUpdate OtherTextWeightComboBox, SECTION_STATION_TEXT, KEY_WEIGHT2
End Sub



'SETTINGS BUTTON
Private Sub SettingsButton_Click()
   Setting
End Sub



'*************************************************************************************************************
'**********************************************USERFORM EVENTS************************************************
Private Sub UserForm_Initialize()
'SET PRECISION GLOBAL VARIABLE
   linearPrecisionGlobal = LINEAR_PRECISION_BASELINE
   
'SET STAATION STYLE GLOBAL VARIABLE
   entryStationStyleGlobal = STYLE_STATION_NO_0_FRAC

'INITIALIZE FONT SCALE TEXT BOX
   LoadNonnegativeEntry FontScaleTextBox, SECTION_STATION_TEXT, KEY_FONT_SCALE, 1
   
'INITIALIZE TRANSVERSE OFFSET OPTION BUTTONS
   Dim myOption As String
   myOption = GetSetting(APP_NAME, SECTION_STATION_TEXT, KEY_OPTION_TRANSVERSE, OPTION_LEFT)
   If myOption = OPTION_LEFT Then
      OptionLeft.value = True
   Else
      OptionRight.value = True
   End If
   
'INITIALIZE TRANSVERSE OFFSET
   LoadNonnegativeEntry TransverseTextBox, SECTION_STATION_TEXT, KEY_OFFSET, 0
   
'INITIALIZE LONGITUDINAL OPTION BUTTONS
   myOption = GetSetting(APP_NAME, SECTION_STATION_TEXT, KEY_OPTION_LONGITUDINAL, OPTION_AHEAD)
   If myOption = OPTION_AHEAD Then
      OptionAhead.value = True
   Else
      OptionBack.value = True
   End If
   
'INITIALIZE LONGITUDINAL OFFSET
   LoadNonnegativeEntry LongitudinalTextBox, SECTION_STATION_TEXT, KEY_OFFSET_LONGITUDINAL, 0

'INITIALIZE ORIENTATION OPTION BUTTONS
   myOption = GetSetting(APP_NAME, SECTION_STATION_TEXT, KEY_ORIENTATION, OPTION_TOP_TO_LEFT)
   Select Case myOption
      Case OPTION_TOP_TO_LEFT
         OptionTopToLeft.value = True
      Case OPTION_TOP_TO_RIGHT
         OptionTopToRight.value = True
      Case OPTION_TOP_FORWARD
         OptionTopForward.value = True
      Case OPTION_TOP_BACK
         OptionTopBack.value = True
      Case Else
         OptionTopToRight.value = True
   End Select
   
'INITIAL INTERVAL OPTION BUTTONS
   myOption = GetSetting(APP_NAME, SECTION_STATION_TEXT, KEY_INTERVAL, OPTION_500S)
   If myOption = OPTION_500S Then
      Option500foot.value = True
   Else
      Option100foot.value = True
   End If

'INITIALIZE INCLUDE "+ 00" CHECK BOX
   InitializeCheckBox Plus00CheckBox, SECTION_STATION_TEXT, KEY_OPTION_INCLUDE_PLUS00

'INITIALIZE JUSTIFICATION OPTION BUTTONS
   myOption = GetSetting(APP_NAME, SECTION_STATION_TEXT, KEY_JUSTIFICATION, OPTION_JUSTIFIED_RIGHT)
   Select Case myOption
      Case OPTION_JUSTIFIED_RIGHT
         OptionRightJustified.value = True
      Case OPTION_JUSTIFIED_CENTER
         OptionCenterJustified.value = True
      Case OPTION_JUSTIFIED_LEFT
         OptionLeftJustified.value = True
   End Select

'INITIALIZE TICKS CHECK BOX LEFT
   InitializeCheckBox CheckBoxLeft, SECTION_STATION_TEXT, KEY_TICKS_LEFT

'INITIALIZE TICKS CHECK BOX RIGHT
   InitializeCheckBox CheckBoxRight, SECTION_STATION_TEXT, KEY_TICKS_RIGHT

'INITIALIZE TICK SCALE TEXT BOXES
   LoadNonnegativeEntry TickScaleLeftTextBox, SECTION_STATION_TEXT, KEY_TICKS_SCALE_LEFT, 1
   LoadNonnegativeEntry TickScaleRightTextBox, SECTION_STATION_TEXT, KEY_TICKS_SCALE_RIGHT, 1

'INITIALIZE STATES OF TEXT BOXES
   TickScaleLeftStates
   TickScaleRightStates

'FILL IN STATION TEXT SETTINGS TEXT BOXES
   PopulateLevelBox OtherTextLevelComboBox, SECTION_STATION_TEXT, KEY_LEVEL
   PopulateColorBox OtherTextColorComboBox, SECTION_STATION_TEXT, KEY_COLOR
   PopulateLinestyleBox OtherTextStyleComboBox, SECTION_STATION_TEXT, KEY_STYLE
   PopulateWeightBox OtherTextWeightComboBox, SECTION_STATION_TEXT, KEY_WEIGHT
   PopulateFontBox OtherTextFontComboBox, SECTION_STATION_TEXT, KEY_FONT

'FILL IN STATION TICK MARK SETTINGS TEXT BOXES
   PopulateLevelBox SymbolsLevelComboBox, SECTION_STATION_TEXT, KEY_LEVEL2
   PopulateColorBox SymbolsColorComboBox, SECTION_STATION_TEXT, KEY_COLOR2
   PopulateLinestyleBox SymbolsStyleComboBox, SECTION_STATION_TEXT, KEY_STYLE2
   PopulateWeightBox SymbolsWeightComboBox, SECTION_STATION_TEXT, KEY_WEIGHT2
   
'INITIALIZE STATION TEXTBOXES
   StartTextBox.MaxLength = MAX_LEN_STA_STRING
   EndTextBox.MaxLength = MAX_LEN_STA_STRING

'INITIALIZE STATUS AREA
   initializeStatus

'INITIALIZE START AT STATION TEXT BOX
   StartTextBox.text = ""

'INITIALIZE END AT STATION TEXT BOX
   EndTextBox.text = ""

'INITIALIZE GLOBAL VARIABLE
   theBeginStation = ""
   FlagInvalidElement
   doNotCloseYet = False

'MAKE SURE COMMAND NAME IS CORRECT
   Me.Caption = COMMAND_NAME_STATION_TEXT

'BRING FIRST PAGE TO FOREGROUND
   Me.MultiPage1.value = 0

'MOVE INTO LAST POSITION
   If GetSetting(APP_NAME, SECTION_STATION_TEXT, KEY_START_TOP, "") = "" Then
      Me.StartUpPosition = 1
   Else
      Me.StartUpPosition = 0
      Me.Top = CDbl(GetSetting(APP_NAME, SECTION_STATION_TEXT, KEY_START_TOP, WINDOW_DEFAULT_TOP))
      Me.Left = CDbl(GetSetting(APP_NAME, SECTION_STATION_TEXT, KEY_START_LEFT, WINDOW_DEFAULT_LEFT))
   End If
   
'START UP LOCATE COMMAND FOR PICKING BASELINE SEGMENTS
   CommandState.StartLocate New StationTextLocate
End Sub



Private Sub UserForm_QueryClose(Cancel As Integer, CloseMode As Integer)
'SAVE USERFORM POSITION
   SaveSetting APP_NAME, SECTION_STATION_TEXT, KEY_START_TOP, FormatNumber(Me.Top, 2)
   SaveSetting APP_NAME, SECTION_STATION_TEXT, KEY_START_LEFT, FormatNumber(Me.Left, 2)
End Sub



Private Sub UserForm_Terminate()
'CLOSE ILOCATECOMMANDEVENTS
   CommandState.StartDefaultCommand
End Sub



'*************************************************************************************************************
'**********************************************STATUS DISPLAY*************************************************
Private Sub updateStatusDisplay(ByVal theElement As Element, ByVal IDstring As String, ByVal length As Double)
'CLEAR STATUS
   initializeStatus
   
'CHECK IF FLAGGED INVALID
   If Not isValidElement Then
      Exit Sub
   End If

'DISPLAY ELEMENT TYPE
   If theElement.IsLineElement Then
      If theElement.Type = msdElementTypeLineString Then
         ElementTypeDisplayLabel.Caption = "spiral"
      Else
         ElementTypeDisplayLabel.Caption = "line"
      End If
   ElseIf theElement.IsArcElement Then
      ElementTypeDisplayLabel.Caption = "curve"
   End If

'DISPLAY THE REST OF THE METRICS
   ElementIDDisplayLabel.Caption = IDstring
   ElementLengthDisplayLabel.Caption = FormatNumber(length, 2)
   BeginStationDisplayLabel.Caption = theBeginStation
   Dim EndingStation As Double
   If Not calcEndStationOfElement(EndingStation) Then
      FlagInvalidElement
      Exit Sub
   End If
   EndStationDisplayLabel.Caption = StationToString(Round(EndingStation, linearPrecisionGlobal), linearPrecisionGlobal, entryStationStyleGlobal)
End Sub



Private Sub initializeStatus()
'BLANK OUT STATUS FIELDS
   ElementIDDisplayLabel.Caption = ""
   ElementTypeDisplayLabel.Caption = ""
   ElementLengthDisplayLabel.Caption = ""
   BeginStationDisplayLabel.Caption = ""
   EndStationDisplayLabel.Caption = ""
End Sub



'*************************************************************************************************************
'************************************************TEMPLATES****************************************************
Private Function OtherTextTemplate() As TextElement
   Set OtherTextTemplate = CreateTextTemplate(SECTION_STATION_TEXT, _
                                              OtherTextFontComboBox, _
                                              KEY_FONT, _
                                              OtherTextLevelComboBox, _
                                              KEY_LEVEL, _
                                              OtherTextWeightComboBox, _
                                              OtherTextColorComboBox, _
                                              OtherTextStyleComboBox, _
                                              KEY_STYLE)
End Function



Private Function SymbolsLineTemplate() As LineElement
   Set SymbolsLineTemplate = CreateLineTemplate(SECTION_STATION_TEXT, _
                                                   SymbolsLevelComboBox, _
                                                   KEY_LEVEL2, _
                                                   SymbolsWeightComboBox, _
                                                   SymbolsColorComboBox, _
                                                   SymbolsStyleComboBox, _
                                                   KEY_STYLE2)
End Function



'*************************************************************************************************************
'*************************************************METRICS*****************************************************
Private Function GetElementMetrics(TheChosenElement As Element) As Boolean
'TRUE IF NO PROBLEM
'INITIALIZE FLAG
   GetElementMetrics = False

'GET THE ELEMENT ID
   Dim ID As DLong
   Dim IDstring As String
   If Not GetTheElementID(TheChosenElement, ID, IDstring) Then
      Exit Function
   End If
   ThePickedID = ID
   ThePickedIDString = IDstring

'GET THE BASELINE INFO
   Dim theValue As Variant
   If Not GetSurveyorToolsTagValue(TheChosenElement, TAG_NAME_BEGIN_STATION, theValue) Then
      Exit Function
   End If
   theBeginStation = theValue

'GET TREATED AS AN ARC
   If TheChosenElement.IsArcElement Then
      Dim TempArc As ArcElement
      Set TempArc = TheChosenElement
      thePickedLength = TempArc.length
      theStartPoint = TempArc.startPoint
      theEndPoint = TempArc.endPoint
      theRadiusPoint = TempArc.CenterPoint
      theSweepAngle = TempArc.SweepAngle
   End If

   If TheChosenElement.IsLineElement Then
      If TheChosenElement.Type = msdElementTypeLineString Then
'TREAT IT AS A SPIRAL
'GET THE LENGTH
         Dim spiralLengthString As String
         If Not GetSurveyorToolsTagValue(TheChosenElement, TAG_NAME_LENGTH, spiralLengthString) Then
            Exit Function
         End If
         thePickedLength = CDbl(spiralLengthString)
         theStartPoint = TheChosenElement.AsLineElement.startPoint
         theEndPoint = TheChosenElement.AsLineElement.endPoint
      Else
'GET TREATED AS A LINE
         Dim tempLine As LineElement
         Set tempLine = TheChosenElement
         thePickedLength = tempLine.length
         theStartPoint = tempLine.startPoint
         theEndPoint = tempLine.endPoint
      End If
   End If
   
'SUCCESS, RETURN TRUE
   GetElementMetrics = True
End Function



Private Function VerifyElementDidNotMove(theElement As Element) As Boolean
'RETURNS TRUE IF DID NOT CHANGE
'INITIALIZE FLAG
   VerifyElementDidNotMove = False
      
'CHECK THE BEGIN STATION
   Dim TagValue As Variant
   If Not GetSurveyorToolsTagValue(theElement, TAG_NAME_BEGIN_STATION, TagValue) Then
      Exit Function
   End If
   If TagValue <> theBeginStation Then
      Exit Function
   End If
   
'USE APPROPRIATE SUBROUTINE FOR TYPE OF ELEMENT
   If theElement.IsArcElement Then
      Dim theArc As ArcElement
      Set theArc = theElement
      VerifyElementDidNotMove = DoArcChecks(theArc)
   ElseIf theElement.IsLineElement Then
      Dim theLine As LineElement
      Set theLine = theElement
      VerifyElementDidNotMove = DoLineChecks(theLine)
   End If
End Function



Private Function DoArcChecks(ByVal theArc As ArcElement) As Boolean
'CHECK FOR CHANGES OF AN ARC ELEMENT, RETURNS TRUE IF NO CHANGE
'INITIALIZE FLAG
   DoArcChecks = False

'CHECK IF THE RADIUS POINT CHANGED
   If Not PointsAreExactlySame(theArc.CenterPoint, theRadiusPoint) Then
      Exit Function
   End If

'CHECK IF THE START POINT CHANGED
   If Not PointsAreExactlySame(theArc.startPoint, theStartPoint) Then
      Exit Function
   End If

'CHECK IF THE END POINT CHANGED
   If Not PointsAreExactlySame(theArc.endPoint, theEndPoint) Then
      Exit Function
   End If

'CHECK IF THE SWEEP ANGLE CHANGED
   If theArc.SweepAngle <> theSweepAngle Then
      Exit Function
   End If

'CHECK IF THE LENGTH CHANGED
   If theArc.length <> thePickedLength Then
      Exit Function
   End If

'NO CHANGE, RETURN TRUE
   DoArcChecks = True
End Function



Private Function DoLineChecks(ByVal theLine As LineElement) As Boolean
'CHECK FOR CHANGES OF AN ARC ELEMENT, RETURNS TRUE IF NO CHANGE
'INITIALIZE FLAG
   DoLineChecks = False

'CHECK IF THE START POINT CHANGED
   If Not PointsAreExactlySame(theLine.startPoint, theStartPoint) Then
      Exit Function
   End If

'CHECK IF THE END POINT CHANGED
   If Not PointsAreExactlySame(theLine.endPoint, theEndPoint) Then
      Exit Function
   End If

'NO CHANGE, RETURN TRUE
   DoLineChecks = True
End Function



'*************************************************************************************************************
'*********************************************FILE OPERATIONS*************************************************
Private Sub WriteStationSettingsFile(ByVal FreeFileNum As Long)
'JUMP ON ERROR
   On Error GoTo errhnd

'WRITE HEADER
   Print #FreeFileNum, FILE_STATION_TEXT_FILE_HEADER

'WRITE SETTINGS
   Print #FreeFileNum, getFontScaleRecord()
   Print #FreeFileNum, getOffsetTransverseRecord()
   Print #FreeFileNum, getOffsetTransverseOptionRecord()
   Print #FreeFileNum, getOffsetLongitudinalRecord()
   Print #FreeFileNum, getOffsetLongitudinalOptionRecord()
   Print #FreeFileNum, getPlusZeroZeroOptionRecord()
   Print #FreeFileNum, getOrientationRecord()
   Print #FreeFileNum, getIntervalRecord()
   Print #FreeFileNum, getJustificationRecord()
   Print #FreeFileNum, getTicksLeftRecord()
   Print #FreeFileNum, getTicksRightRecord()
   Print #FreeFileNum, getTicksScaleLeftRecord()
   Print #FreeFileNum, getTicksScaleRightRecord()

   If OtherTextLevelComboBox.listIndex <> -1 Then
      Print #FreeFileNum, FILE_STATION_TEXT_SETTING_LEVEL & OtherTextLevelComboBox.text
   End If
   If OtherTextColorComboBox.listIndex <> -1 Then
      Print #FreeFileNum, FILE_STATION_TEXT_SETTING_COLOR & OtherTextColorComboBox.text
   End If
   If OtherTextStyleComboBox.listIndex <> -1 Then
      Print #FreeFileNum, FILE_STATION_TEXT_SETTING_STYLE & OtherTextStyleComboBox.text
   End If
   If OtherTextWeightComboBox.listIndex <> -1 Then
      Print #FreeFileNum, FILE_STATION_TEXT_SETTING_WEIGHT & OtherTextWeightComboBox.text
   End If
   If OtherTextFontComboBox.listIndex <> -1 Then
      Print #FreeFileNum, FILE_STATION_TEXT_SETTING_FONT & OtherTextFontComboBox.text
   End If

   If SymbolsLevelComboBox.listIndex <> -1 Then
      Print #FreeFileNum, FILE_STATION_TICK_SETTING_LEVEL & SymbolsLevelComboBox.text
   End If
   If SymbolsColorComboBox.listIndex <> -1 Then
      Print #FreeFileNum, FILE_STATION_TICK_SETTING_COLOR & SymbolsColorComboBox.text
   End If
   If SymbolsStyleComboBox.listIndex <> -1 Then
      Print #FreeFileNum, FILE_STATION_TICK_SETTING_STYLE & SymbolsStyleComboBox.text
   End If
   If SymbolsWeightComboBox.listIndex <> -1 Then
      Print #FreeFileNum, FILE_STATION_TICK_SETTING_WEIGHT & SymbolsWeightComboBox.text
   End If

'JUMP PAST ERROR CODE
   Exit Sub

'ERROR HANDLING
errhnd:
   ErrorMess Err.Number
   Err.Clear
End Sub



Private Function getFontScaleRecord() As String
'CREATES RECORD FOR THE FONT SCALE
   getFontScaleRecord = FILE_STATION_TEXT_REC_FONT_SCALE & FontScaleTextBox.text
End Function



Private Function getOffsetTransverseRecord() As String
'CREATES THE RECORD FOR TRANSVERSE OFFSET
   getOffsetTransverseRecord = FILE_STATION_TEXT_REC_OFFSET_TRANSVERSE & TransverseTextBox.text
End Function



Private Function getOffsetTransverseOptionRecord() As String
'CREATES THE RECORD FOR TRANSVERSE OFFSET OPTION
   If OptionLeft.value = True Then
      getOffsetTransverseOptionRecord = FILE_STATION_TEXT_REC_OFFSET_TRANSVERSE_OPTION & FILE_OPTION_OFFSET_TRANSVERSE_LEFT
   Else
      getOffsetTransverseOptionRecord = FILE_STATION_TEXT_REC_OFFSET_TRANSVERSE_OPTION & FILE_OPTION_OFFSET_TRANSVERSE_RIGHT
   End If
End Function



Private Function getOffsetLongitudinalRecord() As String
'CREATES THE RECORD FOR LONGITUDINAL OFFSET
   getOffsetLongitudinalRecord = FILE_STATION_TEXT_REC_OFFSET_LONGITUDINAL & LongitudinalTextBox.text
End Function



Private Function getOffsetLongitudinalOptionRecord() As String
'CREATES THE RECORD FOR LONGITUDINAL OFFSET OPTION
   If OptionAhead.value = True Then
      getOffsetLongitudinalOptionRecord = FILE_STATION_TEXT_REC_OFFSET_LONGITUDINAL_OPTION & FILE_OPTION_OFFSET_LONGITUDINAL_AHEAD
   Else
      getOffsetLongitudinalOptionRecord = FILE_STATION_TEXT_REC_OFFSET_LONGITUDINAL_OPTION & FILE_OPTION_OFFSET_LONGITUDINAL_BACK
   End If
End Function



Private Function getPlusZeroZeroOptionRecord() As String
'CREATES THE RECORD FOR "+00" OPTION
   If Plus00CheckBox.value = True Then
      getPlusZeroZeroOptionRecord = FILE_STATION_TEXT_REC_PLUS_ZERO_ZERO & FILE_OPTION_IS_CHECKED
   Else
      getPlusZeroZeroOptionRecord = FILE_STATION_TEXT_REC_PLUS_ZERO_ZERO & FILE_OPTION_NOT_CHECKED
   End If
End Function



Private Function getOrientationRecord() As String
'CREATES THE RECORD FOR ORIENTATION OPTION
   If OptionTopToLeft.value = True Then
      getOrientationRecord = FILE_STATION_TEXT_REC_ORIENTATION & FILE_OPTION_ORIENTATION_LEFT
   ElseIf OptionTopToRight.value = True Then
      getOrientationRecord = FILE_STATION_TEXT_REC_ORIENTATION & FILE_OPTION_ORIENTATION_RIGHT
   ElseIf OptionTopForward.value = True Then
      getOrientationRecord = FILE_STATION_TEXT_REC_ORIENTATION & FILE_OPTION_ORIENTATION_FORWARD
   ElseIf OptionTopBack.value = True Then
      getOrientationRecord = FILE_STATION_TEXT_REC_ORIENTATION & FILE_OPTION_ORIENTATION_BACK
   End If
End Function



Private Function getIntervalRecord() As String
'CREATES THE RECORD FOR INTERVAL OPTION
   If Option100foot.value = True Then
      getIntervalRecord = FILE_STATION_TEXT_REC_INTERVAL & FILE_OPTION_INTERVAL_100
   Else
      getIntervalRecord = FILE_STATION_TEXT_REC_INTERVAL & FILE_OPTION_INTERVAL_500
   End If
End Function



Private Function getJustificationRecord() As String
'CREATES THE RECORD FOR JUSTIFICATION OPTION
   If OptionRightJustified.value = True Then
      getJustificationRecord = FILE_STATION_TEXT_REC_JUSTIFICATION & FILE_OPTION_JUSTIFICATION_RIGHT
   ElseIf OptionCenterJustified.value = True Then
      getJustificationRecord = FILE_STATION_TEXT_REC_JUSTIFICATION & FILE_OPTION_JUSTIFICATION_CENTER
   Else
      getJustificationRecord = FILE_STATION_TEXT_REC_JUSTIFICATION & FILE_OPTION_JUSTIFICATION_LEFT
   End If
End Function



Private Function getTicksLeftRecord() As String
'CREATES THE RECORD FOR TICKS LEFT OPTION SETTING
   If CheckBoxLeft.value = True Then
      getTicksLeftRecord = FILE_STATION_TEXT_REC_TICKS_LEFT & FILE_OPTION_IS_CHECKED
   Else
      getTicksLeftRecord = FILE_STATION_TEXT_REC_TICKS_LEFT & FILE_OPTION_NOT_CHECKED
   End If
End Function



Private Function getTicksRightRecord() As String
'CREATES THE RECORD FOR TICKS LEFT OPTION SETTING
   If CheckBoxRight.value = True Then
      getTicksRightRecord = FILE_STATION_TEXT_REC_TICKS_RIGHT & FILE_OPTION_IS_CHECKED
   Else
      getTicksRightRecord = FILE_STATION_TEXT_REC_TICKS_RIGHT & FILE_OPTION_NOT_CHECKED
   End If
End Function



Private Function getTicksScaleLeftRecord() As String
'CREATES THE RECORD FOR TICKS LEFT OPTION SETTING
   getTicksScaleLeftRecord = FILE_STATION_TEXT_REC_SCALE_LEFT & TickScaleLeftTextBox.text
End Function



Private Function getTicksScaleRightRecord() As String
'CREATES THE RECORD FOR TICKS LEFT OPTION SETTING
   getTicksScaleRightRecord = FILE_STATION_TEXT_REC_SCALE_RIGHT & TickScaleRightTextBox.text
End Function



Private Function CreateNewStationTextFile(OutputFilename As String) As Boolean
'RETURNS TRUE IF SUCCESSFUL
'JUMP ON ERROR
   On Error GoTo errhnd

'OPEN FILE
   Dim FreeFileNum As Long
   FreeFileNum = FreeFile
   Open OutputFilename For Output As #FreeFileNum

'WRITE SETTINGS TO FILE
   WriteStationSettingsFile FreeFileNum

'CLOSE FILE
   Close FreeFileNum

'SET FLAG
   CreateNewStationTextFile = True

'JUMP PAST ERROR CODE
   Exit Function

'ERROR HANDLING
errhnd:
   CreateNewStationTextFile = False
   ErrorMess Err.Number
   Err.Clear
End Function



Private Function GetSuggestedPath() As String
'CREATE A DEFAULT PATH NAME IN CASE THERE IS NO PREVIOUS FILE
   Dim DefaultFilename As String
   DefaultFilename = "C:\StationTextSettings" & FILE_STATION_TEXT_FILE_EXTENSION
   
'LOOK IN SETTINGS FOR PREVIOUS FILE WITH PATH
   Dim FilePath As String
   FilePath = GetSetting(APP_NAME, SECTION_STATION_TEXT, KEY_FILENAME, DefaultFilename)
   
'SEPARATE PATH AND FILENAME
   Dim xSplit2 As Variant
   xSplit2 = Split(FilePath, "\")
   xSplit2(UBound(xSplit2)) = ""
   Dim NewTextFilePath As String
   NewTextFilePath = Join(xSplit2, "\")
   
'RETURN PATH
   GetSuggestedPath = NewTextFilePath
End Function



Private Function SaveAsStationTextFile() As Boolean
'RETURNS TRUE IF SUCCESSFUL
'INITIALIZE FLAG
   SaveAsStationTextFile = False

'GET SUGGESTED PATH
   Dim NewTextFilePath As String
   NewTextFilePath = GetSuggestedPath()

'CREATE FILTER STRING
   Dim FilterString As String
   FilterString = "*" & FILE_STATION_TEXT_FILE_EXTENSION

'CALL COMMON DIALOG
   Dim strFName As String
   strFName = space(255)
   Dim retVal As Long
   Dim lngfhandle As Long
   Dim lngrid As Long
   retVal = mdlDialog_fileCreate(strFName, lngfhandle, lngrid, "", FilterString, NewTextFilePath, "Save As")
   Select Case retVal
      Case 0 'Open
         strFName = Left(strFName, InStr(1, strFName, Chr(0)) - 1)
         If CreateNewStationTextFile(strFName) Then
            SaveSetting APP_NAME, SECTION_STATION_TEXT, KEY_FILENAME, strFName
            SaveAsStationTextFile = True
         End If
      Case 1 'Cancel
           'MsgBox "No File Selected."
           'User hit the Cancel Button
   End Select
End Function



Private Function LoadStationTextFile(OPENFILENAME As String) As Boolean
'RETURNS TRUE IF SUCESSFUL, AND FILENAME
'INITIALIZE FLAG
   LoadStationTextFile = False

'CREATE FILTER STRING
   Dim FilterString As String
   FilterString = "*" & FILE_STATION_TEXT_FILE_EXTENSION

'GET SUGGESTED PATH
   Dim NewTextFilePath As String
   NewTextFilePath = GetSuggestedPath()

'CALL COMMON DIALOG
   Dim strFName As String
   strFName = space(255)
   Dim lngfhandle As Long
   Dim lngrid As Long
   Dim retVal As Long
   retVal = mdlDialog_fileOpen(strFName, lngfhandle, lngrid, _
                               "", FilterString, NewTextFilePath, "Load File")
   Select Case retVal
      Case 0 'OPEN
         strFName = Left(strFName, InStr(1, strFName, Chr(0)) - 1)
         OPENFILENAME = strFName
         LoadStationTextFile = True
      Case 1 'Cancel, no action

   End Select
End Function



Private Sub LoadSettingsFromFile(ByVal filename As String)
'JUMP ON ERROR
   On Error GoTo errhnd

'OPEN FILE
   Dim FreeFileNum As Long
   FreeFileNum = FreeFile
   Open filename For Input As #FreeFileNum

'READ EACH LINE IN FILE
   Dim TextLine As String
   While EOF(FreeFileNum) = False
      Line Input #FreeFileNum, TextLine
      ProcessSettingRecord TextLine
   Wend
   
'CLOSE FILE
   Close FreeFileNum

'JUMP PAST ERROR CODE
   Exit Sub

'ERROR HANDLING
errhnd:
   ErrorMess Err.Number
   Err.Clear
End Sub



Private Sub ProcessSettingRecord(InputRecord As String)
'SET SETTINGS ACCORDING TO RECORD STRING
'SPLIT STRING INTO KEY AND DATA
   Dim Key As String
   Dim Data As String
   If Not SplitRecord2(InputRecord, Key, Data) Then
      Exit Sub
   End If

'DISTRIBUTE ACCORDINGLY
   Select Case Key
      Case FILE_STATION_TEXT_REC_FONT_SCALE
         ProcessFontScale Data
      Case FILE_STATION_TEXT_REC_OFFSET_TRANSVERSE
         ProcessOffsetTransverse Data
      Case FILE_STATION_TEXT_REC_OFFSET_TRANSVERSE_OPTION
         ProcessOffsetTransverseOption Data
      Case FILE_STATION_TEXT_REC_OFFSET_LONGITUDINAL
         ProcessOffsetLongitudinal Data
      Case FILE_STATION_TEXT_REC_OFFSET_LONGITUDINAL_OPTION
         ProcessOffsetLongitudinalOption Data
      Case FILE_STATION_TEXT_REC_PLUS_ZERO_ZERO
         ProcessPlusZeroZero Data
      Case FILE_STATION_TEXT_REC_ORIENTATION
         ProcessOrientation Data
      Case FILE_STATION_TEXT_REC_INTERVAL
         ProcessInterval Data
      Case FILE_STATION_TEXT_REC_JUSTIFICATION
         ProcessJustification Data
      Case FILE_STATION_TEXT_REC_TICKS_LEFT
         ProcessTicksOnLeft Data
      Case FILE_STATION_TEXT_REC_TICKS_RIGHT
         ProcessTicksOnRight Data
      Case FILE_STATION_TEXT_REC_SCALE_LEFT
         ProcessTickScaleLeft Data
      Case FILE_STATION_TEXT_REC_SCALE_RIGHT
         ProcessTickScaleRight Data
      Case FILE_STATION_TEXT_SETTING_LEVEL
         ProcessTextLevel Data
      Case FILE_STATION_TEXT_SETTING_COLOR
         ProcessTextColor Data
      Case FILE_STATION_TEXT_SETTING_STYLE
         ProcessTextLinestyle Data
      Case FILE_STATION_TEXT_SETTING_WEIGHT
         ProcessTextWeight Data
      Case FILE_STATION_TEXT_SETTING_FONT
         ProcessTextFont Data
      Case FILE_STATION_TICK_SETTING_LEVEL
         ProcessTickLevel Data
      Case FILE_STATION_TICK_SETTING_COLOR
         ProcessTickColor Data
      Case FILE_STATION_TICK_SETTING_STYLE
         ProcessTickLinestyle Data
      Case FILE_STATION_TICK_SETTING_WEIGHT
         ProcessTickWeight Data
   End Select
End Sub



Private Sub ProcessFontScale(Data As String)
'PROCESS LOAD DATA FOR FONT SCALE
   FontScaleTextBox.text = Data
   FontScaleTextBox_AfterUpdate
End Sub



Private Sub ProcessOffsetTransverse(Data As String)
'PROCESS LOAD DATA FOR THE TRANSVERSE OFFSET
   TransverseTextBox.text = Data
   TransverseTextBox_AfterUpdate
End Sub



Private Sub ProcessOffsetTransverseOption(Data As String)
'PROCESS THE DATA FOR THE TRANSVERSE OFFSET OPTIONS
   Select Case Data
      Case FILE_OPTION_OFFSET_TRANSVERSE_LEFT
         OptionLeft.value = True
      Case FILE_OPTION_OFFSET_TRANSVERSE_RIGHT
         OptionRight.value = True
   End Select
End Sub



Private Sub ProcessOffsetLongitudinal(Data As String)
'PROCESS LOAD DATA FOR THE LONGITUDINAL OFFSET
   LongitudinalTextBox.text = Data
   LongitudinalTextBox_AfterUpdate
End Sub



Private Sub ProcessOffsetLongitudinalOption(Data As String)
'PROCESS THE DATA FOR THE LONGITUDINAL OFFSET OPTIONS
   Select Case Data
      Case FILE_OPTION_OFFSET_LONGITUDINAL_AHEAD
         OptionAhead.value = True
      Case FILE_OPTION_OFFSET_LONGITUDINAL_BACK
         OptionBack.value = True
   End Select
End Sub



Private Sub ProcessPlusZeroZero(Data As String)
'PROCESS THE DATA FOR PLUS ZERO ZERO OPTION CHECK BOX
   Select Case Data
      Case FILE_OPTION_IS_CHECKED
         Plus00CheckBox.value = True
      Case FILE_OPTION_NOT_CHECKED
         Plus00CheckBox.value = False
   End Select
End Sub



Private Sub ProcessOrientation(Data As String)
'PROCESS THE DATA FOR THE ORIENTATION RADIO BUTTONS
   Select Case Data
      Case FILE_OPTION_ORIENTATION_LEFT
         OptionTopToLeft.value = True
      Case FILE_OPTION_ORIENTATION_RIGHT
         OptionTopToRight.value = True
      Case FILE_OPTION_ORIENTATION_FORWARD
         OptionTopForward.value = True
      Case FILE_OPTION_ORIENTATION_BACK
         OptionTopBack.value = True
   End Select
End Sub



Private Sub ProcessInterval(Data As String)
'PROCESS THE DATA FOR THE INTERVAL RADIO BUTTONS
   Select Case Data
      Case FILE_OPTION_INTERVAL_100
         Option100foot.value = True
      Case FILE_OPTION_INTERVAL_500
         Option500foot.value = True
   End Select
End Sub



Private Sub ProcessJustification(Data As String)
'PROCESS THE DATA FOR THE JUSTIFICATION RADIO BUTTONS
   Select Case Data
      Case FILE_OPTION_JUSTIFICATION_RIGHT
         OptionRightJustified.value = True
      Case FILE_OPTION_JUSTIFICATION_CENTER
         OptionCenterJustified.value = True
      Case FILE_OPTION_JUSTIFICATION_LEFT
         OptionLeftJustified.value = True
   End Select
End Sub



Private Sub ProcessTicksOnLeft(Data As String)
'PROCESS THE DATA FOR TICKS ON LEFT OPTION CHECK BOX
   Select Case Data
      Case FILE_OPTION_IS_CHECKED
         CheckBoxLeft.value = True
         TickScaleLeftStates
      Case FILE_OPTION_NOT_CHECKED
         CheckBoxLeft.value = False
         TickScaleLeftStates
   End Select
End Sub



Private Sub ProcessTicksOnRight(Data As String)
'PROCESS THE DATA FOR TICKS ON RIGHT OPTION CHECK BOX
   Select Case Data
      Case FILE_OPTION_IS_CHECKED
         CheckBoxRight.value = True
         TickScaleRightStates
      Case FILE_OPTION_NOT_CHECKED
         CheckBoxRight.value = False
         TickScaleRightStates
   End Select
End Sub



Private Sub ProcessTickScaleLeft(Data As String)
'PROCESS LOAD DATA FOR THE LEFT TICK SCALE
   TickScaleLeftTextBox.text = Data
   TickScaleLeftTextBox_AfterUpdate
End Sub



Private Sub ProcessTickScaleRight(Data As String)
'PROCESS LOAD DATA FOR THE RIGHT TICK SCALE
   TickScaleRightTextBox.text = Data
   TickScaleRightTextBox_AfterUpdate
End Sub



Private Sub ProcessTextLevel(Data As String)
'PROCESS LOAD DATA FOR THE STATION TEXT LEVEL
   OtherTextLevelComboBox.text = Data
   OtherTextLevelComboBox_AfterUpdate
End Sub



Private Sub ProcessTextColor(Data As String)
'PROCESS LOAD DATA FOR THE STATION TEXT COLOR
   OtherTextColorComboBox.text = Data
   OtherTextColorComboBox_AfterUpdate
End Sub



Private Sub ProcessTextLinestyle(Data As String)
'PROCESS LOAD DATA FOR THE STATION TEXT LINESTYLE
   OtherTextStyleComboBox.text = Data
   OtherTextStyleComboBox_AfterUpdate
End Sub



Private Sub ProcessTextWeight(Data As String)
'PROCESS LOAD DATA FOR THE STATION TEXT WEIGHT
   OtherTextWeightComboBox.text = Data
   OtherTextWeightComboBox_AfterUpdate
End Sub



Private Sub ProcessTextFont(Data As String)
'PROCESS LOAD DATA FOR THE STATION TEXT WEIGHT
   OtherTextFontComboBox.text = Data
   OtherTextFontComboBox_AfterUpdate
End Sub



Private Sub ProcessTickLevel(Data As String)
'PROCESS LOAD DATA FOR THE STATION TEXT LEVEL
   SymbolsLevelComboBox.text = Data
   SymbolsLevelComboBox_AfterUpdate
End Sub



Private Sub ProcessTickColor(Data As String)
'PROCESS LOAD DATA FOR THE STATION TEXT COLOR
   SymbolsColorComboBox.text = Data
   SymbolsColorComboBox_AfterUpdate
End Sub



Private Sub ProcessTickLinestyle(Data As String)
'PROCESS LOAD DATA FOR THE STATION TEXT LINESTYLE
   SymbolsStyleComboBox.text = Data
   SymbolsStyleComboBox_AfterUpdate
End Sub



Private Sub ProcessTickWeight(Data As String)
'PROCESS LOAD DATA FOR THE STATION TEXT WEIGHT
   SymbolsWeightComboBox.text = Data
   SymbolsWeightComboBox_AfterUpdate
End Sub



'*************************************************************************************************************
'**************************************DRAWING THE TEXT AND TICK MARKS****************************************
Private Function calcEndStationOfElement(ByRef EndingStation As Double) As Boolean
'CALCULATE THE ENDING STATION OF THE BASELINE
'RETURNS TRUE IF SUCESSFUL,
'INITIALIZE FLAG
   calcEndStationOfElement = False
   
'CONVERT BEGINNING STATION STRING TO DOUBLE, EXIT IF CANNOT
   Dim BeginStationDouble As Double
   Dim origPrec As Long
   If Not IsStationString(theBeginStation, BeginStationDouble, origPrec, entryStationStyleGlobal) Then
      Exit Function
   End If
   EndingStation = Round(thePickedLength, linearPrecisionGlobal) + Round(BeginStationDouble, linearPrecisionGlobal)
   calcEndStationOfElement = True
End Function



Public Sub DoTheTextingAndTicks(theElement As Element)
'/*******************************************************************/
'/* THIS ADDITIONAL CHECKING WAS DONE BECAUSE ORIGINALLY THE DIALOG */
'/* BOX HAD A PICK BUTTON FOR CHOOSING THE BASELINE ELEMENT.  THE   */
'/* CODE FOR CHECK REMAINS IN PLACE JUST IN CASE IT IS DECIDED TO   */
'/* REIMPLEMENT THE PICK BUTTON AGAIN.                              */
'/*******************************************************************/

'MAKE SURE DID NOT DELETE ELEMENT
   If Not theElement.IsValid Then
      FlagInvalidElement
      MsgBox "ELEMENT UNAVAILABLE"
      Exit Sub
   End If

'MAKE SURE NOT READ ONLY FILE
   If ActiveModelReference.IsReadOnly = True Then
      ReadOnlyErrorMess
      Exit Sub
   End If

'VERIFY THE ELEMENT HAS NOT MOVED SINCE PICKED
   If Not VerifyElementDidNotMove(theElement) Then
'IF DID CHANGE AND NOT VALID
      FlagInvalidElement
      MsgBox "ELEMENT CHANGED"
      Exit Sub
   End If

'CHECK IF STATION IS ENTERED IN THE "START AT STATION" BOX
   Dim StartStationDouble As Double
   Dim origPrec As Long
   
   If Not IsStationString(StartTextBox.text, _
                          StartStationDouble, _
                          origPrec, _
                          entryStationStyleGlobal) Then
      MsgBox "Need a Starting Station"
      Exit Sub
   End If

'CHECK IF STATION IS ENTERED IN THE "END AT STATION" BOX
   Dim EndStationDouble As Double
   If Not IsStationString(EndTextBox.text, _
                          EndStationDouble, _
                          origPrec, _
                          entryStationStyleGlobal) Then
      MsgBox "Need an Ending Station"
      Exit Sub
   End If

'OKAY, DRAW IT
   DrawTheStationingText theElement, StartStationDouble, EndStationDouble
   DrawTheStationingTickMarks theElement, StartStationDouble, EndStationDouble
   
'RESET FOR UNDO TO WORK
   doNotCloseYet = True
   CommandState.StartLocate New StationTextLocate
   doNotCloseYet = False
End Sub



Private Sub DrawTheStationingText(ByVal BaselineElement As Element, ByVal beginStation As Double, ByVal endStation As Double)
'SUBROUTINE FOR DRAWING THE STATIONING TEXT FOR THE BASELINE ELEMENTS
'ROUND ENDSTATION FOR CONSISTENT LOOP END
   endStation = Round(endStation, 2)
   
'GET INCREMENT AND STARTING STATION FOR STATIONING LOOP
   Dim Incr As Double
   Dim index As Double
   If Option100foot.value = True Then
      Incr = 100
      index = FirstEven100Station(beginStation)
   Else
      Incr = 500
      index = FirstEven500Station(beginStation)
   End If

'CONVERT ELEMENT BEGIN STATION STRING TO DOUBLE
   Dim ElementBeginStation As Double
   Dim origPrec As Long
   If Not IsStationString(theBeginStation, ElementBeginStation, origPrec, entryStationStyleGlobal) Then
      MsgBox "ERROR ENCOUNTERED"
      Exit Sub
   End If

'DELETE PREVIOUS STATION TEXT WITHIN RANGE
   DeletePreviousStationElements msdElementTypeText, ThePickedIDString, beginStation, endStation

'CREATE TEMPLATE FOR THE TEXT
   Dim template As TextElement
   Set template = OtherTextTemplate()

'LOOP THROUGH ALL THE STATIONS TO BE TEXTED
   Do While index <= endStation
      DrawTheStationText index, BaselineElement, ElementBeginStation, template
      index = Round(index + Incr, 2) 'INCREMENT LOOP
   Loop
End Sub



Private Sub DrawTheStationText(ByVal station As Double, _
                               ByVal Element As Element, _
                               ByVal ElementBeginStation As Double, _
                               ByVal template As Element)
'DRAW THE TEXT FOR A GIVEN STATION ALONG THE BASELINE ELEMENT
'GET POINT ON THE BASELINE AND THE FORWARD AZIMUTH IN DECIMAL DEGREES
   Dim BaselinePoint As Point3d
   Dim FwdAz As Double
   If Element.IsLineElement Then
      If Element.Type = msdElementTypeLineString Then
'CALCULATE FOR SPIRAL
         GetBasePntFwdAzSpiral station, Element, BaselinePoint, FwdAz
      Else
'CALCULATE FOR LINE ELEMENT
         GetBasePntFwdAzLine station, Element, ElementBeginStation, BaselinePoint, FwdAz
      End If
   Else
'CALCULATE FOR ARC ELEMENT
      GetBasePntFwdAzArc station, Element, ElementBeginStation, BaselinePoint, FwdAz
   End If

'GET INSERTION POINT FOR TEXT
   Dim InsertionPoint As Point3d
   InsertionPoint = CalcInsertionPoint(BaselinePoint, FwdAz)

'GENERATE THE TEXT
   Dim StationingString As String
   StationingString = StationToString(station, linearPrecisionGlobal, entryStationStyleGlobal)
   If Plus00CheckBox.value = False Then 'IF NOT CHECKED, THEN REMOVE THE "+00"
      StationingString = Replace(StationingString, "+00", "")
   End If

'CREATE THE TEXT ELEMENT
   Dim StationTextElement As TextElement
   Set StationTextElement = CreateTextElement1(template, StationingString, InsertionPoint, Matrix3dIdentity)

'ADJUST ITS PLACEMENT
   OrientTextElement StationTextElement, InsertionPoint, FwdAz
   SetTextJustification StationTextElement

'ADD IT TO THE DRAWAING
   ActiveModelReference.AddElement StationTextElement
   StationTextElement.Redraw

'ADD THE TAGS
   AddBaselineAutoDeleteTags StationTextElement, station, ThePickedIDString
End Sub



Private Sub DrawTheStationingTickMarks(ByVal BaselineElement As Element, ByVal beginStation As Double, ByVal endStation As Double)
'SUBROUTINE FOR DRAWING THE TICK MARKS FOR THE BASELINE ELEMENTS
'ROUND ENDSTATION FOR CONSISTENT LOOP END
   endStation = Round(endStation, 2)
   
'GET INCREMENT AND STARTING STATION FOR STATIONING LOOP
   Dim Incr As Double
   Incr = 100
   Dim index As Double
   index = FirstEven100Station(beginStation)

'CONVERT ELEMENT BEGIN STATION STRING TO DOUBLE
   Dim ElementBeginStation As Double
   Dim origPrec As Long
   If Not IsStationString(theBeginStation, ElementBeginStation, origPrec, entryStationStyleGlobal) Then
      MsgBox "ERROR ENCOUNTERED"
      Exit Sub
   End If

'DELETE PREVIOUS STATION TICK MARKS WITHIN RANGE
      DeletePreviousStationElements msdElementTypeLine, ThePickedIDString, beginStation, endStation

'LOOP THROUGH ALL THE STATIONS TO BE TEXTED
   Do While index <= endStation
      DrawTheStationTickMark index, BaselineElement, ElementBeginStation
      index = Round(index + Incr, 2) 'INCREMENT LOOP
   Loop
End Sub



Private Sub DrawTheStationTickMark(ByVal station As Double, _
                                   ByVal Element As Element, _
                                   ByVal ElementBeginStation As Double)
'DRAW THE TICK MARK/MARKS FOR A GIVEN STATION ALONG THE BASELINE ELEMENT
'GET POINT ON THE BASELINE AND THE FORWARD AZIMUTH IN DECIMAL DEGREES
   Dim BaselinePoint As Point3d
   Dim FwdAz As Double
   If Element.IsLineElement Then
      If Element.Type = msdElementTypeLineString Then
'CALCULATE FOR SPIRAL
         GetBasePntFwdAzSpiral station, Element, BaselinePoint, FwdAz
      Else
'CALCULATE FOR LINE ELEMENT
         GetBasePntFwdAzLine station, Element, ElementBeginStation, BaselinePoint, FwdAz
      End If
   Else
   'CALCULATE FOR ARC ELEMENT
      GetBasePntFwdAzArc station, Element, ElementBeginStation, BaselinePoint, FwdAz
   End If

'CREATE THE TICK ELEMENT/ELEMENTS
   Dim prototype As Element
   Set prototype = SymbolsLineTemplate()
'LEFT SIDE TICK MARK
   If CheckBoxLeft.value = True Then
      CreateTickMark prototype, BaselinePoint, FwdAz + 270, station, CDbl(TickScaleLeftTextBox.text)
   End If
'RIGHT SIDE TICK MARK
   If CheckBoxRight.value = True Then
      CreateTickMark prototype, BaselinePoint, FwdAz + 90, station, CDbl(TickScaleRightTextBox.text)
   End If
End Sub



Private Sub CreateTickMark(ByVal prototype As Element, _
                           InsertionPoint As Point3d, _
                           ByVal AzimuthDecimal As Double, _
                           ByVal station As Double, _
                           ByVal TheScalefactor As Double)
'CREATES AND ADD THE TICK MARKS TO THE DRAWING
'CALCULATE END POINT OF THE TICK
   Dim charSize As Double
   charSize = GetCharSize()
   Dim endOfTick As Point3d
   endOfTick = CoordFwdSAz(InsertionPoint, AzimuthDecimal, (charSize * TICK_SIZE) * TheScalefactor)
   
'CREATE THE LINE ELEMENT
   Dim TheTick As LineElement
   Set TheTick = CreateLineElement2(prototype, InsertionPoint, endOfTick)

'ADD IT TO THE DRAWAING
   ActiveModelReference.AddElement TheTick
   TheTick.Redraw

'ADD THE AUTO DELETE TAGS
   AddBaselineAutoDeleteTags TheTick, station, ThePickedIDString
End Sub



Private Sub DeletePreviousStationElements(ByVal ElementType As MsdElementType, _
                                          ByVal BaselineElementIDString As String, _
                                          ByVal startStation As Double, _
                                          ByVal endStation As Double)
'REMOVE PREVIOUS STATION TEXT ELEMENT FOR THIS STATION AND ELEMENT
'SCAN FILE FOR TEXT ELEMENTS
   Dim myFilter As New ElementScanCriteria
   myFilter.ExcludeAllTypes
   myFilter.IncludeType ElementType
   Dim myElemEnum As ElementEnumerator
   Set myElemEnum = Application.ActiveModelReference.Scan(myFilter)
   
'CYCLE THROUGH FOUND ELEMENTS, EXAMINE ONE WITH TAGS
   While myElemEnum.MoveNext
      Dim TheElem As Element
      Set TheElem = myElemEnum.Current
      If TheElem.HasAnyTags Then
         DeleteIfPreviousStationElement TheElem, BaselineElementIDString, startStation, endStation
      End If
   Wend
End Sub



Private Sub DeleteIfPreviousStationElement(ByVal TheElem As Element, _
                                           ByVal BaselineElementIDString As String, _
                                           ByVal startStation As Double, _
                                           ByVal endStation As Double)
'CHECK FOR THE CORRECT HOST ELEMENT TAG
   Dim TheTagVal As Variant
   If Not CheckForSurveyorToolsTagAndVal(TheElem, TAG_NAME_HOST_ID, TheTagVal) Then
      Exit Sub
   End If
   If BaselineElementIDString <> TheTagVal Then
      Exit Sub
   End If

'CHECK FOR THE STATION TAG AND CORRECT RANGE
   If Not CheckForSurveyorToolsTagAndVal(TheElem, TAG_NAME_STATION, TheTagVal) Then
      Exit Sub
   End If
   Dim TheStation As Double
   Dim origPrec As Long
   If Not IsStationString(TheTagVal, TheStation, origPrec, entryStationStyleGlobal) Then
      Exit Sub
   End If
   If TheStation < startStation Or TheStation > endStation Then
      Exit Sub
   End If

'CHECK FOR THE CORRECT ELEMENT ID TAG
   If Not CheckForSurveyorToolsTagAndVal(TheElem, TAG_NAME_MY_ID, TheTagVal) Then
      Exit Sub
   End If
   Dim CurrentElementIdString As String
   CurrentElementIdString = DLongToString(TheElem.ID)
   If CurrentElementIdString <> TheTagVal Then
      Exit Sub
   End If

'IT'S CORRECT, REMOVE PREVIOUS ELEMENT
   ActiveModelReference.RemoveElement TheElem
End Sub



Private Sub SetTextJustification(TheTextElement As TextElement)
'SET THE TEXT ACCORDING TO THE OPTION BUTTONS
   If OptionRightJustified.value = True Then
      ChangeJustification TheTextElement, msdTextJustificationRightCenter
   ElseIf OptionCenterJustified.value = True Then
      ChangeJustification TheTextElement, msdTextJustificationCenterCenter
   ElseIf OptionLeftJustified.value = True Then
      ChangeJustification TheTextElement, msdTextJustificationLeftCenter
   End If
End Sub



Private Sub OrientTextElement(theElement As TextElement, InsertionPoint As Point3d, ByVal FwdAz As Double)
'ROTATES TEXT ELEMENT BASED ON FORWARD AZIMUTH (DECIMAL DEGREES)
'MAKE WORKING COPY
   Dim CopyInsertPoint As Point3d
   CopyInsertPoint = InsertionPoint
  
'FIGURE ROTATION ANGLE FOR ORIENTATION CALLED FOR
   If OptionTopToLeft.value = True Then
      Dim RotationAngleDegrees As Double
         RotationAngleDegrees = 360 - (FwdAz + 90)
   ElseIf OptionTopToRight = True Then
         RotationAngleDegrees = 360 - (FwdAz - 90)
   ElseIf OptionTopForward = True Then
      RotationAngleDegrees = 360 - (FwdAz - 180)
   ElseIf OptionTopBack = True Then
      RotationAngleDegrees = 360 - FwdAz
   End If

   theElement.RotateAboutZ InsertionPoint, Radians(RotationAngleDegrees)
End Sub



Private Function CalcInsertionPoint(BaselinePoint As Point3d, ByVal FwdAz As Double) As Point3d
'FORWARD AZIMUTH TAKEN IN DECIMAL DEGREES
'CALCULATE THE INSERTION POINT USING THE OFFSETS IN CHARACTER SIZE
'MAKE WORKING COPY
   Dim CopyBasepoint As Point3d
   CopyBasepoint = BaselinePoint

'GET SIZE OF THE CHARACTERS TO USE
   Dim charSize As Double
   charSize = GetCharSize()

'GET LEFT/RIGHT OFFSET
   Dim LROffset As Double
   LROffset = CDbl(TransverseTextBox.text) * charSize

'MOVE LEFT OR RIGHT
   If OptionRight.value = True Then
      Dim OffsetAz As Double
      OffsetAz = FwdAz + 90
   Else
      OffsetAz = FwdAz + 270
   End If
   Dim OffsetPoint As Point3d
   OffsetPoint = CoordFwdSAz(CopyBasepoint, OffsetAz, LROffset)

'GET FORWARD/BACK OFFSET
   Dim FBOffset As Double
   FBOffset = CDbl(LongitudinalTextBox.text) * charSize
   
'MOVE FORWARD OR BACK ALONG THE TANGENT
   OffsetAz = FwdAz
   If OptionBack.value = True Then
      OffsetAz = OffsetAz + 180
   End If
   CalcInsertionPoint = CoordFwdSAz(OffsetPoint, OffsetAz, FBOffset)
End Function



Private Function DetermineValidStationRange(ByVal EnteredBegin As Double, _
                                            ByVal EnteredEnd As Double, _
                                            ByRef MinStation As Double, _
                                            ByRef MaxStation As Double) As Boolean
'FIGURE OUT THE ACTUAL STATION RANGE TO ITERATE THRU TO PLACE STATIONS
'RETURNS TRUE IF THERE ARE ANY STATIONS IN RANGE
'INITIALIZE FLAG
   DetermineValidStationRange = False

'ROUND ENTRIES TO MAKE SURE
   EnteredBegin = Round(EnteredBegin, 2)
   EnteredEnd = Round(EnteredEnd, 2)
   
'GET THE BEGINNING STATION OF THE BASELINE SEGMENT
   Dim BaselineBeginStation As Double
   Dim origPrec As Long
   If Not IsStationString(theBeginStation, BaselineBeginStation, origPrec, entryStationStyleGlobal) Then
      Exit Function
   End If

'GET THE ENDING STATION OF THE BASELINE SEGMENT
   Dim BaselineEndStation As Double
   If Not calcEndStationOfElement(BaselineEndStation) Then
      Exit Function
   End If

'SORT THE ENTERED STATIONS
   Dim lowerStation As Double
   lowerStation = Min(EnteredBegin, EnteredEnd)
   Dim higherStation As Double
   higherStation = Max(EnteredBegin, EnteredEnd)

'MAKE SURE THE ENTERED IS ON THE BASELINE
   If lowerStation > BaselineEndStation Then
      Exit Function
   End If
   If higherStation < BaselineBeginStation Then
      Exit Function
   End If

'FIGURE WHICH BOUNDARIES TO HOLD
   MinStation = Max(EnteredBegin, BaselineBeginStation)
   MaxStation = Min(EnteredEnd, BaselineEndStation)

'VALID RANGE DETERMINED
   DetermineValidStationRange = True
End Function



'*************************************************************************************************************
'*************************************************OTHER STUFF*************************************************
Private Sub FlagInvalidElement()
'SETS FLAG TO INVALID ELELMENT, UPDATES DISPLAY, DISABLES "GO" BUTTON
   isValidElement = False
   GObutton.enabled = False
   updateStatusDisplay thePickedElement, ThePickedIDString, thePickedLength
End Sub



Public Sub LocateIsClosing(ByVal JustACheck As Long)
'RECIEVES MESSAGE FROM ILOCATE THAT IT'S CLOSING
'UNLOADS THIS USER FORM IF READY
   If JustACheck <> 5 Then
      Exit Sub
   End If
   If Not doNotCloseYet Then
      Unload Me
   End If
End Sub



Private Sub FlagValidElement()
'SETS FLAG TO VALID ELEMENT, UPDATES DISPLAY, ENABLES "GO" BUTTON
   isValidElement = True
   GObutton.enabled = True
   updateStatusDisplay thePickedElement, ThePickedIDString, thePickedLength
End Sub



Private Sub SuggestBeginStation()
'SUGGEST A STARTING STATION TO BEGIN TEXTING FROM, ENTER IT INTO FIELD
   StartTextBox.text = theBeginStation
   StartTextBox_AfterUpdate
End Sub



Private Sub SuggestEndStation()
'SUGGEST AN ENDING STATION TO BEGIN TEXTING FROM, ENTER IT INTO FIELD
   Dim EndingStation As Double
   If calcEndStationOfElement(EndingStation) Then
      EndTextBox.text = StationToString(Round(EndingStation, linearPrecisionGlobal), linearPrecisionGlobal, entryStationStyleGlobal)
   Else
      EndTextBox.text = ""
      FlagInvalidElement
      Exit Sub
   End If
End Sub

Attribute VB_Name = "FrmTraverse"
Attribute VB_Base = "0{6A112EB2-21F0-4D4E-B706-256F01CA9447}{FC824139-51D7-488B-A0D8-38D11597E43E}"
Attribute VB_GlobalNameSpace = False
Attribute VB_Creatable = False
Attribute VB_PredeclaredId = True
Attribute VB_Exposed = False
Attribute VB_TemplateDerived = False
Attribute VB_Customizable = False
















'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.



'GENERAL NOTES:
'ALL THESE ROUTINES WERE WRITTEN BY JASON LOOK.  THEY ARE NOT
'WRITTEN IN THE STYLE COMMONLY USED BY PROFESSIONAL PROGRAMMERS.
'THEY ARE WRITTEN IN THE STYLE PREFERRED BY JASON.  JASON IS NOT
'A PROFESSIONAL PROGRAMMER!

'PROGRAM ASSUMES MASTER UNIT IS FOOT OR SURVEY FOOT, SOME KIND OF FOOT


Option Explicit

Private occupiedPoint                  As Point3d

Private Const TEXTBOX_SETUP_DESC1      As Integer = 1
Private Const TEXTBOX_SETUP_DESC2      As Integer = 2
Private Const TEXTBOX_SETUP_ELEV       As Integer = 3
Private Const TEXTBOX_FORESIGHT_DESC1  As Integer = 4
Private Const TEXTBOX_FORESIGHT_DESC2  As Integer = 5
Private Const TEXTBOX_FORESIGHT_ELEV   As Integer = 6

Private textBoxNumber                  As Integer


'*************************************************************************************************************
'**********************************INTERFACE FOR PICKING TEXT ROUTINE*****************************************
Public Sub EnterText(ByVal Entry As String)
   Select Case textBoxNumber
      Case TEXTBOX_SETUP_DESC1
         TextBoxSetupDesc1.text = Entry
         TextBoxSetupDesc1_AfterUpdate
      Case TEXTBOX_SETUP_DESC2
         TextBoxSetupDesc2.text = Entry
         TextBoxSetupDesc2_AfterUpdate
      Case TEXTBOX_SETUP_ELEV
         Dim floatString As String
         If StrToFloatStr(Entry, floatString) Then
            TextElevation.text = floatString
            TextElevation_AfterUpdate
         End If
      Case TEXTBOX_FORESIGHT_DESC1
         TextBoxDesc1.text = Entry
         TextBoxDesc1_AfterUpdate
      Case TEXTBOX_FORESIGHT_DESC2
         TextBoxDesc2.text = Entry
         TextBoxDesc2_AfterUpdate
      Case TEXTBOX_FORESIGHT_ELEV
         If StrToFloatStr(Entry, floatString) Then
            TextBoxElev.text = floatString
            TextBoxElev_AfterUpdate
         End If
   End Select
End Sub



Private Sub PickSubToo(boxNumber As Integer)
   textBoxNumber = boxNumber
   Dim pickTool As New DrawTraverseILocateText
   Set pickTool.hostForm = Me
   CommandState.StartLocate pickTool
   Me.Hide
End Sub



'*************************************************************************************************************
'*************************************************ENTRY TAB***************************************************
'SETUP DESC1 CHECKBOX
Private Sub CheckBoxSetupDesc1_Click()
   SaveCheckBoxSetting CheckBoxSetupDesc1, SECTION_TRAVERSE, KEY_OCC_CHK_DESC1
   ControlStates
End Sub



'OCCUPIED POINT NAME TEXTBOX
Private Sub TextBoxSetupDesc1_AfterUpdate()
   SavePointDescEntry TextBoxSetupDesc1, SECTION_TRAVERSE, KEY_DESCRIPTION
End Sub

Private Sub TextBoxSetupDesc1_Enter()
   SelectAllText TextBoxSetupDesc1
End Sub



'OCCUPIED POINT NAME PICK BUTTON
Private Sub Desc1PickButton_Click()
   PickSubToo TEXTBOX_SETUP_DESC1
End Sub



'OCCUPIED DESC CHECKBOX
Private Sub CheckBoxSetupDesc2_Click()
   SaveCheckBoxSetting CheckBoxSetupDesc2, SECTION_TRAVERSE, KEY_OCC_CHK_DESC2
   ControlStates
End Sub



'OCCUPIED DESC TEXTBOX
Private Sub TextBoxSetupDesc2_AfterUpdate()
   SavePointDescEntry TextBoxSetupDesc2, SECTION_TRAVERSE, KEY_DESCRIPTION2
End Sub

Private Sub TextBoxSetupDesc2_Enter()
   SelectAllText TextBoxSetupDesc2
End Sub



'OCCUPIED DESC PICK BUTTON
Private Sub Desc2PickButton_Click()
   PickSubToo TEXTBOX_SETUP_DESC2
End Sub



'SETUP NORTHING TEXTBOX
Private Sub TextNorthing_AfterUpdate()
   Dim oricPrec As Long
   Dim northing As Double
   If IsNorthingString(TextNorthing.text, northing, oricPrec) Then
      occupiedPoint.Y = northing
   End If
   SaveNorthingEntry TextNorthing, SECTION_TRAVERSE, KEY_OCC_NORTHING, MAX_PRECISION_COORDINATE
End Sub



'SETUP EASTING TEXTBOX
Private Sub TextEasting_AfterUpdate()
   Dim oricPrec As Long
   Dim easting As Double
   If IsEastingString(TextEasting.text, easting, oricPrec) Then
      occupiedPoint.X = easting
   End If
   SaveEastingEntry TextEasting, SECTION_TRAVERSE, KEY_OCC_EASTING, MAX_PRECISION_COORDINATE
End Sub



'SETUP ELEVATON TEXTBOX
Public Sub TextElevation_AfterUpdate()
   Dim oricPrec As Long
   Dim elevation As Double
   If IsElevationString(TextElevation.text, elevation, oricPrec) Then
      occupiedPoint.z = elevation
   End If
   SaveElevationEntry TextElevation, SECTION_TRAVERSE, KEY_OCC_ELEVATION, oricPrec
End Sub



'SETUP COORDINATE PICK BUTTON
Private Sub CommandPick_Click()
   FrmTraverse.Hide
   If PickSub(COMMAND_NAME_TRVERSE, "Pick Occupied point", occupiedPoint) Then
      Dim occPointCopy As Point3d
      occPointCopy = occupiedPoint
      TextEasting.text = FormatNumber(occupiedPoint.X, MAX_PRECISION_COORDINATE, vbFalse, vbFalse, vbFalse)
      TextEasting_AfterUpdate
      TextNorthing.text = FormatNumber(occupiedPoint.Y, MAX_PRECISION_COORDINATE, vbFalse, vbFalse, vbFalse)
      TextNorthing_AfterUpdate
      TextElevation.text = FormatNumber(occupiedPoint.z, MAX_PRECISION_ELEV, vbFalse, vbFalse, vbFalse)
      TextElevation_AfterUpdate
      occupiedPoint = occPointCopy
   End If
   FrmTraverse.Show
End Sub



'SETUP ELEVATION PICK BUTTON
Private Sub PickElButton_Click()
   PickSubToo TEXTBOX_SETUP_ELEV
End Sub




'SETUP DRAW BUTTON
Private Sub CommandButtonDrawSetup_Click()
   If ActiveModelReference.IsReadOnly = False Then
'SET FOR UNDO
      CommandState.CommandName = COMMAND_NAME_TRVERSE
      If DrawTheOccupied() = False Then
         MsgBox "error occured"
      End If
      CommandState.StartDefaultCommand
   Else
'DO NOTHING IF CANNOT WRITE TO FILE
      Beep
   End If
End Sub



'SETUP SYMBOL 1 RADIO BUTTON
Private Sub OptionSetupSym1_Click()
   SaveSetupSymbol
End Sub



'SETUP SYMBOL 1 IMAGE
Private Sub ImageSetupSym1_Click()
   OptionSetupSym1.value = True
End Sub



'SETUP SYMBOL 2 RADIO BUTTON
Private Sub OptionSetupSym2_Click()
   SaveSetupSymbol
End Sub



'SETUP SYMBOL 2 IMAGE
Private Sub ImageSetupSym2_Click()
   OptionSetupSym2.value = True
End Sub



'SETUP SYMBOL 3 RADIO BUTTON
Private Sub OptionSetupSym3_Click()
   SaveSetupSymbol
End Sub



'SETUP SYMBOL 3 IMAGE
Private Sub ImageSetupSym3_Click()
   OptionSetupSym3.value = True
End Sub



'SETUP SYMBOL 4 RADIO BUTTON
Private Sub OptionSetupSym4_Click()
   SaveSetupSymbol
End Sub



'SETUP SYMBOL 4 IMAGE
Private Sub ImageSetupSym4_Click()
   OptionSetupSym4.value = True
End Sub



'SETUP SYMBOL 5 RADIO BUTTON
Private Sub OptionSetupSym5_Click()
   SaveSetupSymbol
End Sub



'SETUP SYMBOL 5 IMAGE
Private Sub ImageSetupSym5_Click()
   OptionSetupSym5.value = True
End Sub



'SETUP SYMBOL 6 RADIO BUTTON
Private Sub OptionSetupSym6_Click()
   SaveSetupSymbol
End Sub



'SETUP SYMBOL 6 IMAGE
Private Sub ImageSetupSym6_Click()
   OptionSetupSym6.value = True
End Sub



'SETUP SYMBOL NONE RADIO BUTTON
Private Sub OptionSetupSymNone_Click()
   SaveSetupSymbol
End Sub



'SAVE SETUP SYMBOL CHOICE
Private Sub SaveSetupSymbol()
   If OptionSetupSymNone.value = True Then
      SaveSetting APP_NAME, SECTION_TRAVERSE, KEY_SETUP_SYM_OPTION, SYMBOL_NONE
   ElseIf OptionSetupSym1.value = True Then
      SaveSetting APP_NAME, SECTION_TRAVERSE, KEY_SETUP_SYM_OPTION, SYMBOL_1
   ElseIf OptionSetupSym2.value = True Then
      SaveSetting APP_NAME, SECTION_TRAVERSE, KEY_SETUP_SYM_OPTION, SYMBOL_2
   ElseIf OptionSetupSym3.value = True Then
      SaveSetting APP_NAME, SECTION_TRAVERSE, KEY_SETUP_SYM_OPTION, SYMBOL_3
   ElseIf OptionSetupSym4.value = True Then
      SaveSetting APP_NAME, SECTION_TRAVERSE, KEY_SETUP_SYM_OPTION, SYMBOL_4
   ElseIf OptionSetupSym5.value = True Then
      SaveSetting APP_NAME, SECTION_TRAVERSE, KEY_SETUP_SYM_OPTION, SYMBOL_5
   ElseIf OptionSetupSym6.value = True Then
      SaveSetting APP_NAME, SECTION_TRAVERSE, KEY_SETUP_SYM_OPTION, SYMBOL_6
   End If
End Sub



'LABEL COORDINATE CHECKBOX
Private Sub CheckBoxLabelCoord_Click()
   SaveCheckBoxSetting CheckBoxLabelCoord, SECTION_TRAVERSE, KEY_FS_LABELCOORD
End Sub



'LABEL ELEVATION CHECKBOX
Private Sub CheckBoxIncludeElev_Click()
   SaveCheckBoxSetting CheckBoxIncludeElev, SECTION_TRAVERSE, KEY_FS_INCLUDEELEV
End Sub



'LABEL LINE CHECKBOX
Private Sub CheckBoxLabelLine_Click()
   SaveCheckBoxSetting CheckBoxLabelLine, SECTION_TRAVERSE, KEY_FS_LABELLINE
End Sub



'FORESIGHT POINT NAME CHECKBOX
Private Sub CheckBoxDesc1_Click()
   SaveCheckBoxSetting CheckBoxDesc1, SECTION_TRAVERSE, KEY_FS_CHK_DESC1
   ControlStates
End Sub



'FORESIGHT POINT NAME TEXTBOX
Private Sub TextBoxDesc1_AfterUpdate()
   SaveSetting APP_NAME, SECTION_TRAVERSE, KEY_DESCRIPTION3, TextBoxDesc1.text
End Sub

Private Sub TextBoxDesc1_Enter()
   SelectAllText TextBoxDesc1
End Sub



'FORESIGHT POINT NAME PICK BUTTON
Private Sub FSDesc1PickButton_Click()
   PickSubToo TEXTBOX_FORESIGHT_DESC1
End Sub



'FORESIGHT DESC CHECKBOX
Private Sub CheckBoxDesc2_Click()
   SaveCheckBoxSetting CheckBoxDesc2, SECTION_TRAVERSE, KEY_FS_CHK_DESC2
   ControlStates
End Sub



'FORESIGHT DESC TEXTBOX
Private Sub TextBoxDesc2_AfterUpdate()
   SaveSetting APP_NAME, SECTION_TRAVERSE, KEY_DESCRIPTION4, TextBoxDesc2.text
End Sub

Private Sub TextBoxDesc2_Enter()
   SelectAllText TextBoxDesc2
End Sub



'FORESIGHT DESC PICK BUTTON
Private Sub FSDesc2PickButton_Click()
   PickSubToo TEXTBOX_FORESIGHT_DESC2
End Sub



'FORESIGHT DIRECTION TEXTBOX
Private Sub TextBoxAz_AfterUpdate()
   SaveDirEntry TextBoxAz, SECTION_TRAVERSE, KEY_DIRECTION, STYLE_ANGLE_SPACE Or STYLE_ANGLE_LEAD
End Sub

Private Sub TextBoxAz_Enter()
   SelectAllText TextBoxAz
End Sub



'FORESIGHT DISTANCE TEXTBOX
Private Sub TextBoxDist_AfterUpdate()
   SaveNonnegativeEntry TextBoxDist, SECTION_TRAVERSE, KEY_DISTANCE, MAX_DISTANCE, MAX_PRECISION_DISTANCE, True, 100#
End Sub

Private Sub TextBoxDist_Enter()
   SelectAllText TextBoxDist
End Sub



'FORESIGHT ELEVATION TEXTBOX
Public Sub TextBoxElev_AfterUpdate()
   Dim oricPrec As Long
   SaveElevationEntry TextElevation, SECTION_TRAVERSE, KEY_FS_ELEVATION, oricPrec
End Sub

Private Sub TextBoxElev_Enter()
   SelectAllText TextBoxElev
End Sub



'FORESIGHT ELEVATION PICK BUTTON
Private Sub PickFSElButton_Click()
   PickSubToo TEXTBOX_FORESIGHT_ELEV
End Sub



'FORESIGHT SYMBOL 1 RADIO BUTTON
Private Sub OptionFSSym1_Click()
   SaveForesightSymbol
End Sub



'FORESIGHT SYMBOL 1 IMAGE
Private Sub ImageFSSym1_Click()
   OptionFSSym1.value = True
End Sub



'FORESIGHT SYMBOL 2 RADIO BUTTON
Private Sub OptionFSSym2_Click()
   SaveForesightSymbol
End Sub



'FORESIGHT SYMBOL 2 IMAGE
Private Sub ImageFSSym2_Click()
   OptionFSSym2.value = True
End Sub



'FORESIGHT SYMBOL 3 RADIO BUTTON
Private Sub OptionFSSym3_Click()
   SaveForesightSymbol
End Sub



'FORESIGHT SYMBOL 3 IMAGE
Private Sub ImageFSSym3_Click()
   OptionFSSym3.value = True
End Sub



'FORESIGHT SYMBOL 4 RADIO BUTTON
Private Sub OptionFSSym4_Click()
   SaveForesightSymbol
End Sub



'FORESIGHT SYMBOL 4 IMAGE
Private Sub ImageFSSym4_Click()
   OptionFSSym4.value = True
End Sub



'FORESIGHT SYMBOL 5 RADIO BUTTON
Private Sub OptionFSSym5_Click()
   SaveForesightSymbol
End Sub



'FORESIGHT SYMBOL 5 IMAGE
Private Sub ImageFSSym5_Click()
   OptionFSSym5.value = True
End Sub



'FORESIGHT SYMBOL 6 RADIO BUTTON
Private Sub OptionFSSym6_Click()
   SaveForesightSymbol
End Sub



'FORESIGHT SYMBOL 6 IMAGE
Private Sub ImageFSSym6_Click()
   OptionFSSym6.value = True
End Sub



'FORESIGHT SYMBOL NONE
Private Sub OptionFSSymNone_Click()
   SaveForesightSymbol
End Sub



Private Sub SaveForesightSymbol()
   If OptionFSSymNone.value = True Then
      SaveSetting APP_NAME, SECTION_TRAVERSE, KEY_FS_SYM_OPTION, SYMBOL_NONE
   ElseIf OptionFSSym1.value = True Then
      SaveSetting APP_NAME, SECTION_TRAVERSE, KEY_FS_SYM_OPTION, SYMBOL_1
   ElseIf OptionFSSym2.value = True Then
      SaveSetting APP_NAME, SECTION_TRAVERSE, KEY_FS_SYM_OPTION, SYMBOL_2
   ElseIf OptionFSSym3.value = True Then
      SaveSetting APP_NAME, SECTION_TRAVERSE, KEY_FS_SYM_OPTION, SYMBOL_3
   ElseIf OptionFSSym4.value = True Then
      SaveSetting APP_NAME, SECTION_TRAVERSE, KEY_FS_SYM_OPTION, SYMBOL_4
   ElseIf OptionFSSym5.value = True Then
      SaveSetting APP_NAME, SECTION_TRAVERSE, KEY_FS_SYM_OPTION, SYMBOL_5
   ElseIf OptionFSSym6.value = True Then
      SaveSetting APP_NAME, SECTION_TRAVERSE, KEY_FS_SYM_OPTION, SYMBOL_6
   End If
End Sub



'FORESIGHT MODE OPTION SIDE SHOT
Private Sub SideShotOption_Click()
   saveMode
End Sub



'FORESIGHT MODE OPTION TRAVERSE
Private Sub TraverseOption_Click()
   saveMode
End Sub



Private Sub saveMode()
   If TraverseOption.value Then
      SaveSetting APP_NAME, SECTION_TRAVERSE, KEY_CHK_MOVEUP, OPTION_TRUE
   Else
      SaveSetting APP_NAME, SECTION_TRAVERSE, KEY_CHK_MOVEUP, OPTION_FALSE
   End If
End Sub



'DRAW FORESIGHT BUTTON
Private Sub CommandDrawIt_Click()
   If ActiveModelReference.IsReadOnly = False Then
      CommandState.CommandName = COMMAND_NAME_TRVERSE
      If DrawTheTraverse() = False Then
         MsgBox "error occured"
      ElseIf CheckBoxDesc1.value = True Then
         CommandState.StartDefaultCommand
         TextBoxDesc1.SetFocus
      ElseIf CheckBoxDesc2.value = True Then
         CommandState.StartDefaultCommand
         TextBoxDesc2.SetFocus
      Else
         CommandState.StartDefaultCommand
         TextBoxAz.SetFocus
      End If
   Else
'DO NOTHING
      Beep
   End If
End Sub



'*************************************************************************************************************
'************************************************SETTINGS TAB*************************************************
'COORDINATE PRECISION COMBOBOX
Private Sub CoordPrecComboBox_AfterUpdate()
   SaveSetting APP_NAME, SECTION_TRAVERSE, KEY_PRECISION_COORD, CoordPrecComboBox.value
End Sub



'ELEVATION PRECISION COMBOBOX
Private Sub ElPrecComboBox_AfterUpdate()
   SaveSetting APP_NAME, SECTION_TRAVERSE, KEY_PRECISION_ELEV, ElPrecComboBox.value
End Sub



'TEXT LEVEL COMBOBOX
Private Sub ComboBoxTSLevel_AfterUpdate()
   If Not LevelBoxOnUpdate(ComboBoxTSLevel, SECTION_TRAVERSE, KEY_TEXT_LEVEL) Then
      PopulateLevelBox ComboBoxTSLevel, SECTION_TRAVERSE, KEY_TEXT_LEVEL
      Beep
   End If
End Sub



'TEXT COLOR COMBOBOX
Private Sub ComboBoxTSColor_AfterUpdate()
   ColorBoxOnUpdate ComboBoxTSColor, SECTION_TRAVERSE, KEY_TEXT_COLOR
End Sub



'TEXT COLOR COLOR CHOOSER BUTTON
Private Sub TextColorChooserButton_Click()
   Dim MyColor As String
   If ChooseMyTableColor(MyColor) Then
      ComboBoxTSColor.text = MyColor
      ComboBoxTSColor_AfterUpdate
   End If
End Sub



'TEXT STYLE COMBOBOX
Private Sub ComboBoxTSType_AfterUpdate()
   If Not LineStyleBoxOnUpdate(ComboBoxTSType, SECTION_TRAVERSE, KEY_TEXT_STYLE) Then
      PopulateLinestyleBox ComboBoxTSType, SECTION_TRAVERSE, KEY_TEXT_STYLE
      Beep
   End If
End Sub



'TEXT WEIGHT COMBOBOX
Private Sub ComboBoxTSWeight_AfterUpdate()
   WeightBoxOnUpdate ComboBoxTSWeight, SECTION_TRAVERSE, KEY_TEXT_WEIGHT
End Sub



'TEXT FONT COMBOBOX
Private Sub ComboTextFontBox_AfterUpdate()
   If Not FontBoxOnUpdate(ComboTextFontBox, SECTION_TRAVERSE, KEY_TEXT_FONT) Then
      PopulateFontBox ComboTextFontBox, SECTION_TRAVERSE, KEY_TEXT_FONT
      Beep
   End If
End Sub



'LINE LEVEL COMBOBOX
Private Sub ComboBoxLineLevel_AfterUpdate()
   If Not LevelBoxOnUpdate(ComboBoxLineLevel, SECTION_TRAVERSE, KEY_LINE_LEVEL) Then
      PopulateLevelBox ComboBoxLineLevel, SECTION_TRAVERSE, KEY_LINE_LEVEL
      Beep
   End If
End Sub



'LINE COLOR COMBOBOX
Private Sub ComboBoxLineColor_AfterUpdate()
   ColorBoxOnUpdate ComboBoxLineColor, SECTION_TRAVERSE, KEY_LINE_COLOR
End Sub



'LINE COLOR COLOR CHOOSER BUTTON
Private Sub LineColorChooserButton_Click()
   Dim MyColor As String
   If ChooseMyTableColor(MyColor) Then
      ComboBoxLineColor.text = MyColor
      ComboBoxLineColor_AfterUpdate
   End If
End Sub



'LINE STYLE COMBOBOX
Private Sub ComboBoxLineType_AfterUpdate()
   If Not LineStyleBoxOnUpdate(ComboBoxLineType, SECTION_TRAVERSE, KEY_LINE_STYLE) Then
      PopulateLinestyleBox ComboBoxLineType, SECTION_TRAVERSE, KEY_LINE_STYLE
      Beep
   End If
End Sub



'LINE WEIGHT COMBOBOX
Private Sub ComboBoxLineWeight_AfterUpdate()
   WeightBoxOnUpdate ComboBoxLineWeight, SECTION_TRAVERSE, KEY_LINE_WEIGHT
End Sub



'SYMBOLS LEVEL COMBOBOX
Private Sub ComboBoxSymLevel_AfterUpdate()
   If Not LevelBoxOnUpdate(ComboBoxSymLevel, SECTION_TRAVERSE, KEY_SYM_LEVEL) Then
      PopulateLevelBox ComboBoxSymLevel, SECTION_TRAVERSE, KEY_SYM_LEVEL
      Beep
   End If
End Sub



'SYMBOLS COLOR COMBOBOX
Private Sub ComboBoxSymColor_AfterUpdate()
   ColorBoxOnUpdate ComboBoxSymColor, SECTION_TRAVERSE, KEY_SYM_COLOR
End Sub



'SYMBOL COLOR COLOR CHOOSER BUTTON
Private Sub SymbolColorChooserButton_Click()
   Dim MyColor As String
   If ChooseMyTableColor(MyColor) Then
      ComboBoxSymColor.text = MyColor
      ComboBoxSymColor_AfterUpdate
   End If
End Sub



'SYMBOLS STYLE COMBOBOX
Private Sub ComboBoxSymStyle_AfterUpdate()
   If Not LineStyleBoxOnUpdate(ComboBoxSymStyle, SECTION_TRAVERSE, KEY_SYM_STYLE) Then
      PopulateLinestyleBox ComboBoxSymStyle, SECTION_TRAVERSE, KEY_SYM_STYLE
      Beep
   End If
End Sub



'SYMBOLS WEIGHT COMBOBOX
Private Sub ComboBoxSymWeight_AfterUpdate()
   WeightBoxOnUpdate ComboBoxSymWeight, SECTION_TRAVERSE, KEY_SYM_WEIGHT
End Sub



'SETTINGS BUTTON
Private Sub SettingsButton_Click()
   Setting
End Sub



'*************************************************************************************************************
'**********************************************USERFORM EVENTS************************************************
Private Sub UserForm_Initialize()
'INITIALIZE SETUP SYMBOL
   Dim Options As String
   Options = GetSetting(APP_NAME, SECTION_TRAVERSE, KEY_SETUP_SYM_OPTION, "0")
   Select Case Options
      Case SYMBOL_NONE
         OptionSetupSymNone.value = True
      Case SYMBOL_1
         OptionSetupSym1.value = True
      Case SYMBOL_2
         OptionSetupSym2.value = True
      Case SYMBOL_3
         OptionSetupSym3.value = True
      Case SYMBOL_4
         OptionSetupSym4.value = True
      Case SYMBOL_5
         OptionSetupSym5.value = True
      Case SYMBOL_6
         OptionSetupSym6.value = True
   End Select

'INITIALIZE INCLUDE ELEVATION CHECKBOX
   InitializeCheckBox CheckBoxIncludeElev, SECTION_TRAVERSE, KEY_FS_INCLUDEELEV

'INITIALIZE LABEL COORDINATE CHECKBOX
   InitializeCheckBox CheckBoxLabelCoord, SECTION_TRAVERSE, KEY_FS_LABELCOORD

'INITIALIZE LABEL LINE CHECKBOX
   InitializeCheckBox CheckBoxLabelLine, SECTION_TRAVERSE, KEY_FS_LABELLINE

'INITIALIZE SETUP DESCRIPTION1 CHECKBOX
   InitializeCheckBox CheckBoxSetupDesc1, SECTION_TRAVERSE, KEY_OCC_CHK_DESC1

'INITIALIZE SETUP DESCRIPTION2 CHECKBOX
   InitializeCheckBox CheckBoxSetupDesc2, SECTION_TRAVERSE, KEY_OCC_CHK_DESC2

'INITIALIZE FORESIGHT DESCRIPTION1 CHECKBOX
   InitializeCheckBox CheckBoxDesc1, SECTION_TRAVERSE, KEY_FS_CHK_DESC1

'INITIALIZE FORESIGHT DESCRIPTION2 CHECKBOX
   InitializeCheckBox CheckBoxDesc2, SECTION_TRAVERSE, KEY_FS_CHK_DESC2

'INITIALIZE FORESIGHT SYMBOL
   Options = GetSetting(APP_NAME, SECTION_TRAVERSE, KEY_FS_SYM_OPTION, "0")
   Select Case Options
      Case SYMBOL_NONE
         OptionFSSymNone.value = True
      Case SYMBOL_1
         OptionFSSym1.value = True
      Case SYMBOL_2
         OptionFSSym2.value = True
      Case SYMBOL_3
         OptionFSSym3.value = True
      Case SYMBOL_4
         OptionFSSym4.value = True
      Case SYMBOL_5
         OptionFSSym5.value = True
      Case SYMBOL_6
         OptionFSSym6.value = True
   End Select

'INITIALIZE MODE
   If GetSetting(APP_NAME, SECTION_TRAVERSE, KEY_CHK_MOVEUP, OPTION_TRUE) = OPTION_TRUE Then
      TraverseOption.value = True
   Else
      SideShotOption.value = True
   End If

'INITIALIZE COORDINATE PRECISION COMBOBOX
   CoordPrecComboBox.Clear
   CoordPrecComboBox.AddItem "1"
   CoordPrecComboBox.AddItem "2"
   CoordPrecComboBox.AddItem "3"
   CoordPrecComboBox.AddItem "4"
   CoordPrecComboBox.MatchRequired = True
   Options = GetSetting(APP_NAME, SECTION_TRAVERSE, KEY_PRECISION_COORD, "4")
   CoordPrecComboBox.text = Options
   If Not CoordPrecComboBox.MatchFound Then
      CoordPrecComboBox.listIndex = 0
   End If
   
'INITIALIZE ELEVATION PRECISION COMBOBOX
   ElPrecComboBox.Clear
   ElPrecComboBox.AddItem "0"
   ElPrecComboBox.AddItem "1"
   ElPrecComboBox.AddItem "2"
   ElPrecComboBox.AddItem "3"
   CoordPrecComboBox.MatchRequired = True
   Options = GetSetting(APP_NAME, SECTION_TRAVERSE, KEY_PRECISION_ELEV, "2")
   ElPrecComboBox.text = Options
   If Not ElPrecComboBox.MatchFound Then
      ElPrecComboBox.listIndex = 0
   End If

'INITIALIZE SETUP COORDINATE
   TextNorthing.MaxLength = MAX_LEN_COORDINATE_STRING
   TextNorthing.text = GetSetting(APP_NAME, SECTION_TRAVERSE, KEY_OCC_NORTHING, "0")
   TextNorthing_AfterUpdate

   TextEasting.MaxLength = MAX_LEN_COORDINATE_STRING
   TextEasting.text = GetSetting(APP_NAME, SECTION_TRAVERSE, KEY_OCC_EASTING, "0")
   TextEasting_AfterUpdate

   TextElevation.MaxLength = MAX_LEN_ELEV_STRING
   TextElevation.text = GetSetting(APP_NAME, SECTION_TRAVERSE, KEY_OCC_ELEVATION, "0")
   TextElevation_AfterUpdate

'DIRECTION TEXTBOX
   Dim DirString As String
   DirString = GetSetting(APP_NAME, SECTION_TRAVERSE, KEY_DIRECTION, "")
   If DirString = "" Then
      TextBoxAz.text = "0.0000"
      TextBoxAz_AfterUpdate
   Else
      TextBoxAz.text = DirString
   End If

'DISTANCE TEXTBOX
   TextBoxDist.MaxLength = MAX_LEN_DIST_STRING
   TextBoxDist.text = GetSetting(APP_NAME, SECTION_TRAVERSE, KEY_DISTANCE, "100.11")

'FORESIGHT ELEVATION TEXTBOX
   TextBoxElev.MaxLength = MAX_LEN_ELEV_STRING
   TextBoxElev.text = CDbl(GetSetting(APP_NAME, SECTION_TRAVERSE, KEY_FS_ELEVATION, "0"))
   
'FORESIGHT NAME TEXTBOX
   TextBoxDesc1.MaxLength = MAX_LEN_POINT_NAME
   TextBoxDesc1.text = GetSetting(APP_NAME, SECTION_TRAVERSE, KEY_DESCRIPTION3, "")
   
'FORESIGHT DESC TEXTBOX
   TextBoxDesc2.MaxLength = MAX_LEN_POINT_DESC
   TextBoxDesc2.text = GetSetting(APP_NAME, SECTION_TRAVERSE, KEY_DESCRIPTION4, "")
 
'OCCUPIED NAME TEXTBOX
   TextBoxSetupDesc1.MaxLength = MAX_LEN_POINT_NAME
   TextBoxSetupDesc1.text = GetSetting(APP_NAME, SECTION_TRAVERSE, KEY_DESCRIPTION, "")
   
'OCCUPIED DESC TEXTBOX
   TextBoxSetupDesc2.MaxLength = MAX_LEN_POINT_DESC
   TextBoxSetupDesc2.text = GetSetting(APP_NAME, SECTION_TRAVERSE, KEY_DESCRIPTION2, "")

'POPULATE TEXT SETTINGS COMBOBOXES
   PopulateLevelBox ComboBoxTSLevel, SECTION_TRAVERSE, KEY_TEXT_LEVEL
   PopulateColorBox ComboBoxTSColor, SECTION_TRAVERSE, KEY_TEXT_COLOR
   PopulateLinestyleBox ComboBoxTSType, SECTION_TRAVERSE, KEY_TEXT_STYLE
   PopulateWeightBox ComboBoxTSWeight, SECTION_TRAVERSE, KEY_TEXT_WEIGHT
   PopulateFontBox ComboTextFontBox, SECTION_TRAVERSE, KEY_TEXT_FONT
   
'POPULATE LINE SETTINGS COMBOBOXES
   PopulateLevelBox ComboBoxLineLevel, SECTION_TRAVERSE, KEY_LINE_LEVEL
   PopulateColorBox ComboBoxLineColor, SECTION_TRAVERSE, KEY_LINE_COLOR
   PopulateLinestyleBox ComboBoxLineType, SECTION_TRAVERSE, KEY_LINE_STYLE
   PopulateWeightBox ComboBoxLineWeight, SECTION_TRAVERSE, KEY_LINE_WEIGHT
   
'POPULATE SYMBOLS SETTINGS COMBOBOXES
   PopulateLevelBox ComboBoxSymLevel, SECTION_TRAVERSE, KEY_SYM_LEVEL
   PopulateColorBox ComboBoxSymColor, SECTION_TRAVERSE, KEY_SYM_COLOR
   PopulateLinestyleBox ComboBoxSymStyle, SECTION_TRAVERSE, KEY_SYM_STYLE
   PopulateWeightBox ComboBoxSymWeight, SECTION_TRAVERSE, KEY_SYM_WEIGHT
   
'SET STATES OF CONTROLS
   ControlStates
   
'MOVE INTO LAST POSITION
   If GetSetting(APP_NAME, SECTION_TRAVERSE, KEY_START_TOP, "") = "" Then
      Me.StartUpPosition = 1
   Else
      Me.StartUpPosition = 0
      Me.Top = CDbl(GetSetting(APP_NAME, SECTION_TRAVERSE, KEY_START_TOP, WINDOW_DEFAULT_TOP))
      Me.Left = CDbl(GetSetting(APP_NAME, SECTION_TRAVERSE, KEY_START_LEFT, WINDOW_DEFAULT_LEFT))
   End If
   
'BRING ENTRY PAGE TO FOREGROUND
   Me.MultiPage1.value = 0
End Sub



Private Sub UserForm_QueryClose(Cancel As Integer, CloseMode As Integer)
'SAVE USERFORM POSITION
   SaveSetting APP_NAME, SECTION_TRAVERSE, KEY_START_TOP, FormatNumber(Me.Top, 2)
   SaveSetting APP_NAME, SECTION_TRAVERSE, KEY_START_LEFT, FormatNumber(Me.Left, 2)
End Sub



'*************************************************************************************************************
'************************************************CONTROL STATES***********************************************
Private Sub ControlStates()
   TextBoxDesc1.BackColor = BackOLE_COLOR(CheckBoxDesc1.value)
   TextBoxDesc1.enabled = CheckBoxDesc1.value
   FSDesc1PickButton.enabled = CheckBoxDesc1.value

   TextBoxDesc2.BackColor = BackOLE_COLOR(CheckBoxDesc2.value)
   TextBoxDesc2.enabled = CheckBoxDesc2.value
   FSDesc2PickButton.enabled = CheckBoxDesc2.value

   TextBoxSetupDesc1.BackColor = BackOLE_COLOR(CheckBoxSetupDesc1.value)
   TextBoxSetupDesc1.enabled = CheckBoxSetupDesc1.value
   Desc1PickButton.enabled = CheckBoxSetupDesc1.value

   TextBoxSetupDesc2.BackColor = BackOLE_COLOR(CheckBoxSetupDesc2.value)
   TextBoxSetupDesc2.enabled = CheckBoxSetupDesc2.value
   Desc2PickButton.enabled = CheckBoxSetupDesc2.value
End Sub



'*************************************************************************************************************
'*************************************************TEMPLATES***************************************************
'LINE TEMPLATE
Private Function TraverseLineTemplate() As LineElement
   Set TraverseLineTemplate = CreateLineTemplate(SECTION_TRAVERSE, _
                                                 ComboBoxLineLevel, _
                                                 KEY_LINE_LEVEL, _
                                                 ComboBoxLineWeight, _
                                                 ComboBoxLineColor, _
                                                 ComboBoxLineType, _
                                                 KEY_LINE_STYLE)
End Function



'SYMBOLS TEMPLATE
Private Function makeSymbolTemplate() As LineElement
   Set makeSymbolTemplate = CreateLineTemplate(SECTION_TRAVERSE, _
                                               ComboBoxSymLevel, _
                                               KEY_SYM_LEVEL, _
                                               ComboBoxSymWeight, _
                                               ComboBoxSymColor, _
                                               ComboBoxSymStyle, _
                                               KEY_SYM_STYLE)
End Function



'TEXT TEMPLATE
Private Function makeTextTemplate() As TextElement
   Set makeTextTemplate = CreateTextTemplate(SECTION_TRAVERSE, _
                                             ComboTextFontBox, _
                                             KEY_TEXT_FONT, _
                                             ComboBoxTSLevel, _
                                             KEY_TEXT_LEVEL, _
                                             ComboBoxTSWeight, _
                                             ComboBoxTSColor, _
                                             ComboBoxTSType, _
                                             KEY_TEXT_STYLE)
End Function



'*************************************************************************************************************
'*************************************************DRAWING*****************************************************
Private Function DrawTheOccupied() As Boolean
'DRAWS THE OCCUPIED POINT, RETURNS TRUE IF OKAY
'INITIALIZE COMPLETION FLAG
   DrawTheOccupied = True

'GET ACTIVE VIEW IF ANY
   Dim mySelectedView As view
   Set mySelectedView = GetSelectedView()

'IF THERE IS NO OPEN VIEW, THEN QUIT
   If mySelectedView Is Nothing Then
      DrawTheOccupied = False
      Beep
      Exit Function
   End If

'CALCULATE ROATATION TO MATCH VIEW
   Dim rotateViewAboutZAngle As Double
   rotateViewAboutZAngle = TheViewRotRadians(mySelectedView)

'CALCULATE METRICS
   Dim characterSize As Double
   characterSize = GetCharSize()
   Dim LineSpacing As Double
   LineSpacing = characterSize * 0.3

'DRAW SYMBOL IF CHOSEN
   DrawTheOCSymbols occupiedPoint, characterSize, rotateViewAboutZAngle

'DRAW TEXT IF CHOSEN
   Dim OccPoint As Point3d
   OccPoint = occupiedPoint

   DrawTheText OccPoint, _
               characterSize, _
               LineSpacing, _
               rotateViewAboutZAngle, _
               CheckBoxSetupDesc1.value, _
               TextBoxSetupDesc1.text, _
               CheckBoxSetupDesc2.value, _
               TextBoxSetupDesc2.text
End Function



Private Sub DrawTheOCSymbols(InsertionPoint As Point3d, ByVal charSize As Double, ByVal rotateViewAboutZAngle As Double)
'CREATE LINE TEMPLATE
   Dim template As LineElement
   Set template = makeSymbolTemplate()

'DRAW SYMBOL IF CHOSEN
   If OptionSetupSym1.value Then
      Dim symCell As CellElement
      Set symCell = CreateSymbol1Cell(template, InsertionPoint, charSize, rotateViewAboutZAngle)
   ElseIf OptionSetupSym2.value Then
      Set symCell = CreateSymbol2Cell(template, InsertionPoint, charSize, rotateViewAboutZAngle)
   ElseIf OptionSetupSym3.value Then
      Set symCell = CreateSymbol3Cell(template, InsertionPoint, charSize, rotateViewAboutZAngle)
   ElseIf OptionSetupSym4.value Then
      Set symCell = CreateSymbol4Cell(template, InsertionPoint, charSize, rotateViewAboutZAngle)
   ElseIf OptionSetupSym5.value Then
      Set symCell = CreateSymbol5Cell(template, InsertionPoint, charSize, rotateViewAboutZAngle)
   ElseIf OptionSetupSym6.value Then
      Set symCell = CreateSymbol6Cell(template, InsertionPoint, charSize, rotateViewAboutZAngle)
   Else
      Exit Sub
   End If
   ActiveModelReference.AddElement symCell
   symCell.Redraw
End Sub



Private Sub DrawTheText(TheTraversePoint As Point3d, _
                        ByVal characterSize As Double, _
                        ByVal LineSpacing As Double, _
                        ByVal rotateViewAboutZAngle As Double, _
                        ByVal Desc1IsChecked As Boolean, _
                        ByVal Desc1 As String, _
                        ByVal Desc2IsChecked As Boolean, _
                        ByVal Desc2 As String)
                         
'MAKE WORKING COPY
   Dim TraversePoint As Point3d
   TraversePoint = TheTraversePoint

'CREATE TEXT TEMPLATE
   Dim myTextTemplate As TextElement
   Set myTextTemplate = makeTextTemplate()

'CALCULATE INITIAL POSITION OF TEXT
   Dim InitalPosition As Point3d
   InitalPosition = TraversePoint
   InitalPosition.X = InitalPosition.X + (characterSize / 2) + LineSpacing

'DRAW THE DESCRIPTIONS
   Dim HaveDescription As Boolean
   HaveDescription = True
   If Desc1IsChecked And Desc2IsChecked Then
      InitalPosition.Y = InitalPosition.Y + (LineSpacing + characterSize) / 2
      AddTextElement TraversePoint, InitalPosition, rotateViewAboutZAngle, Desc1, myTextTemplate
      
      InitalPosition.Y = InitalPosition.Y - (LineSpacing + characterSize)
      AddTextElement TraversePoint, InitalPosition, rotateViewAboutZAngle, Desc2, myTextTemplate
      
      InitalPosition.Y = InitalPosition.Y - (LineSpacing + characterSize)
   ElseIf Desc1IsChecked Then
      AddTextElement TraversePoint, InitalPosition, rotateViewAboutZAngle, Desc1, myTextTemplate
      InitalPosition.Y = InitalPosition.Y - (LineSpacing + characterSize)
   ElseIf Desc2IsChecked Then
      AddTextElement TraversePoint, InitalPosition, rotateViewAboutZAngle, Desc2, myTextTemplate
      InitalPosition.Y = InitalPosition.Y - (LineSpacing + characterSize)
   Else
      HaveDescription = False
   End If
   
'DRAW THE COORDINATE CELL
   DrawCoordCell TraversePoint, InitalPosition, HaveDescription, characterSize, LineSpacing, myTextTemplate, rotateViewAboutZAngle
End Sub



Private Sub AddTheElement(TheTraversePoint As Point3d, _
                          ByVal rotateViewAboutZAngle As Double, _
                          theElement As Element)
   theElement.RotateAboutZ TheTraversePoint, rotateViewAboutZAngle
   ActiveModelReference.AddElement theElement
   theElement.Redraw
End Sub



Private Sub AddTextElement(TheTraversePoint As Point3d, _
                           TheInsertionPoint As Point3d, _
                           ByVal rotateViewAboutZAngle As Double, _
                           ByVal theText As String, _
                           ByRef myTextTemplate As TextElement)
   Dim TextElem As TextElement
   Set TextElem = CreateTextElement1(myTextTemplate, theText, TheInsertionPoint, Matrix3dIdentity)
   AddTheElement TheTraversePoint, rotateViewAboutZAngle, TextElem
End Sub



Private Sub DrawCoordCell(TraversePoint As Point3d, _
                          InitialPoint As Point3d, _
                          HaveDescription As Boolean, _
                          fontSize As Double, _
                          LineSpacing As Double, _
                          myTextTemplate As TextElement, _
                          rotateViewAboutZAngle As Double)
'EXIT IF NO NOT NEEDED
   If Not (CheckBoxLabelCoord.value Or CheckBoxIncludeElev.value) Then
      Exit Sub
   End If
      
'MAKE WORKING COPY
   Dim northing As Double
   northing = TraversePoint.Y
   Dim easting As Double
   easting = TraversePoint.X
   Dim elevation As Double
   elevation = TraversePoint.z
   
'ROUND OFF VALUES
   Dim CoordinatePrecision As Long
   CoordinatePrecision = GetCoordTextPrecision()
   northing = Round(northing, CoordinatePrecision)
   easting = Round(easting, CoordinatePrecision)
   
   Dim ElevationPrecision As Long
   ElevationPrecision = GetElevationTextPrecision()
   elevation = Round(elevation, ElevationPrecision)

'CREATE THE TEXT STRINGS
   Dim NorthingString As String
   NorthingString = DoubleToNorthingString(northing, CoordinatePrecision)
   Dim EastingString As String
   EastingString = DoubleToEastingString(easting, CoordinatePrecision)
   Dim elevationString As String
   elevationString = "El.= " & FormatNumber(elevation, ElevationPrecision)
   
'CREATE THE TEXT ELEMENTS
   Dim northTextElement As TextElement
   Set northTextElement = CreateTextElement1(myTextTemplate, NorthingString, InitialPoint, Matrix3dIdentity)
   Dim eastTextElement As TextElement
   Set eastTextElement = CreateTextElement1(myTextTemplate, EastingString, InitialPoint, Matrix3dIdentity)
   Dim elevationTextElement As TextElement
   Set elevationTextElement = CreateTextElement1(myTextTemplate, elevationString, InitialPoint, Matrix3dIdentity)

'GET THE TEXT ELEMENTS METRICS
   Dim northingSize As Point2d
   northTextElement.GetTotalTextSize northingSize.X, northingSize.Y
   Dim eastingSize As Point2d
   eastTextElement.GetTotalTextSize eastingSize.X, eastingSize.Y
   Dim elevationSize As Point2d
   elevationTextElement.GetTotalTextSize elevationSize.X, elevationSize.Y
   
'CHANGE THIER TEXT JUSTIFICATION
   ChangeJustification northTextElement, msdTextJustificationRightBottom
   ChangeJustification eastTextElement, msdTextJustificationRightBottom
   ChangeJustification elevationTextElement, msdTextJustificationRightBottom
   
'CALCULATE CELL WIDTH
   Dim CellWidth As Double
   If CheckBoxIncludeElev.value And CheckBoxLabelCoord.value Then
      CellWidth = Max(Max(northingSize.X, eastingSize.X), elevationSize.X)
   ElseIf CheckBoxLabelCoord.value Then
      CellWidth = Max(northingSize.X, eastingSize.X)
   ElseIf CheckBoxIncludeElev.value Then
      CellWidth = elevationSize.X
   End If

'INITIALIZE ARRAY FOR CELL
   Dim cellArray() As Element
   ReDim cellArray(0)

'ADD NORTHING EASTING TO CELL ARRAY IF CHOSEN
   If CheckBoxLabelCoord.value Then
      Dim northingOrigin As Point3d
      northingOrigin = InitialPoint
      northingOrigin.X = InitialPoint.X + CellWidth
      If HaveDescription Then
         northingOrigin.Y = InitialPoint.Y - fontSize / 2
      Else
         northingOrigin.Y = InitialPoint.Y + LineSpacing / 2
      End If
      northTextElement.origin = northingOrigin
      Set cellArray(UBound(cellArray)) = northTextElement
      ReDim Preserve cellArray(UBound(cellArray) + 1)

      Dim eastingOrigin As Point3d
      eastingOrigin = northingOrigin
      eastingOrigin.Y = eastingOrigin.Y - (LineSpacing + fontSize)
      eastTextElement.origin = eastingOrigin
      Set cellArray(UBound(cellArray)) = eastTextElement
      ReDim Preserve cellArray(UBound(cellArray) + 1)
      
      InitialPoint = eastingOrigin
   End If
   
   
'ADD ELEVATION
   If CheckBoxIncludeElev.value = True Then
      If CheckBoxLabelCoord.value Then
         Dim ElevationOrigin As Point3d
         ElevationOrigin = eastingOrigin
         ElevationOrigin.Y = ElevationOrigin.Y - (LineSpacing + fontSize)
      ElseIf HaveDescription Then
         ElevationOrigin = InitialPoint
         ElevationOrigin.X = ElevationOrigin.X + CellWidth
         ElevationOrigin.Y = ElevationOrigin.Y - fontSize / 2
      Else
         ElevationOrigin = InitialPoint
         ElevationOrigin.X = ElevationOrigin.X + CellWidth
         ElevationOrigin.Y = ElevationOrigin.Y - fontSize / 2
      End If

      elevationTextElement.origin = ElevationOrigin
      Set cellArray(UBound(cellArray)) = elevationTextElement
      ReDim Preserve cellArray(UBound(cellArray) + 1)
   End If
      
'GET RID OF EXTRA ARRAY ELEMENT
   ReDim Preserve cellArray(UBound(cellArray) - 1)

'CREATE THE CELL
   Dim CoordinateCell As CellElement
   Set CoordinateCell = CreateCellElement1(vbNullString, cellArray, InitialPoint)

'ADD THE CELL TO FILE
   AddTheElement TraversePoint, rotateViewAboutZAngle, CoordinateCell
End Sub



Private Function GetCoordTextPrecision() As Long
   GetCoordTextPrecision = CLng(CoordPrecComboBox.text)
End Function



Private Function GetElevationTextPrecision() As Long
   GetElevationTextPrecision = CLng(ElPrecComboBox.text)
End Function



Private Function DrawTheTraverse() As Boolean
'CREATE WORKING COPY
   Dim OccPoint As Point3d
   OccPoint = occupiedPoint
   
'INITIALIZE COMPLETION FLAG
   DrawTheTraverse = False

'GET ACTIVE VIEW IF ANY
   Dim mySelectedView As view
   Set mySelectedView = GetSelectedView()

'QUIT IF NO VIEW OPEN
   If mySelectedView Is Nothing Then
      Beep
      Exit Function
   End If

'CONVERT VIEW TO ROATATION ANGLE TO PARALLEL VIEW
   Dim ViewAngle As Double
   Dim rotateViewAboutZAngle As Double
   rotateViewAboutZAngle = TheViewRotRadians(mySelectedView)

'CALCULATE ENDPOINT
   Dim sAz As Double
   Dim origPrec As Long
   Dim degPart As Long
   Dim dirType As Integer
   Dim quad As Integer
   If Not DirStringToSAz(TextBoxAz.text, sAz, origPrec, dirType, quad) Then
      Exit Function
   End If
   Dim distance As Double
   distance = CDbl(TextBoxDist.text)
   Dim endPoint As Point3d
   endPoint = CoordFwdSAz(OccPoint, sAz, distance)
   endPoint.z = CDbl(TextBoxElev.text)

'CALCULATE METRICS
   Dim characterSize As Double
   characterSize = GetCharSize()
   Dim LineSpacing As Double
   LineSpacing = characterSize / 3
   Dim arrowLength As Double
   arrowLength = ARROW_LENGTH * characterSize

'DRAW SYMBOL IF CHOSEN
   DrawTheFSSymbols endPoint, characterSize, rotateViewAboutZAngle

'CREATE THE TRAVERSE LINE ELEMENT
   Dim TemplateTraverseLineElement As LineElement
   Set TemplateTraverseLineElement = TraverseLineTemplate()
   Dim TraverseLineElement As LineElement
   Set TraverseLineElement = CreateLineElement2(TemplateTraverseLineElement, OccPoint, endPoint)

'ADD IT TO THE FILE
   ActiveModelReference.AddElement TraverseLineElement
   TraverseLineElement.Redraw

'DRAW TEXT IF CHOSEN
   Dim TraversePoint As Point3d
   TraversePoint = endPoint
   DrawTheText TraversePoint, _
               characterSize, _
               LineSpacing, _
               rotateViewAboutZAngle, _
               CheckBoxDesc1.value, _
               TextBoxDesc1.text, _
               CheckBoxDesc2.value, _
               TextBoxDesc2.text

'DRAW AZIMUTH AND DISTANCE LINE LABEL HERE
   LabelTheTraverseLine characterSize, LineSpacing, OccPoint, endPoint, rotateViewAboutZAngle

'MOVE UP THE SETUP POINT
   MoveUp endPoint

'INCREMENT FORESIGHT IF NEEDED
   If CheckBoxDesc1.value Then
      Dim formattedName As String
      If IsPointnameString(TextBoxDesc1.text, formattedName) Then
         TextBoxDesc1.text = IncPointName(formattedName)
         TextBoxDesc1_AfterUpdate
      End If
   End If

   DrawTheTraverse = True
End Function



Private Sub DrawTheFSSymbols(InsertionPoint As Point3d, ByVal charSize As Double, ByVal rotateViewAboutZAngle As Double)
'MAKE TEMPLATE FOR SYMBOLS
   Dim template As LineElement
   Set template = makeSymbolTemplate()

'DRAW SYMBOL IF CHOSEN
   If OptionFSSym1.value Then
      Dim symCell As CellElement
      Set symCell = CreateSymbol1Cell(template, InsertionPoint, charSize, rotateViewAboutZAngle)
   ElseIf OptionFSSym2.value Then
      Set symCell = CreateSymbol2Cell(template, InsertionPoint, charSize, rotateViewAboutZAngle)
   ElseIf OptionFSSym3.value Then
      Set symCell = CreateSymbol3Cell(template, InsertionPoint, charSize, rotateViewAboutZAngle)
   ElseIf OptionFSSym4.value Then
      Set symCell = CreateSymbol4Cell(template, InsertionPoint, charSize, rotateViewAboutZAngle)
   ElseIf OptionFSSym5.value Then
      Set symCell = CreateSymbol5Cell(template, InsertionPoint, charSize, rotateViewAboutZAngle)
   ElseIf OptionFSSym6.value Then
      Set symCell = CreateSymbol6Cell(template, InsertionPoint, charSize, rotateViewAboutZAngle)
   Else
      Exit Sub
   End If
   ActiveModelReference.AddElement symCell
   symCell.Redraw
End Sub



Private Sub MoveUp(endPoint As Point3d)
'IF OPTION IS SELECTED, MOVE UP COORDINATE AND DESCRITPION
   If TraverseOption.value Then
      TextEasting.text = FormatNumber(endPoint.X, MAX_PRECISION_COORDINATE, vbFalse, vbFalse, vbFalse)
      TextEasting_AfterUpdate
      TextNorthing.text = FormatNumber(endPoint.Y, MAX_PRECISION_COORDINATE, vbFalse, vbFalse, vbFalse)
      TextNorthing_AfterUpdate
      TextElevation.text = FormatNumber(endPoint.z, MAX_PRECISION_ELEV, vbFalse, vbFalse, vbFalse)
      TextElevation_AfterUpdate
      occupiedPoint = endPoint

      If CheckBoxDesc2.value = True Then
         TextBoxSetupDesc2.text = TextBoxDesc2.text
      Else
         TextBoxSetupDesc2.text = ""
      End If
      TextBoxSetupDesc2_AfterUpdate
      
      If CheckBoxDesc1.value = True Then
         TextBoxSetupDesc1.text = TextBoxDesc1.text
      Else
         TextBoxSetupDesc1.text = ""
      End If
      TextBoxSetupDesc1_AfterUpdate
   End If
End Sub



Private Sub LabelTheTraverseLine(ByVal charSize As Double, _
                                 ByVal LineSpacing As Double, _
                                 startPoint As Point3d, _
                                 endPoint As Point3d, _
                                 ByVal rotateViewAboutZAngle As Double)
'DRAW DIRECTION AND DISTANCE LINE LABEL

'EXIT IF OPTION NOT CHOSEN
   If Not CheckBoxLabelLine.value Then
      Exit Sub
   End If
   
'CREATE THE TEMPLATE FOR TEXT ELEMENTS
   Dim myTextTemplate As TextElement
   Set myTextTemplate = makeTextTemplate()

'CREATE THE STRINGS FOR DIRECTION AND DISTANCE
   Dim DirString As String
   DirString = ReplaceDegreeSymbol2(TextBoxAz.text)
   Dim DistString As String
   DistString = TextBoxDist.text

'CREATE THE TEXT ELEMENTS
   Dim dirTextElement As TextElement
   Set dirTextElement = CreateTextElement1(myTextTemplate, DirString, startPoint, Matrix3dIdentity)
   Dim disTextElement As TextElement
   Set disTextElement = CreateTextElement1(myTextTemplate, DistString, startPoint, Matrix3dIdentity)
      
'GET THEIR SIZES
   Dim dirTextMetrics As Point2d
   dirTextElement.GetTotalTextSize dirTextMetrics.X, dirTextMetrics.Y
   Dim disTextMetrics As Point2d
   disTextElement.GetTotalTextSize disTextMetrics.X, disTextMetrics.Y
      
'DETERMINE IF LINE IS POINTING TO THE LEFT OR RIGHT OF VIEW
   Dim lineSAz As Double
   Dim lineDistance As Double
   Inverse startPoint, endPoint, lineSAz, lineDistance
   Dim theLinePointsLeft As Boolean
   theLinePointsLeft = linePointsLeft(lineSAz, rotateViewAboutZAngle)
         
'CALCULATE MINIMUM LINE LENGTH FOR ALL ON ONE SIDE
   Dim arrowLength As Double
   arrowLength = charSize * ARROW_LENGTH
   Dim minLineLength As Double
   minLineLength = dirTextMetrics.X + arrowLength + disTextMetrics.X + charSize * 4
         
'CALCULATE INSERTION POINT OFFSET FROM LINE
   Dim TextOffset As Double
   TextOffset = LineSpacing + charSize / 2

'IF IT ALL FITS, DRAW IT ON TOP OF THE LINE
   If minLineLength <= lineDistance Then
      Dim spaceBetween As Double
      spaceBetween = (lineDistance - (dirTextMetrics.X + disTextMetrics.X + arrowLength)) / 4
'MAX SPACE BETWEEN SHOULD BE SOMETHING LIKE 40 CHARACTERS
      spaceBetween = Min(spaceBetween, (40 * charSize))
      Dim endSpace As Double
      endSpace = (lineDistance - (dirTextMetrics.X + disTextMetrics.X + 2 * spaceBetween + arrowLength)) / 2

'CALCULATE INSERTION POINTS
      Dim cellInsertionPoint As Point3d
      cellInsertionPoint = startPoint
      cellInsertionPoint.Y = cellInsertionPoint.Y + TextOffset
      If theLinePointsLeft Then
         cellInsertionPoint.X = cellInsertionPoint.X + endSpace - lineDistance
      Else
         cellInsertionPoint.X = cellInsertionPoint.X + endSpace
      End If
      dirTextElement.origin = cellInsertionPoint

'CALCULATE TAIL OF ARROW
      Dim arrowInPt As Point3d
      arrowInPt = cellInsertionPoint
      arrowInPt.X = arrowInPt.X + dirTextMetrics.X + spaceBetween

'CREATE ARROW IN POSITION
      Dim ArrowCell As CellElement
      Set ArrowCell = MyCreateArrowCell(arrowInPt, charSize, theLinePointsLeft, dirTextElement)

'MOVE THE DISTANCE TEXT INTO POSITION
      Dim distTextInPt As Point3d
      distTextInPt = cellInsertionPoint
      distTextInPt.X = distTextInPt.X + dirTextMetrics.X + spaceBetween + arrowLength + spaceBetween
      disTextElement.origin = distTextInPt

'CREATE THE CELL ARRAY
      Dim arrayForCell(3) As Element
      Set arrayForCell(0) = dirTextElement
      Set arrayForCell(1) = ArrowCell
      Set arrayForCell(2) = disTextElement
      Dim AboveLineCell As CellElement
      Set AboveLineCell = CreateCellElement1(vbNullString, arrayForCell, cellInsertionPoint)

'ROTATE IT APPROPRIATELY
      Dim rotateToRadians As Double
      If theLinePointsLeft Then
         rotateToRadians = -Radians(lineSAz - 90#)
      Else
         rotateToRadians = -Radians(lineSAz - 270#)
      End If
      AboveLineCell.RotateAboutZ startPoint, rotateToRadians

'ADD THE CELL TO THE FILE
      ActiveModelReference.AddElement AboveLineCell
      AboveLineCell.Redraw
      Exit Sub
   End If

'DOES NOT FIT ABOVE LINE, TRY ABOVE AND BELOW
   If (dirTextMetrics.X + arrowLength + charSize * 3) > lineDistance Then
      DrawOffToSide startPoint, endPoint, dirTextElement, disTextElement, LineSpacing, charSize, rotateViewAboutZAngle
      Exit Sub
   End If
   
   If (disTextMetrics.X + charSize * 2) > lineDistance Then
      DrawOffToSide startPoint, endPoint, dirTextElement, disTextElement, LineSpacing, charSize, rotateViewAboutZAngle
      Exit Sub
   End If

'PLACE THE DIRECTION ON TOP OF THE LINE, PLACE DISTANCE ON THE BOTTOM
   Dim topCellInsertionPoint As Point3d
   topCellInsertionPoint = startPoint
   topCellInsertionPoint.Y = topCellInsertionPoint.Y + TextOffset
   Dim topSpacing As Double
   topSpacing = (lineDistance - (dirTextMetrics.X + arrowLength)) / 3
   If theLinePointsLeft Then
      topCellInsertionPoint.X = topCellInsertionPoint.X - lineDistance + topSpacing
   Else
      topCellInsertionPoint.X = topCellInsertionPoint.X + topSpacing
   End If
'MOVE DIRECTION TEXT INTO POSITION
   dirTextElement.origin = topCellInsertionPoint

'CREATE THE ARROW
   arrowInPt = topCellInsertionPoint
   arrowInPt.X = arrowInPt.X + dirTextMetrics.X + topSpacing
   Set ArrowCell = MyCreateArrowCell(arrowInPt, charSize, theLinePointsLeft, dirTextElement)

'CREATE THE TOP OF LINE CELL
   Dim topCellArray(2) As Element
   Set topCellArray(0) = dirTextElement
   Set topCellArray(1) = ArrowCell
   If theLinePointsLeft Then
      rotateToRadians = -Radians(lineSAz - 90)
   Else
      rotateToRadians = -Radians(lineSAz - 270)
   End If
   Set AboveLineCell = CreateCellElement1(vbNullString, topCellArray, topCellInsertionPoint)
   AboveLineCell.RotateAboutZ startPoint, rotateToRadians
   
'ADD THE CELL TO THE FILE
   ActiveModelReference.AddElement AboveLineCell
   AboveLineCell.Redraw

'MOVE THE TEXT
   Dim disInsertPoint As Point3d
   disInsertPoint = startPoint
   disInsertPoint.Y = disInsertPoint.Y - TextOffset
   Dim disSpacing As Double
   disSpacing = (lineDistance - disTextMetrics.X) / 2
   If theLinePointsLeft Then
      disInsertPoint.X = disInsertPoint.X - lineDistance + disSpacing
   Else
      disInsertPoint.X = disInsertPoint.X + disSpacing
   End If
   disTextElement.origin = disInsertPoint
   disTextElement.RotateAboutZ startPoint, rotateToRadians

'ADD TO DRAWING
   ActiveModelReference.AddElement disTextElement
   disTextElement.Redraw
End Sub



Private Sub DrawOffToSide(startPoint As Point3d, _
                          endPoint As Point3d, _
                          dirTextElement As TextElement, _
                          disTextElement As TextElement, _
                          ByVal LineSpacing As Double, _
                          ByVal characterSize As Double, _
                          ByVal rotateViewAboutZAngle As Double)

'CALCULATE POSITIONS OF THE TEXT, IF LINE POINTS LEFT, PUT IT ON THE RIGHT (ABOVE) OF THE LINE
   Dim midPoint As Point3d
   midPoint = CalcMidPoint(startPoint, endPoint)
   Dim dirPoint As Point3d
   dirPoint = midPoint
   Dim disPoint As Point3d
   disPoint = midPoint
   dirPoint.Y = dirPoint.Y + (characterSize + LineSpacing) / 2
   disPoint.Y = disPoint.Y - (characterSize + LineSpacing) / 2

'MOVE THE TEXT ELEMENTS INTO POSITION
   dirTextElement.origin = dirPoint
   disTextElement.origin = disPoint
  
'ROTATE THE TEXT ELEMENTS TO MATCH THE VIEW
   dirTextElement.RotateAboutZ midPoint, rotateViewAboutZAngle
   disTextElement.RotateAboutZ midPoint, rotateViewAboutZAngle

'ADD THE TEXT ELEMENTS TO THE FILE
   ActiveModelReference.AddElement dirTextElement
   dirTextElement.Redraw
   ActiveModelReference.AddElement disTextElement
   disTextElement.Redraw
End Sub

Attribute VB_Name = "IntersectchooserPimitive"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit

Implements IPrimitiveCommandEvents

Private RP1 As Point3d
Private Rad1 As Double
Private RP2 As Point3d
Private Rad2 As Double

Private int1 As Point3d
Private int2 As Point3d


Public Property Let RadiusPt1(radiusPoint As Point3d)
   RP1 = radiusPoint
End Property

Public Property Let RadiusPt2(radiusPoint As Point3d)
   RP2 = radiusPoint
End Property

Public Property Let Radius1(ByVal radius As Double)
   Rad1 = radius
End Property

Public Property Let Radius2(ByVal radius As Double)
   Rad2 = radius
End Property

Public Property Let IntersetionPt1(IntersetionPt As Point3d)
   int1 = IntersetionPt
End Property

Public Property Let IntersetionPt2(IntersetionPt As Point3d)
   int2 = IntersetionPt
End Property







Private Sub IPrimitiveCommandEvents_Cleanup()
End Sub






Private Sub IPrimitiveCommandEvents_DataPoint(point As Point3d, ByVal view As view)
   Dim closerIntersect As Point3d
   closerIntersect = closerInt(point, int1, int2)
   FrmArcArcInt.IntChosen closerIntersect
End Sub








Private Sub IPrimitiveCommandEvents_Dynamics(point As Point3d, ByVal view As view, ByVal DrawMode As MsdDrawingMode)
   Dim Arc1 As EllipseElement
   Set Arc1 = CreateEllipseElement2(Nothing, RP1, Rad1, Rad1, Matrix3dIdentity)
   Arc1.color = GetTetherColor()
   Arc1.Redraw DrawMode
   Dim Arc2 As EllipseElement
   Set Arc2 = CreateEllipseElement2(Arc1, RP2, Rad2, Rad2, Matrix3dIdentity)
   Arc2.Redraw DrawMode
   Dim closerIntersect As Point3d
   closerIntersect = closerInt(point, int1, int2)
   Dim lineTo1 As LineElement
   closerIntersect.z = RP1.z
   Set lineTo1 = CreateLineElement2(Arc1, RP1, closerIntersect)
   Dim lineTo2 As LineElement
   closerIntersect.z = RP2.z
   Set lineTo2 = CreateLineElement2(Arc1, RP2, closerIntersect)
   lineTo1.Redraw DrawMode
   lineTo2.Redraw DrawMode
End Sub


Private Function closerInt(pointer As Point3d, int1 As Point3d, int2 As Point3d) As Point3d
   Dim distTo1 As Double
   distTo1 = InverseHD(int1, pointer)
   Dim distTo2 As Double
   distTo2 = InverseHD(int2, pointer)
   If distTo1 < distTo2 Then
      closerInt = int1
   Else
      closerInt = int2
   End If
End Function









Private Sub IPrimitiveCommandEvents_Keyin(ByVal Keyin As String)

End Sub






Private Sub IPrimitiveCommandEvents_Reset()
   CommandState.StartDefaultCommand
   FrmArcArcInt.Show
End Sub







Private Sub IPrimitiveCommandEvents_Start()
   ShowCommand COMMAND_NAME_ARC_ARC_INT
   ShowPrompt "Choose intersection Point/Reset to cancel"
   CommandState.DisableAccuSnap
   CommandState.StartDynamics
End Sub

Attribute VB_Name = "LabelCoordLocateText"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit

Implements ILocateCommandEvents

Public hostForm As FrmLabelCoord

Private myLC As LocateCriteria

Private Sub ILocateCommandEvents_Accept(ByVal Element As Element, point As Point3d, ByVal view As view)

End Sub



Private Sub ILocateCommandEvents_Cleanup()
   FrmLabelCoord.NotifyOfClosing
   ClearCommandPromptArea
   CommandState.EnableAccuSnap
End Sub



Private Sub ILocateCommandEvents_Dynamics(point As Point3d, ByVal view As view, ByVal DrawMode As MsdDrawingMode)
   
End Sub



Private Sub ILocateCommandEvents_LocateFailed()
   FrmLabelCoord.SetNotOkayToClose
   CommandState.StartPrimitive New LabelCoordPrimitive
End Sub



Private Sub ILocateCommandEvents_LocateFilter(ByVal Element As Element, point As Point3d, Accepted As Boolean)
   Dim myEl As Element
   Set myEl = CommandState.GetLocatedElement(False)
   If myEl.IsTextElement Then
      hostForm.EnterText myEl.AsTextElement.text
   End If
   FrmLabelCoord.Show
   FrmLabelCoord.SetNotOkayToClose
   CommandState.StartPrimitive New LabelCoordPrimitive
   Accepted = False
End Sub



Private Sub ILocateCommandEvents_LocateReset()
   FrmLabelCoord.SetNotOkayToClose
   CommandState.StartPrimitive New LabelCoordPrimitive
End Sub



Private Sub ILocateCommandEvents_Start()
   FrmLabelCoord.NotifyOfOpenning

   Set myLC = CommandState.CreateLocateCriteria(False)
   myLC.ExcludeAllTypes
   myLC.IncludeType msdElementTypeText
   myLC.IncludeType msdElementTypeTextNode
   myLC.IncludeType msdElementTypeCellHeader
   CommandState.SetLocateCriteria myLC
   
   ShowCommand COMMAND_NAME_LABELCOORD
   ShowPrompt "Pick Text Element/Reset"

   ActiveModelReference.UnselectAllElements
   
   FrmLabelCoord.Hide

   CommandState.DisableAccuSnap
End Sub

Attribute VB_Name = "LabelCoordPrimitive"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit

Implements IPrimitiveCommandEvents

Private ThePointPicked As Point3d
Private isPicked As Boolean


Private Sub IPrimitiveCommandEvents_Cleanup()
   FrmLabelCoord.NotifyOfClosing
   CommandState.EnableAccuSnap
End Sub



Private Sub IPrimitiveCommandEvents_DataPoint(point As Point3d, ByVal view As view)
   If isPicked = False Then
'POINT NOW PICKED, ASSIGN POINT AND CALCULATE VALUES
'INITIALIZE VARIABLES
      ThePointPicked = point
      isPicked = True 'set flag

'GIVE INSTRUCTIONS
      PromptUser

'START INTERACTIVE PLACEMENT
      CommandState.DisableAccuSnap
      CommandState.StartDynamics
   Else
'POINT WAS PICKED, NOW DRAW CELL
'CHECK IF OKAY TO DRAW
      If ActiveModelReference.IsReadOnly = True Then
          ReadOnlyErrorMess
          Exit Sub
      End If

      isPicked = False 'reset flag

      Dim anchorPoint As Point3d
      anchorPoint = ThePointPicked
      Dim CurrentPosition As Point3d
      CurrentPosition = point
      Dim charSize As Double
      charSize = GetCharSize()
      Dim textTemplate As TextElement
      Set textTemplate = FrmLabelCoord.GetTextTemp()
   
'DRAW THE LEADER
      Dim useLeftCell As Boolean
      Dim labelPoint As Point3d
      Dim ViewAngleRadians As Double
      ViewAngleRadians = TheViewRotRadians(view)
      Dim leaderCell As CellElement
      Set leaderCell = CreateArrowLeader(anchorPoint, _
                                         CurrentPosition, _
                                         charSize, _
                                         textTemplate, _
                                         ViewAngleRadians, _
                                         0.6, _
                                         0.9, _
                                         useLeftCell, _
                                         labelPoint, 1)
      
      ActiveModelReference.AddElement leaderCell
      leaderCell.Redraw
      
'DRAW THE COORDINATE CELL
      Dim coordCell As CellElement
      Set coordCell = CreateCoordinateCell(labelPoint, useLeftCell, charSize, textTemplate, ViewAngleRadians)
      ActiveModelReference.AddElement coordCell
      coordCell.Redraw

'WRITE FILE IF OPTION CHOSEN
      If FrmLabelCoord.OverrideCheckBox.value Then
         If IsNumeric(FrmLabelCoord.UseElevTextBox.text) Then
            anchorPoint.z = CDbl(FrmLabelCoord.UseElevTextBox.text)
         End If
      End If
      WriteFileRecord anchorPoint
   
'FINISHED, START A NEW CYCLE
      isPicked = False
      CommandState.StopDynamics
      CommandState.EnableAccuSnap
      PromptUser
   End If
End Sub



Private Sub WriteFileRecord(point As Point3d)
'WRITE FILE IF OPTION CHOSEN
   Dim OutputFilename As String
   OutputFilename = GetSetting(APP_NAME, SECTION_LABEL_COORD, KEY_FILENAME, "")
   If OutputFilename <> "" And FrmLabelCoord.OutFileCheckBox.value = True Then
      Dim CoordinateRecordString As String
      CoordinateRecordString = CreateCoordinateString(point)
      WritePointToFile CoordinateRecordString, OutputFilename
   End If
End Sub



Private Function CreateCoordinateString(point As Point3d) As String
'MAKE WORKING COPY
   Dim pointPicked As Point3d
   pointPicked = point

'CREATE THE STRING
   Dim NEprecision As Integer
   NEprecision = CInt(FrmLabelCoord.PrecisionComboBox.text)
   Dim ElevationPrecision As Integer
   ElevationPrecision = FrmLabelCoord.GetElPrec()
   Dim RecordString As String
   RecordString = FrmLabelCoord.PointNumTextBox.text
   RecordString = RecordString & "," _
                  & FormatNumber(Round(pointPicked.Y, NEprecision), NEprecision, vbTrue, vbFalse, vbFalse) & "," _
                  & FormatNumber(Round(pointPicked.X, NEprecision), NEprecision, vbTrue, vbFalse, vbFalse) & "," _
                  & FormatNumber(Round(pointPicked.z, ElevationPrecision), ElevationPrecision, vbTrue, vbFalse, vbFalse) & "," _
                  & FrmLabelCoord.DescTextBox.text
   CreateCoordinateString = RecordString
End Function



Private Sub WritePointToFile(RecordString As String, OutputFilename As String)
   If WriteStringToFile(RecordString, OutputFilename) Then
'UPDATE FIELD
      FrmLabelCoord.PointNumTextBox.text = IncPointName(FrmLabelCoord.PointNumTextBox.text)
'UPDATE SETTINGS
      SaveSetting APP_NAME, SECTION_LABEL_COORD, KEY_POINTNAME, FrmLabelCoord.PointNumTextBox.text
   End If
End Sub



Private Function WriteStringToFile(RecordString As String, OutputFilename As String) As Boolean
'RETURNS TRUE IF SUCCESSFUL
On Error GoTo errhnd

'write to file here
   Dim FFILE As Long
   FFILE = FreeFile
   Open OutputFilename For Append As #FFILE
      Print #FFILE, RecordString
   Close #FFILE
   WriteStringToFile = True
   Exit Function

errhnd:
   WriteStringToFile = False
   ErrorMess Err.Number
   Err.Clear
End Function



Private Sub IPrimitiveCommandEvents_Dynamics(point As Point3d, ByVal view As view, ByVal DrawMode As MsdDrawingMode)
'INITIALIZE VARIABLES, GET METRICS
   Dim anchorPoint As Point3d
   anchorPoint = ThePointPicked
   Dim CurrentPosition As Point3d
   CurrentPosition = point
   Dim charSize As Double
   charSize = GetCharSize()
   Dim textTemplate As TextElement
   Set textTemplate = FrmLabelCoord.GetTextTemp()

'DRAW THE LEADER
   Dim useLeftCell As Boolean
   Dim labelPoint As Point3d
   Dim ViewAngleRadians As Double
   ViewAngleRadians = TheViewRotRadians(view)
   Dim leaderCell As CellElement
   Set leaderCell = CreateArrowLeader(anchorPoint, _
                                      CurrentPosition, _
                                      charSize, _
                                      textTemplate, _
                                      ViewAngleRadians, _
                                      0.6, _
                                      0.9, _
                                      useLeftCell, _
                                      labelPoint, 1)
   leaderCell.Redraw DrawMode

'DRAW THE COORDINATE CELL
   Dim coordCell As CellElement
   Set coordCell = CreateCoordinateCell(labelPoint, useLeftCell, charSize, textTemplate, ViewAngleRadians)
   coordCell.Redraw DrawMode
End Sub



Private Sub IPrimitiveCommandEvents_Keyin(ByVal Keyin As String)

End Sub



Private Sub IPrimitiveCommandEvents_Reset()
   If isPicked = False Then
      CommandState.StartDefaultCommand
   Else
      isPicked = False
      CommandState.StopDynamics
      CommandState.EnableAccuSnap
      PromptUser
   End If
End Sub



Private Sub IPrimitiveCommandEvents_Start()
   FrmLabelCoord.NotifyOfOpenning
   FrmLabelCoord.Show
   isPicked = False
   ActiveModelReference.UnselectAllElements
   PromptUser
   CommandState.EnableAccuSnap
End Sub



Private Function CreateCoordinateCell(InsertionPoint As Point3d, _
                                      ByVal IsLeftCell As Boolean, _
                                      ByVal characterSize As Double, _
                                      ByVal textTemplate As Element, _
                                      ByVal rotAngleRad As Double) As CellElement
'MAKE WORKING COPY OF POINT
   Dim iPoint As Point3d
   iPoint = InsertionPoint
                                      
'CALCULATE METRICS
   Dim ElevationPrecision As Integer
   ElevationPrecision = FrmLabelCoord.GetElPrec()
   Dim NEprecision As Long
   NEprecision = CInt(FrmLabelCoord.PrecisionComboBox.text)
   Dim LineSpacing As Double
   LineSpacing = characterSize / 3#
                                      
'GET VALUES
   Dim northing As Double
   northing = ThePointPicked.Y
   Dim easting As Double
   easting = ThePointPicked.X
   Dim DescString As String
   DescString = FrmLabelCoord.DescTextBox.text
   Dim elevation As Double
   elevation = ThePointPicked.z
'IF ELEVATION OVERRIDE OPTION IS CHOSEN, CHANGE ELEVATION
   If FrmLabelCoord.OverrideCheckBox.value = True Then
      elevation = CDbl(FrmLabelCoord.UseElevTextBox.text)
   End If

'MAKE THE VALUES INTO STRINGS
   Dim NorthingString As String
   NorthingString = DoubleToNorthingString(northing, NEprecision)
   Dim EastingString As String
   EastingString = DoubleToEastingString(easting, NEprecision)
   Dim elevationString As String
   elevationString = "El.=" & FormatNumber(elevation, ElevationPrecision)
   Dim PointNumString As String
   PointNumString = FrmLabelCoord.PointNumTextBox.text

'GENERATE TEXT ELEMENTS
'NORTHING TEXT ELEMENT
   Dim northingText As TextElement
   Set northingText = CreateTextElement1(textTemplate, NorthingString, iPoint, Matrix3dIdentity)

'EASTING TEXT ELEMENT
   Dim eastingText As TextElement
   Set eastingText = CreateTextElement1(textTemplate, EastingString, iPoint, Matrix3dIdentity)
      
'ELEVATION TEXT ELEMENT
   Dim ElevationText As TextElement
   Set ElevationText = CreateTextElement1(textTemplate, elevationString, iPoint, Matrix3dIdentity)

'POINT NUMBER TEXT ELEMENT
   Dim pointNumText As TextElement
   Set pointNumText = CreateTextElement1(textTemplate, PointNumString, iPoint, Matrix3dIdentity)

'POINT DESCRIPTION TEXT ELEMENT
   If DescString = "" Then
      Dim dString As String
      dString = " "
   Else
      dString = DescString
   End If
   Dim DescriptionText As TextElement
   Set DescriptionText = CreateTextElement1(textTemplate, dString, iPoint, Matrix3dIdentity)

'DETERMINE CELL WIDTH AND HEIGHT
   Dim CellWidth As Double
   CellWidth = 0
   Dim LineCount As Long
   LineCount = 0
   Dim lineHeight As Double
   
   If FrmLabelCoord.OutFileCheckBox.value Then
      Dim PointNumTextMetrics As Point2d
      pointNumText.GetTotalTextSize PointNumTextMetrics.X, PointNumTextMetrics.Y
      CellWidth = Max(CellWidth, PointNumTextMetrics.X)
      LineCount = LineCount + 1
      lineHeight = PointNumTextMetrics.Y
   End If
   
   If FrmLabelCoord.ShowDescCheckBox.value Then
      Dim DescriptionTextMetrics As Point2d
      DescriptionText.GetTotalTextSize DescriptionTextMetrics.X, DescriptionTextMetrics.Y
      CellWidth = Max(CellWidth, DescriptionTextMetrics.X)
      LineCount = LineCount + 1
      lineHeight = DescriptionTextMetrics.Y
   End If

   If FrmLabelCoord.NEandNumCheckBox.value Or (FrmLabelCoord.OutFileCheckBox.value = False) Then
      Dim NorthingTextMetrics As Point2d
      northingText.GetTotalTextSize NorthingTextMetrics.X, NorthingTextMetrics.Y
      CellWidth = Max(CellWidth, NorthingTextMetrics.X)
      
      Dim EastingTextMetrics As Point2d
      eastingText.GetTotalTextSize EastingTextMetrics.X, EastingTextMetrics.Y
      CellWidth = Max(CellWidth, EastingTextMetrics.X)
      LineCount = LineCount + 2
      lineHeight = EastingTextMetrics.Y
   End If
   
   If FrmLabelCoord.ElevationCheckBox.value Then
      Dim ElevationTextMetrics As Point2d
      ElevationText.GetTotalTextSize ElevationTextMetrics.X, ElevationTextMetrics.Y
      CellWidth = Max(CellWidth, ElevationTextMetrics.X)
      LineCount = LineCount + 1
      lineHeight = ElevationTextMetrics.Y
   End If
   
'POSITION ELEMENTS AND ADD THEM TO ARRAY
   Dim NewPosition As Point3d
   NewPosition = iPoint

'CALCULATE NEW POSITION FOR HIGHEST ELEMENT
   NewPosition.Y = NewPosition.Y + ((lineHeight + LineSpacing) / 2#) * (LineCount - 1)

'CALCUATE X FOR LEFT OR RIGHT OF INSERTION POINT
   Dim LeftOffset As Double
   LeftOffset = 0#
   If Not IsLeftCell Then
      LeftOffset = CellWidth
   End If
   NewPosition.X = NewPosition.X + LeftOffset
   Dim nothingInArray As Boolean
   nothingInArray = True
   Dim cellArray() As Element
   If FrmLabelCoord.OutFileCheckBox.value Then
      Dim NewPointNumPos As Point3d
      NewPointNumPos = NewPosition
      If FrmLabelCoord.AlignLeftOption.value Then
         NewPointNumPos.X = NewPosition.X + (PointNumTextMetrics.X - CellWidth)
      End If
      pointNumText.origin = NewPointNumPos
      AddToArray nothingInArray, cellArray, pointNumText
      NewPosition.Y = NewPosition.Y - (LineSpacing + PointNumTextMetrics.Y)
   End If

   If FrmLabelCoord.ShowDescCheckBox.value Then
      Dim NewDescPos As Point3d
      NewDescPos = NewPosition
      If FrmLabelCoord.AlignLeftOption.value Then
         NewDescPos.X = NewPosition.X + (DescriptionTextMetrics.X - CellWidth)
      End If
      DescriptionText.origin = NewDescPos
      AddToArray nothingInArray, cellArray, DescriptionText
      NewPosition.Y = NewPosition.Y - (LineSpacing + DescriptionTextMetrics.Y)
   End If

   If FrmLabelCoord.NEandNumCheckBox.value Or (FrmLabelCoord.OutFileCheckBox.value = False) Then
      Dim NEoffset As Double
      NEoffset = Max(NorthingTextMetrics.X, EastingTextMetrics.X) - CellWidth
      Dim NewNorthPos As Point3d
      NewNorthPos = NewPosition
      If FrmLabelCoord.AlignLeftOption.value Then
         NewNorthPos.X = NewPosition.X + NEoffset
      End If
      northingText.origin = NewNorthPos
      AddToArray nothingInArray, cellArray, northingText
      NewPosition.Y = NewPosition.Y - (LineSpacing + NorthingTextMetrics.Y)
      
      Dim NewEastPos As Point3d
      NewEastPos = NewPosition
      If FrmLabelCoord.AlignLeftOption.value Then
         NewEastPos.X = NewPosition.X + NEoffset
      End If
      eastingText.origin = NewEastPos
      AddToArray nothingInArray, cellArray, eastingText
      NewPosition.Y = NewPosition.Y - (LineSpacing + EastingTextMetrics.Y)
   End If
   
   If FrmLabelCoord.ElevationCheckBox.value Then
      Dim NewElPos As Point3d
      NewElPos = NewPosition
      If FrmLabelCoord.AlignLeftOption.value Then
         NewElPos.X = NewPosition.X + (ElevationTextMetrics.X - CellWidth)
      End If
      ElevationText.origin = NewElPos
      AddToArray nothingInArray, cellArray, ElevationText
   End If
   
   Dim coordCell As CellElement
   Set coordCell = CreateCellElement1(vbNullString, cellArray, iPoint)
   coordCell.RotateAboutZ iPoint, rotAngleRad

   Set CreateCoordinateCell = coordCell
End Function



Private Sub AddToArray(ByRef nothingInArray As Boolean, cellArray() As Element, newElement As Element)
   If nothingInArray Then
      ReDim cellArray(0)
      Set cellArray(UBound(cellArray)) = newElement
      nothingInArray = False
   Else
      AddItToArray cellArray, newElement
   End If
End Sub



Private Sub PromptUser()
   ShowCommand COMMAND_NAME_LABELCOORD
   If isPicked Then
      ShowPrompt "Pick PLACEMENT of text/Reset"
   Else
      ShowPrompt "Pick POINT to label/Reset"
   End If
End Sub

Attribute VB_Name = "LabelCurveLocate"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit

Implements ILocateCommandEvents

Private myLC As LocateCriteria
Private OkayToCloseDialog As Boolean
Private MyCurveElement As Element

Private Const PROMPT_STRING_ARC = "Pick Curve/Reset to quit"


Private Sub ILocateCommandEvents_Accept(ByVal Element As Element, point As Point3d, ByVal view As view)
'DON'T CLOSE DIALOG BOX
   OkayToCloseDialog = False

'LAUNCH IPRIMITIVE
   Dim PlaceTheCurveData As New LabelCurvePrimitive
   PlaceTheCurveData.ElementToUse = MyCurveElement
   CommandState.StartPrimitive PlaceTheCurveData
End Sub

Private Sub ILocateCommandEvents_Cleanup()
   If OkayToCloseDialog Then
      Unload FrmLabelCurve
   End If
   ClearCommandPromptArea
   CommandState.EnableAccuSnap
End Sub

Private Sub ILocateCommandEvents_Dynamics(point As Point3d, ByVal view As view, ByVal DrawMode As MsdDrawingMode)

End Sub

Private Sub ILocateCommandEvents_LocateFailed()
   FrmLabelCurve.arcMode True
   ShowCommand COMMAND_NAME_LABEL_CURVE
   ShowPrompt PROMPT_STRING_ARC
End Sub

Private Sub ILocateCommandEvents_LocateFilter(ByVal myEl As Element, point As Point3d, Accepted As Boolean)
'INITIALIZE FLAG
   Accepted = False

'IS A LINSTRING
   If myEl.IsLineElement Then
     If Not IsSpiralElementLite(myEl) Then
        Exit Sub
     End If
     FrmLabelCurve.arcMode False
   End If

'IS AN ARC
   If myEl.IsArcElement Then
'MAKE SURE ELEMENT IS NOT ROTATED OFF OF THE X-Y PLANE
'change this method, too strict
'   Dim dummy As Double
'   If Not Matrix3dIsXYRotation(myEl.AsArcElement.rotation, dummy) Then
'      Exit Sub
'   End If
      Dim pcEl As Double
      pcEl = myEl.AsArcElement.startPoint.z
      Dim rpEl As Double
      rpEl = myEl.AsArcElement.CenterPoint.z
      Dim ptEl As Double
      ptEl = myEl.AsArcElement.endPoint.z
      If pcEl <> rpEl Or rpEl <> ptEl Then
         Exit Sub
      End If
   End If

'STORE ELEMENT POINTER
   Set MyCurveElement = myEl

   ShowCommand COMMAND_NAME_LABEL_CURVE
   ShowPrompt ACCEPT_RESET_STRING

'VALID ELEMENT
   Accepted = True
End Sub

Private Sub ILocateCommandEvents_LocateReset()
'EXIT COMMAND
   FrmLabelCurve.arcMode True
   CommandState.StartDefaultCommand
End Sub

Private Sub ILocateCommandEvents_Start()
'MAKE SURE NOTHING IS SELECTED
   ActiveModelReference.UnselectAllElements

'TURN ACCUSNAP OFF
   CommandState.DisableAccuSnap
   
'OPEN DIALOG BOX
   FrmLabelCurve.Show

'MAKE SURE EVERYTHING IS ON
   FrmLabelCurve.arcMode True

'SET LOCATE CRITERIA TO ONLY ARCS
   Set myLC = CommandState.CreateLocateCriteria(True)
   myLC.ExcludeAllTypes
   myLC.IncludeType msdElementTypeArc
   myLC.IncludeType msdElementTypeLineString
   CommandState.SetLocateCriteria myLC

'INITIALIZE FLAG
   OkayToCloseDialog = True

'COMMAND PROMPT
   ShowCommand COMMAND_NAME_LABEL_CURVE
   ShowPrompt PROMPT_STRING_ARC
End Sub

Attribute VB_Name = "LabelCurvePrimitive"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit

Implements IPrimitiveCommandEvents

Private Const PRECISION_LINEAR    As Long = 2
Private Const DEF_HEADING         As String = "Spiral Data"

Private MyElement                 As Element
Private OkayToCloseDialog         As Boolean

Private angleStyle                As Integer


Public Property Let ElementToUse(theElement As Element)
   Set MyElement = theElement
End Property



Private Sub IPrimitiveCommandEvents_Cleanup()
   ClearCommandPromptArea
   CommandState.EnableAccuSnap

'CLOSE DIALOG MAYBE
   If OkayToCloseDialog Then
      Unload FrmLabelCurve
   End If
End Sub



Private Sub IPrimitiveCommandEvents_DataPoint(point As Point3d, ByVal view As view)
   OkayToCloseDialog = False
   Dim DataCell As CellElement
   If MyElement.IsArcElement Then
      Set DataCell = MakeOurCurveDataCell(point, view)
   ElseIf MyElement.IsLineElement Then
      Set DataCell = MakeOurSpiralDataCell(point, view)
   End If
   ActiveModelReference.AddElement DataCell
   DataCell.Redraw
   CommandState.StartLocate New LabelCurveLocate
End Sub



Private Sub IPrimitiveCommandEvents_Dynamics(point As Point3d, ByVal view As view, ByVal DrawMode As MsdDrawingMode)

   Dim DataCell As CellElement
   If MyElement.IsArcElement Then
      Set DataCell = MakeOurCurveDataCell(point, view)
   ElseIf MyElement.IsLineElement Then
      Set DataCell = MakeOurSpiralDataCell(point, view)
   End If
   DataCell.Redraw DrawMode
End Sub



Private Sub IPrimitiveCommandEvents_Keyin(ByVal Keyin As String)

End Sub



Private Sub IPrimitiveCommandEvents_Reset()
   OkayToCloseDialog = False
   CommandState.StartLocate New LabelCurveLocate
End Sub



Private Sub IPrimitiveCommandEvents_Start()
   angleStyle = STYLE_ANGLE_CARET + STYLE_ANGLE_NO_00_SEC + STYLE_ANGLE_LEAD
   OkayToCloseDialog = True
   ShowCommand COMMAND_NAME_LABEL_CURVE
   ShowPrompt "Pick POSITITON for curve data/RESET"
   CommandState.DisableAccuSnap
   CommandState.StartDynamics
End Sub



Private Function MakeOurCurveDataCell(point As Point3d, view As view) As CellElement
'GET RADIUS
   Dim radius As Double
   radius = MyElement.AsArcElement.PrimaryRadius
'GET PRECISION
   Dim SecondsPrecision As Long
   SecondsPrecision = FrmLabelCurve.GetPrecision()
   
'CREATE DELTA STRING
   Dim deltaRadians As Double
   deltaRadians = Abs(MyElement.AsArcElement.SweepAngle)
   Dim deltaString As String
   deltaString = DegreesToAngleString(Degrees(deltaRadians), SecondsPrecision + 4, angleStyle)

'CREATE HALF DELTA STRING
   Dim degPart As Long
   Dim minPart As Long
   Dim secPart As Double
   Dim sugPrec As Long
   Dim deltaOver2 As Double
   If halfDelta(deltaString, degPart, minPart, secPart, sugPrec, deltaOver2) Then
      Dim halfDeltaString As String
      halfDeltaString = DegreesToAngleString(deltaOver2, sugPrec, angleStyle)
   Else
      halfDeltaString = "error"
   End If

'CREATE RADIUS STRING
   Dim radiusString As String
   radiusString = FormatNumber(radius, PRECISION_LINEAR, vbTrue, vbFalse, vbTrue)

'CREATE TANGENT STRING
   If deltaOver2 < 90# Then
      Dim tangentString As String
      tangentString = FormatNumber(Tan(Radians(deltaOver2)) * radius, PRECISION_LINEAR, vbTrue, vbFalse, vbTrue)
   Else
      tangentString = "N/A"
   End If

'CREATE LONG CHORD STRING
   Dim longChord As Double
   longChord = radius * Sin(Radians(deltaOver2)) * 2#
   Dim longChordString As String
   longChordString = FormatNumber(longChord, PRECISION_LINEAR, vbTrue, vbFalse, vbTrue)

'CREATE CURVE LENGTH STRING
   Dim lengthOfCurve As Double
   lengthOfCurve = Round(Radians(deltaOver2 + deltaOver2) * radius, PRECISION_LINEAR)
   Dim curveLengthString As String
   curveLengthString = FormatNumber(lengthOfCurve, PRECISION_LINEAR, vbTrue, vbFalse, vbTrue)

'CREATE TEXT TEMPLATE
   Dim template As TextElement
   Set template = FrmLabelCurve.textTemplate()

'RETURN THE CURVE DATA CELL
   Set MakeOurCurveDataCell = CreateCurveDataCell(point, _
                                                  TheViewRotRadians(view), _
                                                  template, _
                                                  deltaString, _
                                                  halfDeltaString, _
                                                  radiusString, _
                                                  tangentString, _
                                                  longChordString, _
                                                  curveLengthString, _
                                                  FrmLabelCurve.GetPrefix(), _
                                                  FrmLabelCurve.GetHeading(), _
                                                  FrmLabelCurve.GetAlignRight())
End Function


Private Function MakeOurSpiralDataCell(point As Point3d, view As view) As CellElement
'GET THE LENGTH
   Dim spiralLengthString As String
   If Not GetSurveyorToolsTagValue(MyElement, TAG_NAME_LENGTH, spiralLengthString) Then
      Exit Function
   End If

'GET THE SPIRAL ANGLE
   Dim spiralAngleString As String
   If Not GetSurveyorToolsTagValue(MyElement, TAG_NAME_SPIRAL_ANGLE, spiralAngleString) Then
      Exit Function
   End If

'CREATE TEXT TEMPLATE
   Dim template As TextElement
   Set template = FrmLabelCurve.textTemplate()
   Set MakeOurSpiralDataCell = CreateSpiralData(spiralAngleString, _
                                                spiralLengthString, _
                                                FrmLabelCurve.CurveDataPrefixTextBox.text, _
                                                DEF_HEADING, _
                                                point, _
                                                template, _
                                                TheViewRotRadians(view))
End Function

Attribute VB_Name = "LabelLineLocate"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit

Implements ILocateCommandEvents

Private myLC As LocateCriteria
Private OkayToCloseDialog As Boolean

Private Const PROMPT_STRING_LINE = "Pick LINE to label/Reset"

Private Sub ILocateCommandEvents_Accept(ByVal Element As Element, point As Point3d, ByVal view As view)
   OkayToCloseDialog = False

'LAUNCH IPRIMITIVE
   Dim ChooseSideOfLine As New LabelLinePrimitive
   ChooseSideOfLine.LineElementToUse = Element
   CommandState.StartPrimitive ChooseSideOfLine
End Sub



Private Sub ILocateCommandEvents_Cleanup()
'CLEAR PROMPT AREA
   ClearCommandPromptArea

'CLOSE DIALOG MAYBE
   If OkayToCloseDialog Then
      Unload FrmLabelLine
   End If

   CommandState.EnableAccuSnap
End Sub



Private Sub ILocateCommandEvents_Dynamics(point As Point3d, ByVal view As view, ByVal DrawMode As MsdDrawingMode)
End Sub



Private Sub ILocateCommandEvents_LocateFailed()
   ShowCommand COMMAND_NAME_LABEL_LINE
   ShowPrompt PROMPT_STRING_LINE
End Sub



Private Sub ILocateCommandEvents_LocateFilter(ByVal Element As Element, point As Point3d, Accepted As Boolean)
   Accepted = False
   Dim SelectedLine As LineElement
   Set SelectedLine = Element
   Select Case SelectedLine.Type
      Case msdElementTypeLine
         If CheckLine(SelectedLine) Then
            Accepted = True
            ShowCommand COMMAND_NAME_LABEL_LINE
            ShowPrompt ACCEPT_RESET_STRING
         End If
   End Select
End Sub



Private Sub ILocateCommandEvents_LocateReset()
   CommandState.StartDefaultCommand
End Sub



Private Sub ILocateCommandEvents_Start()
   FrmLabelLine.Show
   OkayToCloseDialog = True
   ActiveModelReference.UnselectAllElements
   
   Set myLC = CommandState.CreateLocateCriteria(True)
   myLC.ExcludeAllTypes
   myLC.IncludeType msdElementTypeLine
   CommandState.SetLocateCriteria myLC
   
   CommandState.DisableAccuSnap
   
   ShowCommand COMMAND_NAME_LABEL_LINE
   ShowPrompt PROMPT_STRING_LINE
End Sub



Private Function CheckLine(OldLine As LineElement) As Boolean
'RETURNS TRUE IF OKAY FOR LABELLING
'INITIALIZE FLAG
   CheckLine = False
   
'DO SOME CHECKING
   If OldLine.VerticesCount <> 2 Then
      Exit Function
   End If
   CheckLine = True
End Function

Attribute VB_Name = "LabelLinePrimitive"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit

Implements IPrimitiveCommandEvents

Private MyLineElement As LineElement
Private OkayToCloseDialog As Boolean


Public Property Let LineElementToUse(theLineElement As LineElement)
   Set MyLineElement = theLineElement
End Property



Private Sub IPrimitiveCommandEvents_Cleanup()
   ClearCommandPromptArea

'CLOSE DIALOG MAYBE
   If OkayToCloseDialog Then
      Unload FrmLabelLine
   End If
      
'TURN ACCUSNAP BACK ON
   CommandState.EnableAccuSnap
End Sub



Private Sub IPrimitiveCommandEvents_DataPoint(point As Point3d, ByVal view As view)
   DrawLineLabel point, MyLineElement, view, True
   OkayToCloseDialog = False
   CommandState.StartLocate New LabelLineLocate
End Sub



Private Sub IPrimitiveCommandEvents_Dynamics(point As Point3d, ByVal view As view, ByVal DrawMode As MsdDrawingMode)
   DrawLineLabel point, MyLineElement, view, False, DrawMode
End Sub



Private Sub IPrimitiveCommandEvents_Keyin(ByVal Keyin As String)

End Sub



Private Sub IPrimitiveCommandEvents_Reset()
   OkayToCloseDialog = False
   CommandState.StartLocate New LabelLineLocate
End Sub



Private Sub IPrimitiveCommandEvents_Start()
   OkayToCloseDialog = True

   ShowCommand COMMAND_NAME_LABEL_LINE
   ShowPrompt "Pick POSITION of label/Reset"
   
   CommandState.DisableAccuSnap
   CommandState.StartDynamics
End Sub



Private Sub DrawLineLabel(PointerPosition As Point3d, _
                          theLine As LineElement, _
                          ByVal TheView As view, _
                          ByVal makePermanent As Boolean, _
                          Optional ByVal DrawMode As MsdDrawingMode = msdDrawingModeNormal)

'GET DESIRED STYLE OF LABEL
   Select Case FrmLabelLine.LabelOption()
      Case OPTION_AZ_DIST
         If FrmLabelLine.CheckBoxOverUnder.value Then
'STYLE DIRECTION AND DISTANCE OVER AND UNDER
            DrawDirDistOU PointerPosition, theLine, TheView, makePermanent, DrawMode
         Else
'STYLE DIRECTION AND DISTANCE
            DrawDirDistance PointerPosition, theLine, TheView, makePermanent, DrawMode
         End If
      Case OPTION_AZ
'STYLE DIRECTION ONLY
         DrawDirection PointerPosition, theLine, TheView, makePermanent, DrawMode
      Case Else
'STYLE DISTANCE ONLY
         DrawDistance PointerPosition, theLine, TheView, makePermanent, DrawMode
   End Select
End Sub



Private Sub CreateTextElements(theLineElement As LineElement, _
                               ByRef dirTextElFwd As TextElement, _
                               ByRef dirTextFwdMet As Point2d, _
                               ByRef dirTextElBk As TextElement, _
                               ByRef dirTextBxMet As Point2d, _
                               ByRef distTextEl As TextElement, _
                               ByRef distTextMet As Point2d, _
                               ByRef sAzFwdLine As Double, _
                               ByRef lineLength As Double, _
                               ByRef charSize As Double, _
                               ByRef arrowLength As Double)
'GET AZIMUTH AND DISTANCE OF LINE
   Inverse theLineElement.startPoint, theLineElement.endPoint, sAzFwdLine, lineLength
   
'GET TEXT TEMPLATE
   Dim template As TextElement
   Set template = FrmLabelLine.textTemplate()

'GET ANGLE PRECISION
   Dim anglePrec As Long
   Select Case FrmLabelLine.DirPrec()
      Case OPTION_PREC_ANG_SEC
         anglePrec = 4
      Case OPTION_PREC_ANG_SEC1
         anglePrec = 5
      Case OPTION_PREC_ANG_SEC01
         anglePrec = 6
      Case OPTION_PREC_ANG_SEC001
         anglePrec = 7
   End Select
   
'GENERATE ANGLE STYLE
   Dim angleStyle As Integer
   angleStyle = STYLE_ANGLE_SPACE Or STYLE_ANGLE_LEAD Or STYLE_ANGLE_CARET
   Select Case FrmLabelLine.LeaveOffOption()
      Case OPTION_NO_00
         angleStyle = angleStyle Or STYLE_ANGLE_NO_00_SEC
      Case OPTION_NO_00_00
         angleStyle = angleStyle Or STYLE_ANGLE_NO_00_MIN
   End Select

'GET DIRECTION TYPE
   If FrmLabelLine.dirType() = OPTION_DIR_TYPE_AZIMUTH Then
      Dim dirType As Integer
      dirType = DIR_TYPE_AZIMUTH
   Else
      dirType = DIR_TYPE_BEARING
   End If

'CREATE ANGLE TEXT ELEMENTS
   Dim dirFwdString As String
   dirFwdString = SAzToDirectionStr(sAzFwdLine, anglePrec, dirType, angleStyle)
   Set dirTextElFwd = CreateTextElement1(template, dirFwdString, theLineElement.startPoint, Matrix3dIdentity)
   Dim sAzBkLine As Double
   sAzBkLine = InverseAzimuth(theLineElement.endPoint, theLineElement.startPoint)
   Dim dirBkString As String
   dirFwdString = SAzToDirectionStr(sAzBkLine, anglePrec, dirType, angleStyle)
   Set dirTextElBk = CreateTextElement1(template, dirFwdString, theLineElement.startPoint, Matrix3dIdentity)

'GET SIZES OF THE TEXT ELEMENT
   dirTextElFwd.GetTotalTextSize dirTextFwdMet.X, dirTextFwdMet.Y
   dirTextElBk.GetTotalTextSize dirTextBxMet.X, dirTextBxMet.Y

'GET DITANCE PRECISION
   Dim distPrec As Long
   distPrec = 0
   Select Case FrmLabelLine.distPrec()
      Case OPTION_PREC_DIST_FT01
         distPrec = 2
      Case OPTION_PREC_DIST_FT001
         distPrec = 3
      Case OPTION_PREC_DIST_FT0001
         distPrec = 4
      Case OPTION_PREC_DIST_FT00001
         distPrec = 5
   End Select

'CREATE DISTANCE TEXT ELEMENT
   Dim DistString As String
   DistString = FormatNumber(lineLength, distPrec, vbTrue, vbFalse, vbTrue)

'GET SIZE OF TEXT ELEMENT
   Set distTextEl = CreateTextElement1(template, DistString, theLineElement.startPoint, Matrix3dIdentity)
   distTextEl.GetTotalTextSize distTextMet.X, distTextMet.Y

'GET CHARACTER SIZE
   charSize = GetCharSize()
   
'CALCULATE ARROW LENGTH
   arrowLength = ARROW_LENGTH * charSize
End Sub



Private Sub relativeToLine(theLineElement As LineElement, _
                           sAzFwdLine As Double, _
                           TheView As view, _
                           PointerPos As Point3d, _
                           ByRef forward As Boolean, _
                           ByRef aboveLine As Boolean, _
                           ByRef pointsLeft As Boolean, _
                           ByRef arrowIsLeft As Boolean)
   Dim midPoint As Point3d
   midPoint = CalcMidPoint(theLineElement.startPoint, theLineElement.endPoint)
   Dim sAzToPointer As Double
   sAzToPointer = InverseAzimuth(midPoint, PointerPos)
   Dim relativeAngle As Double
   relativeAngle = To360(sAzFwdLine, sAzToPointer)
   If relativeAngle > 90# And relativeAngle <= 270# Then
      forward = True
   Else
      forward = False
   End If
   pointsLeft = linePointsLeft(sAzFwdLine, TheViewRotRadians(TheView))
   If relativeAngle < 180 Then
      aboveLine = Not pointsLeft
   Else
      aboveLine = pointsLeft
   End If
   If pointsLeft Then
      arrowIsLeft = forward
   Else
      arrowIsLeft = Not forward
   End If
End Sub



Private Function CalcRotAngle(sAzFwdLine As Double, linePointsLeft As Boolean) As Double
'CALCULATE ROTATION ANGLE
   If linePointsLeft Then
      CalcRotAngle = -Radians(sAzFwdLine - 90#)
   Else
      CalcRotAngle = -Radians(sAzFwdLine - 270#)
   End If
End Function



Private Sub CalcInsertPoint(theLine As LineElement, _
                            charSize As Double, _
                            above As Boolean, _
                            ByRef LineSpacing As Double, _
                            ByRef moveOffLine As Double, _
                            ByRef insertPoint As Point3d)
   LineSpacing = charSize / 3#
   moveOffLine = LineSpacing + charSize / 2#
   If Not above Then
      moveOffLine = -moveOffLine
   End If
   insertPoint = theLine.startPoint
   insertPoint.z = (theLine.startPoint.z + theLine.endPoint.z) / 2#
   insertPoint.Y = insertPoint.Y + moveOffLine
End Sub



Private Sub DrawDirDistOU(CurrentPosition As Point3d, _
                          theLine As LineElement, _
                          TheView As view, _
                          makePermanent As Boolean, _
                          ByVal DrawMode As MsdDrawingMode)

'GET TEXT AND IT'S SIZES
   Dim charSize As Double
   Dim arrowLength As Double
   Dim dirTextElFwd As TextElement
   Dim dirTextFwdMet As Point2d
   Dim dirTextElBk As TextElement
   Dim dirTextBxMet As Point2d
   Dim distTextEl As TextElement
   Dim distTextMet As Point2d
   Dim sAzFwdLine As Double
   Dim lineLength As Double
   CreateTextElements theLine, _
                      dirTextElFwd, _
                      dirTextFwdMet, _
                      dirTextElBk, _
                      dirTextBxMet, _
                      distTextEl, _
                      distTextMet, _
                      sAzFwdLine, _
                      lineLength, _
                      charSize, _
                      arrowLength

'IF FORCE LEADER LINE, DO LEADER LINE
   If FrmLabelLine.LeaderCheckBox.value Then
'GO TO LEADER
      LeaderDrawDirDist CurrentPosition, theLine, TheView, makePermanent, DrawMode, True
      Exit Sub
   End If

'CHECK THE DISTANCE TEXT FIT
   If (distTextMet.X + charSize * 2#) > lineLength Then
'NO FIT, GO TO LEADER
      LeaderDrawDirDist CurrentPosition, theLine, TheView, makePermanent, DrawMode, True
      Exit Sub
   End If

'CHECK THE DIRECTION CELL FIT
   If (Max(dirTextFwdMet.X, dirTextBxMet.X) + charSize * 3# + arrowLength) > lineLength Then
'NO FIT, GO TO LEADER
      LeaderDrawDirDist CurrentPosition, theLine, TheView, makePermanent, DrawMode, True
      Exit Sub
   End If

'HOW TO PLACE THE LABELS
   Dim forward As Boolean
   Dim above As Boolean
   Dim pointsLeft As Boolean
   Dim arrowIsLeft As Boolean
   relativeToLine theLine, sAzFwdLine, TheView, CurrentPosition, forward, above, pointsLeft, arrowIsLeft

'CALCULATE INSERT POINTS
   Dim LineSpacing As Double
   Dim moveOffLine As Double
   Dim dirInsertPoint As Point3d
   CalcInsertPoint theLine, charSize, above, LineSpacing, moveOffLine, dirInsertPoint
   Dim distInsertPoint As Point3d
   distInsertPoint = theLine.startPoint
   distInsertPoint.Y = distInsertPoint.Y - moveOffLine
   distInsertPoint.z = dirInsertPoint.z
   Dim distEndSpace As Double
   distEndSpace = (lineLength - distTextMet.X) / 2#
   If pointsLeft Then
      distInsertPoint.X = distInsertPoint.X - (distEndSpace + distTextMet.X)
   Else
      distInsertPoint.X = distInsertPoint.X + distEndSpace
   End If

'CALCULATE ROTATION ANGLE
   Dim rotateToAzim As Double
   rotateToAzim = CalcRotAngle(sAzFwdLine, pointsLeft)

'MOVE TEXT
   distTextEl.origin = distInsertPoint
   distTextEl.RotateAboutZ theLine.startPoint, rotateToAzim

'CREATE DIRECTION CELL
   If forward Then
      Dim dirTextLen As Double
      dirTextLen = dirTextFwdMet.X
      Dim DirTextEl As TextElement
      Set DirTextEl = dirTextElFwd
   Else
      dirTextLen = dirTextBxMet.X
      Set DirTextEl = dirTextElBk
   End If
   Dim endSpace As Double
   endSpace = (lineLength - (dirTextLen + charSize + arrowLength)) / 2#
   If pointsLeft Then
      dirInsertPoint.X = dirInsertPoint.X - (dirTextLen + charSize + arrowLength + endSpace)
   Else
      dirInsertPoint.X = dirInsertPoint.X + endSpace
   End If
   Dim ArrowInsertPoint As Point3d
   ArrowInsertPoint = dirInsertPoint
   ArrowInsertPoint.X = ArrowInsertPoint.X + dirTextLen + charSize
   Dim ArrowCell As CellElement
   Set ArrowCell = MyCreateArrowCell(ArrowInsertPoint, charSize, arrowIsLeft, DirTextEl)
   DirTextEl.origin = dirInsertPoint
   Dim arrayForCell(2) As Element
   Set arrayForCell(0) = DirTextEl
   Set arrayForCell(1) = ArrowCell
   Dim dirCell As CellElement
   Set dirCell = CreateCellElement1(vbNullString, arrayForCell, dirInsertPoint)
   dirCell.RotateAboutZ theLine.startPoint, rotateToAzim

'DRAW THE ELEMENT
   If makePermanent Then
      Dim lineID As DLong
      Dim lineIDString As String
      If GetTheElementID(theLine, lineID, lineIDString) Then
'DELETE OLD LABELS
         DeletePreviousLabelElements lineIDString
'ADD NEW ONES
         ActiveModelReference.AddElement dirCell
         ActiveModelReference.AddElement distTextEl
         AddLabelLineAutoDeleteTags dirCell, lineIDString
         AddLabelLineAutoDeleteTags distTextEl, lineIDString
      Else
         ActiveModelReference.AddElement dirCell
         ActiveModelReference.AddElement distTextEl
      End If
   End If
   dirCell.Redraw DrawMode
   distTextEl.Redraw DrawMode
End Sub



Private Sub DrawDirDistance(CurrentPosition As Point3d, _
                            theLine As LineElement, _
                            TheView As view, _
                            makePermanent As Boolean, _
                            ByVal DrawMode As MsdDrawingMode)
'GET TEXT AND IT'S SIZES
   Dim charSize As Double
   Dim arrowLength As Double
   Dim dirTextElFwd As TextElement
   Dim dirTextFwdMet As Point2d
   Dim dirTextElBk As TextElement
   Dim dirTextBxMet As Point2d
   Dim distTextEl As TextElement
   Dim distTextMet As Point2d
   Dim sAzFwdLine As Double
   Dim lineLength As Double
   CreateTextElements theLine, _
                      dirTextElFwd, _
                      dirTextFwdMet, _
                      dirTextElBk, _
                      dirTextBxMet, _
                      distTextEl, _
                      distTextMet, _
                      sAzFwdLine, _
                      lineLength, _
                      charSize, _
                      arrowLength

'IF FORCE LEADER LINE, DO LEADER LINE
   If FrmLabelLine.LeaderCheckBox.value Then
'GO TO LEADER
      LeaderDrawDirDist CurrentPosition, theLine, TheView, makePermanent, DrawMode, True
      Exit Sub
   End If

'CHECK THE FIT
   If (Max(dirTextFwdMet.X, dirTextBxMet.X) + distTextMet.X + charSize * 4#) > lineLength Then
'NO FIT, GO TO OVER/UNDER
      DrawDirDistOU CurrentPosition, theLine, TheView, makePermanent, DrawMode
      Exit Sub
   End If

'HOW TO PLACE THE LABELS
   Dim forward As Boolean
   Dim above As Boolean
   Dim pointsLeft As Boolean
   Dim arrowIsLeft As Boolean
   relativeToLine theLine, sAzFwdLine, TheView, CurrentPosition, forward, above, pointsLeft, arrowIsLeft

'CALCULATE INSERTION POINT
   Dim LineSpacing As Double
   Dim moveOffLine As Double
   Dim insertPoint As Point3d
   CalcInsertPoint theLine, charSize, above, LineSpacing, moveOffLine, insertPoint

'CALCULATE ROTATION ANGLE
   Dim rotateToAzim As Double
   rotateToAzim = CalcRotAngle(sAzFwdLine, pointsLeft)
   
'MOVE ELEMENTS INTO POSITION
   If forward Then
      Dim DirTextEl As TextElement
      Set DirTextEl = dirTextElFwd
      Dim dirTextLen As Double
      dirTextLen = dirTextFwdMet.X
   Else
      Set DirTextEl = dirTextElBk
      dirTextLen = dirTextBxMet.X
   End If
   Dim arrowSpace As Double
   arrowSpace = (lineLength - (dirTextLen + arrowLength + distTextMet.X)) / 4#
'MAX SPACE BETWEEN IS 40 CHARACTERS
   arrowSpace = Min(arrowSpace, charSize * 40#)
   Dim endSpace As Double
   endSpace = (lineLength - (arrowSpace * 2# + dirTextLen + arrowLength + distTextMet.X)) / 2#
   If pointsLeft Then
      insertPoint.X = insertPoint.X - (arrowSpace * 2# + dirTextLen + arrowLength + distTextMet.X + endSpace)
   Else
      insertPoint.X = insertPoint.X + endSpace
   End If
   DirTextEl.origin = insertPoint
   Dim ArrowInsertPoint As Point3d
   ArrowInsertPoint = insertPoint
   ArrowInsertPoint.X = ArrowInsertPoint.X + dirTextLen + arrowSpace
   Dim ArrowCell As CellElement
   Set ArrowCell = MyCreateArrowCell(ArrowInsertPoint, charSize, arrowIsLeft, DirTextEl)
   Dim distInsertPoint As Point3d
   distInsertPoint = ArrowInsertPoint
   distInsertPoint.X = distInsertPoint.X + arrowSpace + arrowLength
   distTextEl.origin = distInsertPoint

'CREATE THE LABEL CELL
   Dim arrayForCell(3) As Element
   Set arrayForCell(0) = DirTextEl
   Set arrayForCell(1) = ArrowCell
   Set arrayForCell(2) = distTextEl
   Dim labelCell As CellElement
   Set labelCell = CreateCellElement1(vbNullString, arrayForCell, insertPoint)
   labelCell.RotateAboutZ MyLineElement.startPoint, rotateToAzim

'DRAW THE ELEMENT
   If makePermanent Then
      Dim lineID As DLong
      Dim lineIDString As String
      If GetTheElementID(theLine, lineID, lineIDString) Then
'DELETE OLD LABELS
         DeletePreviousLabelElements lineIDString
'ADD NEW ONES
         ActiveModelReference.AddElement labelCell
         AddLabelLineAutoDeleteTags labelCell, lineIDString
      Else
         ActiveModelReference.AddElement labelCell
      End If
   End If
   labelCell.Redraw DrawMode
End Sub



Private Sub LeaderDrawDirDist(CurrentPosition As Point3d, _
                              theLine As LineElement, _
                              TheView As view, _
                              makePermanent As Boolean, _
                              ByVal DrawMode As MsdDrawingMode, _
                              drawBoth As Boolean)

'GET TEXT AND IT'S SIZES
   Dim charSize As Double
   Dim arrowLength As Double
   Dim dirTextElFwd As TextElement
   Dim dirTextFwdMet As Point2d
   Dim dirTextElBk As TextElement
   Dim dirTextBxMet As Point2d
   Dim distTextEl As TextElement
   Dim distTextMet As Point2d
   Dim sAzFwdLine As Double
   Dim lineLength As Double
   CreateTextElements theLine, _
                      dirTextElFwd, _
                      dirTextFwdMet, _
                      dirTextElBk, _
                      dirTextBxMet, _
                      distTextEl, _
                      distTextMet, _
                      sAzFwdLine, _
                      lineLength, _
                      charSize, _
                      arrowLength

'FOR PLACING THE ARROW
   Dim forward As Boolean
   Dim leaderIsAbove As Boolean
   Dim pointsLeft As Boolean
   Dim arrowIsLeft As Boolean
   relativeToLine theLine, sAzFwdLine, TheView, CurrentPosition, forward, leaderIsAbove, pointsLeft, arrowIsLeft

'CHOOSE THE DIRECTION TEXT
   If FrmLabelLine.CheckBoxBkAz.value Then
      Dim DirTextEl As TextElement
      Set DirTextEl = dirTextElBk
      Dim dirTextLength As Double
      dirTextLength = dirTextBxMet.X
      arrowIsLeft = Not pointsLeft
   Else
      Set DirTextEl = dirTextElFwd
      dirTextLength = dirTextFwdMet.X
      arrowIsLeft = pointsLeft
   End If

'CREATE THE LEADER CELL
   Dim anchorPoint As Point3d
   anchorPoint = CalcMidPoint(theLine.startPoint, theLine.endPoint)
   Dim useLeftCell As Boolean
   Dim labelPoint As Point3d
   Dim ViewAngleRadians As Double
   ViewAngleRadians = TheViewRotRadians(TheView)
   Dim leaderCell As CellElement
   Set leaderCell = CreateArrowLeader(anchorPoint, _
                                      CurrentPosition, _
                                      charSize, _
                                      distTextEl, _
                                      ViewAngleRadians, _
                                      0.6, _
                                      0.9, _
                                      useLeftCell, _
                                      labelPoint, 1)

'MOVE THE TEXT
   Dim labelInsPoint As Point3d
   labelInsPoint = labelPoint
   Dim offset As Double
   offset = ((charSize / 3#) + charSize / 2#)
   If drawBoth Then
      labelInsPoint.Y = labelInsPoint.Y + offset
   End If
   Dim distInsPoint As Point3d
   distInsPoint = labelPoint
   distInsPoint.Y = distInsPoint.Y - offset
   
   If useLeftCell Then
      labelInsPoint.X = labelPoint.X - dirTextLength
      distInsPoint.X = distInsPoint.X - distTextMet.X
   End If
   DirTextEl.origin = labelInsPoint
   DirTextEl.RotateAboutZ labelPoint, ViewAngleRadians
   distTextEl.origin = distInsPoint
   distTextEl.RotateAboutZ labelPoint, ViewAngleRadians

'CREATE TEMPORARY ARROW CELL
   Dim LineSpacing As Double
   Dim moveOffLine As Double
   Dim insertPoint As Point3d
   CalcInsertPoint theLine, charSize, Not leaderIsAbove, LineSpacing, moveOffLine, insertPoint
   If pointsLeft Then
      insertPoint.X = (insertPoint.X - (lineLength - arrowLength) / 2#) - arrowLength
   Else
      insertPoint.X = insertPoint.X + (lineLength - arrowLength) / 2#
   End If
   Dim ArrowCell As CellElement
   Set ArrowCell = MyCreateArrowCell(insertPoint, charSize, arrowIsLeft, DirTextEl)

'ROTATE THE ARROW CELL
   Dim rotateToAzim As Double
   rotateToAzim = CalcRotAngle(sAzFwdLine, pointsLeft)
   ArrowCell.RotateAboutZ theLine.startPoint, rotateToAzim

'DRAW IT
   If makePermanent Then
      Dim lineID As DLong
      Dim lineIDString As String
      If GetTheElementID(theLine, lineID, lineIDString) Then
'DELETE OLD LABELS
         DeletePreviousLabelElements lineIDString
'ADD NEW ONES
         ActiveModelReference.AddElement leaderCell
         ActiveModelReference.AddElement DirTextEl
         AddLabelLineAutoDeleteTags leaderCell, lineIDString
         AddLabelLineAutoDeleteTags DirTextEl, lineIDString
         If drawBoth Then
            ActiveModelReference.AddElement distTextEl
            AddLabelLineAutoDeleteTags distTextEl, lineIDString
         End If
      Else
         ActiveModelReference.AddElement leaderCell
         ActiveModelReference.AddElement DirTextEl
         If drawBoth Then
            ActiveModelReference.AddElement distTextEl
         End If
      End If
   End If
   leaderCell.Redraw DrawMode
   DirTextEl.Redraw DrawMode
   ArrowCell.Redraw DrawMode
   If drawBoth Then
      distTextEl.Redraw DrawMode
   End If
End Sub



Private Sub DrawDirection(CurrentPosition As Point3d, _
                          theLine As LineElement, _
                          TheView As view, _
                          makePermanent As Boolean, _
                          ByVal DrawMode As MsdDrawingMode)
'GET TEXT AND IT'S SIZES
   Dim charSize As Double
   Dim arrowLength As Double
   Dim dirTextElFwd As TextElement
   Dim dirTextFwdMet As Point2d
   Dim dirTextElBk As TextElement
   Dim dirTextBxMet As Point2d
   Dim distTextEl As TextElement
   Dim distTextMet As Point2d
   Dim sAzFwdLine As Double
   Dim lineLength As Double
   CreateTextElements theLine, _
                      dirTextElFwd, _
                      dirTextFwdMet, _
                      dirTextElBk, _
                      dirTextBxMet, _
                      distTextEl, _
                      distTextMet, _
                      sAzFwdLine, _
                      lineLength, _
                      charSize, _
                      arrowLength

'IF FORCE LEADER LINE, DO LEADER LINE
   If FrmLabelLine.LeaderCheckBox.value Then
'GO TO LEADER
      LeaderDrawDirDist CurrentPosition, theLine, TheView, makePermanent, DrawMode, False
      Exit Sub
   End If

'CHECK THE FIT
   If (Max(dirTextFwdMet.X, dirTextBxMet.X) + arrowLength + charSize * 3#) > lineLength Then
'GO TO LEADER
      LeaderDrawDirDist CurrentPosition, theLine, TheView, makePermanent, DrawMode, False
      Exit Sub
   End If

'HOW TO PLACE THE LABELS
   Dim forward As Boolean
   Dim above As Boolean
   Dim pointsLeft As Boolean
   Dim arrowIsLeft As Boolean
   relativeToLine theLine, sAzFwdLine, TheView, CurrentPosition, forward, above, pointsLeft, arrowIsLeft

'CALCULATE INSERTION POINT
   Dim LineSpacing As Double
   Dim moveOffLine As Double
   Dim insertPoint As Point3d
   CalcInsertPoint theLine, charSize, above, LineSpacing, moveOffLine, insertPoint

'CALCULATE ROTATION ANGLE
   Dim rotateToAzim As Double
   rotateToAzim = CalcRotAngle(sAzFwdLine, pointsLeft)

'MOVE ELEMENTS INTO POSITION
   If forward Then
      Dim DirTextEl As TextElement
      Set DirTextEl = dirTextElFwd
      Dim dirTextLen As Double
      dirTextLen = dirTextFwdMet.X
   Else
      Set DirTextEl = dirTextElBk
      dirTextLen = dirTextBxMet.X
   End If
   Dim endSpace As Double
   endSpace = (lineLength - (dirTextLen + charSize + arrowLength)) / 2#
   If pointsLeft Then
      insertPoint.X = insertPoint.X - (dirTextLen + charSize + arrowLength + endSpace)
   Else
      insertPoint.X = insertPoint.X + endSpace
   End If
   DirTextEl.origin = insertPoint
   Dim ArrowInsertPoint As Point3d
   ArrowInsertPoint = insertPoint
   ArrowInsertPoint.X = ArrowInsertPoint.X + dirTextLen + charSize
   Dim ArrowCell As CellElement
   Set ArrowCell = MyCreateArrowCell(ArrowInsertPoint, charSize, arrowIsLeft, DirTextEl)

'CREATE LABEL CELL
   Dim arrayForCell(2) As Element
   Set arrayForCell(0) = DirTextEl
   Set arrayForCell(1) = ArrowCell
   Dim dirCell As CellElement
   Set dirCell = CreateCellElement1(vbNullString, arrayForCell, insertPoint)
   dirCell.RotateAboutZ theLine.startPoint, rotateToAzim

'DRAW THE ELEMENT
   If makePermanent Then
      Dim lineID As DLong
      Dim lineIDString As String
      If GetTheElementID(theLine, lineID, lineIDString) Then
'DELETE OLD LABELS
         DeletePreviousLabelElements lineIDString
'ADD NEW ONES
         ActiveModelReference.AddElement dirCell
         AddLabelLineAutoDeleteTags dirCell, lineIDString
      Else
         ActiveModelReference.AddElement dirCell
      End If
   End If
   dirCell.Redraw DrawMode
End Sub



Private Sub DrawDistance(CurrentPosition As Point3d, _
                         theLine As LineElement, _
                         TheView As view, _
                         makePermanent As Boolean, _
                         ByVal DrawMode As MsdDrawingMode)
'GET TEXT AND IT'S SIZES
   Dim charSize As Double
   Dim arrowLength As Double
   Dim dirTextElFwd As TextElement
   Dim dirTextFwdMet As Point2d
   Dim dirTextElBk As TextElement
   Dim dirTextBxMet As Point2d
   Dim distTextEl As TextElement
   Dim distTextMet As Point2d
   Dim sAzFwdLine As Double
   Dim lineLength As Double
   CreateTextElements theLine, _
                      dirTextElFwd, _
                      dirTextFwdMet, _
                      dirTextElBk, _
                      dirTextBxMet, _
                      distTextEl, _
                      distTextMet, _
                      sAzFwdLine, _
                      lineLength, _
                      charSize, _
                      arrowLength

'IF FORCE LEADER LINE, DO LEADER LINE
   If FrmLabelLine.LeaderCheckBox.value Then
      LeaderDrawDistance CurrentPosition, theLine, TheView, makePermanent, DrawMode
      Exit Sub
   End If

'CHECK THE FIT, DO LEADER IF NOT FIT
   If (distTextMet.X + charSize * 2#) > lineLength Then
      LeaderDrawDistance CurrentPosition, theLine, TheView, makePermanent, DrawMode
      Exit Sub
   End If

'HOW TO PLACE THE LABELS
   Dim forward As Boolean
   Dim above As Boolean
   Dim pointsLeft As Boolean
   Dim arrowIsLeft As Boolean
   relativeToLine theLine, sAzFwdLine, TheView, CurrentPosition, forward, above, pointsLeft, arrowIsLeft

'CALCULATE INSERTION POINT
   Dim LineSpacing As Double
   Dim moveOffLine As Double
   Dim insertPoint As Point3d
   CalcInsertPoint theLine, charSize, above, LineSpacing, moveOffLine, insertPoint
   
'CALCULATE ROTATION ANGLE
   Dim rotateToAzim As Double
   rotateToAzim = CalcRotAngle(sAzFwdLine, pointsLeft)
   
'MOVE ELEMENT INTO POSITION
   Dim endSpace As Double
   endSpace = (lineLength - distTextMet.X) / 2#
   If pointsLeft Then
      insertPoint.X = insertPoint.X - (distTextMet.X + endSpace)
   Else
      insertPoint.X = insertPoint.X + endSpace
   End If
   distTextEl.origin = insertPoint
   distTextEl.RotateAboutZ theLine.startPoint, rotateToAzim
   
'DRAW THE ELEMENT
   If makePermanent Then
      Dim lineID As DLong
      Dim lineIDString As String
      If GetTheElementID(theLine, lineID, lineIDString) Then
'DELETE OLD LABELS
         DeletePreviousLabelElements lineIDString
'ADD NEW ONES
         ActiveModelReference.AddElement distTextEl
         AddLabelLineAutoDeleteTags distTextEl, lineIDString
      Else
         ActiveModelReference.AddElement distTextEl
      End If
   End If
   distTextEl.Redraw DrawMode
End Sub



Private Sub LeaderDrawDistance(CurrentPosition As Point3d, _
                               theLine As LineElement, _
                               TheView As view, _
                               makePermanent As Boolean, _
                               ByVal DrawMode As MsdDrawingMode)
'GET TEXT AND IT'S SIZES
   Dim charSize As Double
   Dim arrowLength As Double
   Dim dirTextElFwd As TextElement
   Dim dirTextFwdMet As Point2d
   Dim dirTextElBk As TextElement
   Dim dirTextBxMet As Point2d
   Dim distTextEl As TextElement
   Dim distTextMet As Point2d
   Dim sAzFwdLine As Double
   Dim lineLength As Double
   CreateTextElements theLine, _
                      dirTextElFwd, _
                      dirTextFwdMet, _
                      dirTextElBk, _
                      dirTextBxMet, _
                      distTextEl, _
                      distTextMet, _
                      sAzFwdLine, _
                      lineLength, _
                      charSize, _
                      arrowLength
'CREATE THE LEADER CELL
   Dim anchorPoint As Point3d
   anchorPoint = CalcMidPoint(theLine.startPoint, theLine.endPoint)
   Dim useLeftCell As Boolean
   Dim labelPoint As Point3d
   Dim ViewAngleRadians As Double
   ViewAngleRadians = TheViewRotRadians(TheView)
   Dim leaderCell As CellElement
   Set leaderCell = CreateArrowLeader(anchorPoint, _
                                      CurrentPosition, _
                                      charSize, _
                                      distTextEl, _
                                      ViewAngleRadians, _
                                      0.6, _
                                      0.9, _
                                      useLeftCell, _
                                      labelPoint, 1)
'MOVE THE TEXT
   Dim labelInsPoint As Point3d
   labelInsPoint = labelPoint
   If useLeftCell Then
      labelInsPoint.X = labelPoint.X - distTextMet.X
   End If
   distTextEl.origin = labelInsPoint
   distTextEl.RotateAboutZ labelPoint, ViewAngleRadians

'DRAW IT
   If makePermanent Then
      Dim lineID As DLong
      Dim lineIDString As String
      If GetTheElementID(theLine, lineID, lineIDString) Then
'DELETE OLD LABELS
         DeletePreviousLabelElements lineIDString
'ADD NEW ONES
         ActiveModelReference.AddElement leaderCell
         ActiveModelReference.AddElement distTextEl
         AddLabelLineAutoDeleteTags leaderCell, lineIDString
         AddLabelLineAutoDeleteTags distTextEl, lineIDString
      Else
         ActiveModelReference.AddElement leaderCell
         ActiveModelReference.AddElement distTextEl
      End If
   End If
   leaderCell.Redraw DrawMode
   distTextEl.Redraw DrawMode
End Sub



Private Sub AddLabelLineAutoDeleteTags(ByVal theElement As Element, ByVal lineIDString As String)
'TAG ELEMENT WITH ITS ID STRING SO WE KNOW THIS PROGRAM CREATED IT, AND IT'S NOT JUST A COPY
'TAG THE ELEMENT WITH THE LINE ELEMENT'S ID SO WE KNOW IT RELATES ONLY TO THAT ELEMENT

   Dim ID As DLong
   Dim IDstring As String
   If Not GetTheElementID(theElement, ID, IDstring) Then
   'SOMETHING WRONG, EXIT
      Exit Sub
   End If
   TagMyElement theElement, TAG_NAME_MY_ID, IDstring
   TagMyElement theElement, TAG_NAME_LABEL_LINE, lineIDString
End Sub



Private Sub DeletePreviousLabelElements(ByVal lineIDString As String)
'ONLY OPERATE IF BOX IS CHECKED
   If Not FrmLabelLine.EraseOldCheckBox.value Then
      Exit Sub
   End If

'REMOVE OLD LABELS
   Dim myFilter As New ElementScanCriteria
   myFilter.ExcludeAllTypes
   myFilter.IncludeType msdElementTypeText
   myFilter.IncludeType msdElementTypeCellHeader
   Dim myElemEnum As ElementEnumerator
   Set myElemEnum = Application.ActiveModelReference.Scan(myFilter)
   
'CYCLE THROUGH FOUND ELEMENTS, EXAMINE ONES WITH TAGS
   While myElemEnum.MoveNext
      Dim TheElem As Element
      Set TheElem = myElemEnum.Current
      If TheElem.HasAnyTags Then
         DeleteIfPreviousLabelElement TheElem, lineIDString
      End If
   Wend
End Sub



Private Sub DeleteIfPreviousLabelElement(ByVal TheElem As Element, ByVal lineIDString As String)
'CHECK FOR THE CORRECT HOST ELEMENT TAG
   Dim TheTagVal As Variant
   If Not CheckForSurveyorToolsTagAndVal(TheElem, TAG_NAME_LABEL_LINE, TheTagVal) Then
      Exit Sub
   End If
   If lineIDString <> TheTagVal Then
      Exit Sub
   End If


'CHECK FOR THE CORRECT ELEMENT ID TAG
   If Not CheckForSurveyorToolsTagAndVal(TheElem, TAG_NAME_MY_ID, TheTagVal) Then
      Exit Sub
   End If
   Dim CurrentElementIdString As String
   CurrentElementIdString = DLongToString(TheElem.ID)
   If CurrentElementIdString <> TheTagVal Then
      Exit Sub
   End If

'IT'S CORRECT, REMOVE PREVIOUS ELEMENT
   ActiveModelReference.RemoveElement TheElem
End Sub

Attribute VB_Name = "LocateText"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

'FOR DEMONSTRATING IN SAMPLE FORM

Option Explicit

Implements ILocateCommandEvents

Public hostForm As FrmSample

Private myLC As LocateCriteria

Private Sub ILocateCommandEvents_Accept(ByVal Element As Element, point As Point3d, ByVal view As view)

End Sub



Private Sub ILocateCommandEvents_Cleanup()
   ClearCommandPromptArea
   CommandState.EnableAccuSnap
End Sub



Private Sub ILocateCommandEvents_Dynamics(point As Point3d, ByVal view As view, ByVal DrawMode As MsdDrawingMode)
   
End Sub



Private Sub ILocateCommandEvents_LocateFailed()
End Sub



Private Sub ILocateCommandEvents_LocateFilter(ByVal Element As Element, point As Point3d, Accepted As Boolean)
   Dim myEl As Element
   Set myEl = CommandState.GetLocatedElement(False)
   If myEl.IsTextElement Then
          hostForm.EnterText myEl.AsTextElement.text
   End If
   CommandState.StartDefaultCommand
   Accepted = False
End Sub



Private Sub ILocateCommandEvents_LocateReset()
End Sub



Private Sub ILocateCommandEvents_Start()
   
   Set myLC = CommandState.CreateLocateCriteria(False)
   myLC.ExcludeAllTypes
   myLC.IncludeType msdElementTypeText
   myLC.IncludeType msdElementTypeTextNode
   myLC.IncludeType msdElementTypeCellHeader
   CommandState.SetLocateCriteria myLC
   
   ShowCommand COMMAND_NAME_LABELCOORD
   ShowPrompt "Pick Text Element/Reset"

   ActiveModelReference.UnselectAllElements

   CommandState.DisableAccuSnap
End Sub

Attribute VB_Name = "LotClosurePickLegPrim"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.



'GENERAL NOTES:
'PROGRAM ASSUMES MASTER UNIT IS FOOT OR SURVEY FOOT, SOME KIND OF FOOT

Option Explicit

Implements IPrimitiveCommandEvents

Private Sub IPrimitiveCommandEvents_Cleanup()
   FrmPlotLot.Show
   ClearCommandPromptArea
End Sub

Private Sub IPrimitiveCommandEvents_DataPoint(point As Point3d, ByVal view As view)
   FrmPlotLot.SetLegPoint point
   FrmPlotLot.UpdateAll
   CommandState.StartDefaultCommand
End Sub

Private Sub IPrimitiveCommandEvents_Dynamics(point As Point3d, ByVal view As view, ByVal DrawMode As MsdDrawingMode)
End Sub

Private Sub IPrimitiveCommandEvents_Keyin(ByVal Keyin As String)
End Sub

Private Sub IPrimitiveCommandEvents_Reset()
   CommandState.StartDefaultCommand
End Sub

Private Sub IPrimitiveCommandEvents_Start()
   FrmPlotLot.Hide
   ShowCommand COMMAND_NAME_LOT_CLOSURE
   ShowPrompt "Pick near course"
   CommandState.DisableAccuSnap
End Sub

Attribute VB_Name = "LotClosurePrimitive"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.



'GENERAL NOTES:
'PROGRAM ASSUMES MASTER UNIT IS FOOT OR SURVEY FOOT, SOME KIND OF FOOT

Option Explicit

Implements IPrimitiveCommandEvents

Private UsedCell        As Boolean      'FLAG TO ADD ELEMENTS TO FLAG
Private LotCell         As CellElement  'THE CELL ELEMENT TO ADD THE ELEMENTS TO
Private ThePOB          As Point3d      'THE POINT TO DRAW TETHER FROM, GET FINAL Z FROM HERE
Private AreaInFeet      As Double       'THE AREA TO TEXT
Private AreaDone        As Boolean      'FLAG THAT ALREADY PLACED AREA TEXT IF DESIRED
Private AreaInFeetDone  As Boolean      'FLAG THAT SQUARE FEET TEXT HAS BEEN PLACED
Private DescriptionDone As Boolean      'FLAG THAT ALREADY PLACED DESCRIPTION IF DESIRED



Public Property Let TheLotCell(TheLotCellElement As CellElement)
   Set LotCell = TheLotCellElement
End Property



Public Property Let UseCell(UsedCellFlag As Boolean)
   UsedCell = UsedCellFlag
End Property



Public Property Let POB(startPoint As Point3d)
   ThePOB = startPoint
End Property



Public Property Let TheAreaInFeet(TheArea As Double)
   AreaInFeet = TheArea
End Property



Private Sub Class_Initialize()
   HandleNoActiveFont
End Sub



Private Sub IPrimitiveCommandEvents_Cleanup()
   FrmPlotLot.Show
   ClearCommandPromptArea
End Sub



Private Sub IPrimitiveCommandEvents_DataPoint(point As Point3d, ByVal view As view)
'CHECK IF CAN WRITE TO FILE
   If ActiveModelReference.IsReadOnly = True Then
      ReadOnlyErrorMess
      CommandState.StartDefaultCommand
      Exit Sub
   End If

'DRAW THE TEXT
   Dim rotateToView As Matrix3d
   rotateToView = Matrix3dTranspose(view.rotation)
   Dim CurrentPosition As Point3d
   CurrentPosition = point
   CurrentPosition.z = ThePOB.z
   If Not DescriptionDone Then
      Dim DescriptionTextElement As TextElement
      Set DescriptionTextElement = CreateDescriptionTextElement(CurrentPosition, rotateToView)
      AddItToTheDrawing DescriptionTextElement
      DescriptionDone = True
   ElseIf Not AreaDone Then
      Dim AreaTextElement As TextElement
      Set AreaTextElement = createAreaTextElement(CurrentPosition, rotateToView)
      AddItToTheDrawing AreaTextElement
      If FrmPlotLot.OptionAcresAndFeet.value = False Then
         AreaDone = True
      ElseIf AreaInFeetDone = False Then
         AreaInFeetDone = True
      Else
         AreaDone = True
      End If
   End If
   If DescriptionDone And AreaDone Then
      CommandState.StartDefaultCommand
   End If
End Sub



Private Sub IPrimitiveCommandEvents_Dynamics(point As Point3d, ByVal view As view, ByVal DrawMode As MsdDrawingMode)
'MAKE INSERTION POINT TO START POINT Z
   Dim CurrentPosition As Point3d
   CurrentPosition = point
   CurrentPosition.z = ThePOB.z

'DRAW TETHER LINE
   DrawTether ThePOB, CurrentPosition, DrawMode

'DRAW THE TEXT
   Dim rotateToView As Matrix3d
   rotateToView = Matrix3dTranspose(view.rotation)
   If Not DescriptionDone Then
      Dim DescriptionTextElement As TextElement
      Set DescriptionTextElement = CreateDescriptionTextElement(CurrentPosition, rotateToView)
      DescriptionTextElement.Redraw DrawMode
   ElseIf Not AreaDone Then
      Dim AreaTextElement As Element
      Set AreaTextElement = createAreaTextElement(CurrentPosition, rotateToView)
      AreaTextElement.Redraw DrawMode
   End If
End Sub



Private Sub IPrimitiveCommandEvents_Keyin(ByVal Keyin As String)
End Sub



Private Sub IPrimitiveCommandEvents_Reset()
   CommandState.StartDefaultCommand
End Sub



Private Sub IPrimitiveCommandEvents_Start()
   If FrmPlotLot.DGNDescriptionCheckBox.value = True Then
      DescriptionDone = False
   Else
      DescriptionDone = True
   End If
   If FrmPlotLot.DGNAreaCheckBox.value = True Then
      AreaDone = False
      AreaInFeetDone = False
   Else
      AreaDone = True
   End If
   ShowCommand COMMAND_NAME_LOT_CLOSURE
   ShowPrompt "Place text"
   CommandState.StartDynamics
End Sub



Private Function CreateDescriptionTextElement(CurrentPosition As Point3d, rotateToView As Matrix3d) As TextElement
   Dim DescriptionTemplate As TextElement
   Set DescriptionTemplate = FrmPlotLot.CreateDescriptionTextTemplate()
   Set CreateDescriptionTextElement = CreateTextElement1(DescriptionTemplate, FrmPlotLot.DescriptionTextBox.text, CurrentPosition, rotateToView)
End Function



Private Function createAreaTextElement(CurrentPosition As Point3d, rotateToView As Matrix3d) As TextElement
   Dim AreaSqFtText As String
   AreaSqFtText = FormatNumber(AreaInFeet, 0) & " sq.ft."
   Dim AreaInAcres As Double
   AreaInAcres = AreaInFeet / Square_Feet_Per_Acre
   Dim AreaAcresText As String
   AreaAcresText = FormatNumber(AreaInAcres, 3, vbTrue, vbFalse, vbTrue) & " ac."
   Dim AreaTextElement As TextElement
   Dim AreaTemplate As TextElement
   Set AreaTemplate = FrmPlotLot.CreateAreaTextTemplate()
   If FrmPlotLot.OptionFeet.value = True Then
      Set createAreaTextElement = CreateTextElement1(AreaTemplate, AreaSqFtText, CurrentPosition, rotateToView)
   ElseIf FrmPlotLot.OptionAcres.value = True Then
      Set createAreaTextElement = CreateTextElement1(AreaTemplate, AreaAcresText, CurrentPosition, rotateToView)
   ElseIf Not AreaInFeetDone Then
      Set createAreaTextElement = CreateTextElement1(AreaTemplate, AreaSqFtText, CurrentPosition, rotateToView)
   Else
      AreaAcresText = "(" & AreaAcresText & ")"
      Set createAreaTextElement = CreateTextElement1(AreaTemplate, AreaAcresText, CurrentPosition, rotateToView)
   End If
End Function



Private Sub AddItToTheDrawing(TheTextElement As TextElement)
   If UsedCell Then
      LotCell.AppendToCellOfCurrentElement TheTextElement
      LotCell.Rewrite
   Else
      ActiveModelReference.AddElement TheTextElement
      TheTextElement.Redraw
   End If
End Sub

Attribute VB_Name = "MeasureDirPrimitive"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit

Implements IPrimitiveCommandEvents

Private startPoint As Point3d
Private StartFound As Boolean

Private Sub Class_Initialize()
   HandleNoActiveLevel
End Sub



Private Sub IPrimitiveCommandEvents_Cleanup()
'CLEAR PROMPT AREA
   ClearCommandPromptArea

'END DIALOG
   Unload FrmMeasureDir
End Sub



Private Sub IPrimitiveCommandEvents_DataPoint(point As Point3d, ByVal view As view)
   If StartFound Then
'END POINT PICKED
      Dim endPoint As Point3d
      endPoint = point
'SEND DATA BACK TO DIALOG BOX
      FrmMeasureDir.setMeaseredPoints startPoint, endPoint
'RESTART COMMAND
      CommandState.StopDynamics
'CANCEL FLAG
      StartFound = False
   Else
'START POINT PICKED
      startPoint = point
'SET FLAG
      StartFound = True
'LOOK FOR END POINT
      CommandState.StartDynamics
   End If

'PROMPT USER
   PromptUser

End Sub



Private Sub IPrimitiveCommandEvents_Dynamics(point As Point3d, ByVal view As view, ByVal DrawMode As MsdDrawingMode)
'EXIT IF NOT START POINT
   If Not StartFound Then
      Exit Sub
   End If

'CREATE TETHER LINE
   Dim myLineElem As LineElement
   Set myLineElem = CreateLineElement2(Nothing, startPoint, point)

'CHANGE ITS LINESTYLE
   Dim oLineStyle As LineStyle
   Set oLineStyle = ActiveDesignFile.LineStyles.Find("0")
   Set myLineElem.LineStyle = oLineStyle
   myLineElem.color = GetTetherColor()

'DRAW IT
   myLineElem.Redraw DrawMode
End Sub



Private Sub IPrimitiveCommandEvents_Keyin(ByVal Keyin As String)
End Sub



Private Sub IPrimitiveCommandEvents_Reset()
   If StartFound = False Then
'EXIT COMMAND
      CommandState.StartDefaultCommand
   Else
'CANCEL FLAG
      StartFound = False
'RESTART COMMAND
      CommandState.StopDynamics
'PROMPT USER
      PromptUser
   End If
End Sub



Private Sub IPrimitiveCommandEvents_Start()
'INITIALIZE FLAG
   StartFound = False
'DIALOG BOX
   FrmMeasureDir.Show

'PROMPT USER
   PromptUser
   
'ENABLE ACCUSNAP
   CommandState.EnableAccuSnap
End Sub



Private Sub PromptUser()
   ShowCommand COMMAND_NAME_MESAURE_DIR
   If StartFound Then
     ShowPrompt "Pick End Point/Reset"
     ShowStatus ""
   Else
     ShowPrompt "Pick Start Point/Reset"
   End If
End Sub

Attribute VB_Name = "PlaceLinePrimitive"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

'FOR DEMONSTRATING IN SAMPLE FORM

Option Explicit

Implements IPrimitiveCommandEvents

Private lineStarted As Boolean
Private startPoint As Point3d



Private Sub IPrimitiveCommandEvents_Cleanup()
   ClearCommandPromptArea
End Sub



Private Sub IPrimitiveCommandEvents_DataPoint(point As Point3d, ByVal view As view)
   If lineStarted Then
'ADD TO DRAWING
      If ActiveModelReference.IsReadOnly = False Then
         Dim lineTemplate As LineElement
         Set lineTemplate = FrmSample.GetLineTemp
         Dim theLine As LineElement
         Set theLine = CreateLineElement2(lineTemplate, startPoint, point)
         ActiveModelReference.AddElement theLine
         theLine.Redraw
      End If
      lineStarted = False
      ShowPrompt "Pick starting point/Reset to quit"
   Else
      lineStarted = True
      startPoint = point
      ShowPrompt "Pick ending point/Reset to quit"
   End If
End Sub



Private Sub IPrimitiveCommandEvents_Dynamics(point As Point3d, ByVal view As view, ByVal DrawMode As MsdDrawingMode)
   If lineStarted Then
      Dim lineTemplate As LineElement
      Set lineTemplate = FrmSample.GetLineTemp
      Dim theLine As LineElement
      Set theLine = CreateLineElement2(lineTemplate, startPoint, point)
      theLine.Redraw DrawMode
   End If
End Sub



Private Sub IPrimitiveCommandEvents_Keyin(ByVal Keyin As String)
End Sub



Private Sub IPrimitiveCommandEvents_Reset()
   CommandState.StartDefaultCommand
End Sub



Private Sub IPrimitiveCommandEvents_Start()
   lineStarted = False
   ShowCommand "Place Line"
   ShowPrompt "Pick starting point/Reset to quit"
   CommandState.EnableAccuSnap
   CommandState.StartDynamics
End Sub

Attribute VB_Name = "PlaceTextPrimitive"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

'FOR DEMONSTRATING IN SAMPLE FORM

Option Explicit

Implements IPrimitiveCommandEvents


Private Sub IPrimitiveCommandEvents_Cleanup()
   ClearCommandPromptArea
End Sub



Private Sub IPrimitiveCommandEvents_DataPoint(point As Point3d, ByVal view As view)
   If ActiveModelReference.IsReadOnly = False Then
      Dim textTemp As TextElement
      Set textTemp = FrmSample.GetTextTemp
      Dim theText As TextElement
      Set theText = CreateTextElement1(textTemp, "Desc: " & FrmSample.PointDescTextBox.text, point, Matrix3dIdentity)
      theText.RotateAboutZ point, TheViewRotRadians(view)
      ActiveModelReference.AddElement theText
      theText.Redraw
   End If
End Sub



Private Sub IPrimitiveCommandEvents_Dynamics(point As Point3d, ByVal view As view, ByVal DrawMode As MsdDrawingMode)
   Dim textTemp As TextElement
   Set textTemp = FrmSample.GetTextTemp
   Dim theText As TextElement
   Set theText = CreateTextElement1(textTemp, "Desc: " & FrmSample.PointDescTextBox.text, point, Matrix3dIdentity)
   theText.RotateAboutZ point, TheViewRotRadians(view)
   theText.Redraw DrawMode
End Sub



Private Sub IPrimitiveCommandEvents_Keyin(ByVal Keyin As String)
End Sub



Private Sub IPrimitiveCommandEvents_Reset()
   CommandState.StartDefaultCommand
End Sub



Private Sub IPrimitiveCommandEvents_Start()
   ShowCommand "Place Text"
   ShowPrompt "Pick where to place text/Reset to quit"
   CommandState.EnableAccuSnap
   CommandState.StartDynamics
End Sub

Attribute VB_Name = "PlotLotBatchCode"
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.



'GENERAL NOTES:
'PROGRAM ASSUMES MASTER UNIT IS FOOT OR SURVEY FOOT, SOME KIND OF FOOT
    
#If VBA7 Then
   Private Declare PtrSafe Function GetOpenFileName Lib "comdlg32.dll" Alias "GetOpenFileNameA" (pOpenfilename As OPENFILENAME) As Long
   Private Type OPENFILENAME
      lStructSize        As Long
      hWndOwner          As LongPtr
      hInstance          As LongPtr
      lpstrFilter        As String
      lpstrCustomFilter  As String
      nMaxCustFilter     As Long
      nFilterIndex       As Long
      lpstrFile          As String
      nMaxFile           As Long
      lpstrFileTitle     As String
      nMaxFileTitle      As Long
      lpstrInitialDir    As String
      lpstrTitle         As String
      flags              As Long
      nFileOffset        As Integer
      nFileExtension     As Integer
      lpstrDefExt        As String
      lCustData          As LongPtr
      lpfnHook           As LongPtr
      lpTemplateName     As String
   End Type
#Else
   Private Declare Function GetOpenFileName Lib "comdlg32.dll" Alias "GetOpenFileNameA" (pOpenfilename As OPENFILENAME) As Long
   Private Type OPENFILENAME
      lStructSize        As Long
      hWndOwner          As Long
      hInstance          As Long
      lpstrFilter        As String
      lpstrCustomFilter  As String
      nMaxCustFilter     As Long
      nFilterIndex       As Long
      lpstrFile          As String
      nMaxFile           As Long
      lpstrFileTitle     As String
      nMaxFileTitle      As Long
      lpstrInitialDir    As String
      lpstrTitle         As String
      flags              As Long
      nFileOffset        As Integer
      nFileExtension     As Integer
      lpstrDefExt        As String
      lCustData          As Long
      lpfnHook           As Long
      lpTemplateName     As String
   End Type
#End If




   
   

Private Const BIF_RETURNONLYFSDIRS = 1
Private Const MAX_PATH = 260
Private Const OFN_OVERWRITEPROMPT = &H2
Private Const OFN_FILEMUSTEXIST = &H1000
Private Const OFN_PATHMUSTEXIST = &H800
Private Const OFN_ALLOWMULTISELECT = &H200
Private Const OFN_EXPLORER = &H80000 ' new look commdlg



Public Function GetBatchLotFilesString(strTitle As String, Optional strInitDir As String = "C:\") As String
   Dim OpenFile    As OPENFILENAME
   Dim lReturn     As Long
   
   Dim strFileFilter As String
   Dim strFileSelected As String
   strFileFilter = COMMAND_NAME_LOT_CLOSURE & " (*.lcj)" + Chr$(0) + "*.lcj" + Chr$(0)

   OpenFile.lpstrFilter = strFileFilter
   OpenFile.nFilterIndex = 1
   OpenFile.hWndOwner = 0
   OpenFile.lpstrFile = String(254999, 0)
   #If VBA7 Then
       OpenFile.nMaxFile = LenB(OpenFile.lpstrFile) - 1
       OpenFile.lStructSize = LenB(OpenFile)
   #Else
       OpenFile.nMaxFile = Len(OpenFile.lpstrFile) - 1
       OpenFile.lStructSize = Len(OpenFile)
   #End If
   OpenFile.lpstrFileTitle = OpenFile.lpstrFile
   OpenFile.nMaxFileTitle = OpenFile.nMaxFile
   OpenFile.lpstrInitialDir = strInitDir
   OpenFile.lpstrTitle = strTitle
   OpenFile.flags = OFN_PATHMUSTEXIST Or OFN_FILEMUSTEXIST Or OFN_ALLOWMULTISELECT Or OFN_EXPLORER
   lReturn = GetOpenFileName(OpenFile)
 
   If lReturn = 0 Then
       GetBatchLotFilesString = ""
   Else
       GetBatchLotFilesString = OpenFile.lpstrFile
   End If
End Function



Public Function GetFilesToBatch(ByRef Filenames() As String, Optional ByVal InitialDirectory As String = "C:\") As Boolean
   GetFilesToBatch = False
   Dim strFileSelected As String
   strFileSelected = GetBatchLotFilesString("Select Files to batch process", InitialDirectory)
   If (InStr(strFileSelected, Chr(0)) > 0) Then 'CHECK FOR NULL STRING
      Dim NameList As Variant
      NameList = Split(strFileSelected, Chr(0))
      Dim NeedsRedim As Boolean
      NeedsRedim = False
      ReDim Filenames(0)
      Dim i As Long
      For i = LBound(NameList) To UBound(NameList)
         If NameList(i) <> "" Then
            If NeedsRedim Then
               ReDim Preserve Filenames(UBound(Filenames) + 1)
            End If
            Filenames(UBound(Filenames)) = NameList(i)
            NeedsRedim = True
         End If
      Next i
      GetFilesToBatch = True
   End If
End Function

Attribute VB_Name = "PlotLotFileCode"
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.



'GENERAL NOTES:
'PROGRAM ASSUMES MASTER UNIT IS FOOT OR SURVEY FOOT, SOME KIND OF FOOT

Option Explicit

Public Const StartPointPrec                     As Long = 5
Public Const DisplayPointPrec                   As Long = 4

Public Const Lot_Closure_Format_Number          As String = "4"
Public Const Lot_Closure_File_Header            As String = "FMTLC"
Public Const Lot_Closure_File_Extension         As String = ".lcj"
Public Const Lot_Closure_Report_File_Extension  As String = ".txt"

Public Const Lot_Closure_Rec_Prefix_Start       As String = "STP "
Public Const Lot_Closure_Rec_Prefix_Line        As String = "LIN "
Public Const Lot_Closure_Rec_Prefix_Curve       As String = "CRV "
Public Const Lot_Closure_Rec_Prefix_Project     As String = "PRJ "
Public Const Lot_Closure_Rec_Prefix_Proj_Num    As String = "PNM "
Public Const Lot_Closure_Rec_Prefix_Date        As String = "DAT "
Public Const Lot_Closure_Rec_Prefix_Azimuth     As String = "AZM "
Public Const Lot_Closure_Rec_Prefix_Coordinate  As String = "CRD "
Public Const Lot_Closure_Rec_Prefix_Description As String = "DES "
Public Const Lot_Closure_Rec_Prefix_Note        As String = "NOT "

Public Const Lot_Closure_Data_Prefix_Azimuth    As String = "Az:"
Public Const Lot_Closure_Data_Prefix_Direction  As String = "Dr:"
Public Const Lot_Closure_Data_Prefix_Distance   As String = "Dist:"
Public Const Lot_Closure_Data_Prefix_Radius     As String = "Rad:"
Public Const Lot_Closure_Data_Prefix_Chord      As String = "Chord:"
Public Const Lot_Closure_Data_Prefix_Chord_Az   As String = "ChdAz:"
Public Const Lot_Closure_Data_Prefix_Chord_Dr   As String = "ChdDr:"
Public Const Lot_Closure_Data_Prefix_RadialIn   As String = "RadIn:"
Public Const Lot_Closure_Data_Prefix_RadialOut  As String = "RadOut:"
Public Const Lot_Closure_Data_Prefix_TangentIn  As String = "TanIn:"
Public Const Lot_Closure_Data_Prefix_TangentOut As String = "TanOut:"
Public Const Lot_Closure_Data_Prefix_Size       As String = "Size:"
Public Const Lot_Closure_Data_Prefix_Rotation   As String = "Rot:"

Public Const Lot_Closure_Data_Size_Small        As String = "Sm"
Public Const Lot_Closure_Data_Size_Large        As String = "Lg"

Public Const Lot_Closure_Data_Rot_Left          As String = "Left"
Public Const Lot_Closure_Data_Rot_Right         As String = "Right"

Public Const Lot_Closure_List_Type_Line         As String = "Line"
Public Const Lot_Closure_List_Type_Curve        As String = "Curve"

Public Const Mode_Edit                          As Long = 1
Public Const Mode_Insert                        As Long = 2


Public Const Mode_Draw_Transient_Hilite_Sel     As Long = 3
Public Const Mode_Draw_Transient_Blank_Sel      As Long = 4
Public Const Mode_Draw_Transient_Hilite_All     As Long = 5
Public Const Mode_Draw_Dynamic                  As Long = 6
Public Const Mode_Draw_Permanent                As Long = 7
Public Const Mode_Draw_Report                   As Long = 8
Public Const Mode_Draw_Export                   As Long = 9
Public Const Mode_Draw_Boundary_Report          As Long = 10

Public PlotLotEntryAngleStyle                   As Integer

Public Const Lot_Closure_Column_Leg_Num         As Long = 0
Public Const Lot_Closure_Column_Leg_Type        As Long = 1
Public Const Lot_Closure_Column_Data_1          As Long = 2
Public Const Lot_Closure_Column_Data_2          As Long = 3
Public Const Lot_Closure_Column_Data_3          As Long = 4
Public Const Lot_Closure_Column_Data_4          As Long = 5
Public Const Lot_Closure_Column_Data_5          As Long = 6


'LOT CLOSURE FILE FORMAT
'=======================
'LINE 1 CONTAINS HEADER ONLY.
'LINE 2 CONTAINS FORMAT VERSION NUMBER. SHOULD BE AN INTEGER.
'



Private Function CreateNewLotFile(OutputFilename As String) As Boolean
'RETURNS TRUE IF SUCCESSFUL
   CreateNewLotFile = True

'JUMP ON ERROR
   On Error GoTo errhnd

'OPEN FILE
   Open OutputFilename For Output As #1

'WRITE HEADER
      Print #1, Lot_Closure_File_Header
      Print #1, Lot_Closure_Format_Number

'CLOSE FILE
   Close #1

'JUMP PAST ERROR CODE
   Exit Function

'ERROR HANDLING
errhnd:
   CreateNewLotFile = False
   ErrorMess Err.Number
   Err.Clear
End Function



Private Function CreateOutRecString(ByVal index As Long) As String
'CREATE RECORD STRING FOR LIST BOX ENTRIES
   Dim temp As String
   Select Case FrmPlotLot.CoursesListBox.List(index, Lot_Closure_Column_Leg_Type)
      Case Lot_Closure_List_Type_Line
         temp = Replace(FrmPlotLot.CoursesListBox.List(index, Lot_Closure_Column_Data_1), " ", "")
         temp = temp & " " & Replace(FrmPlotLot.CoursesListBox.List(index, Lot_Closure_Column_Data_2), " ", "")
         temp = Lot_Closure_Rec_Prefix_Line & temp
         CreateOutRecString = temp
      Case Lot_Closure_List_Type_Curve
         Dim Temp2 As String
         Dim typeString As String
         Dim dataString As String
         temp = Replace(FrmPlotLot.CoursesListBox.List(index, Lot_Closure_Column_Data_1), " ", "")
         Temp2 = temp
         SplitData Temp2, typeString, dataString
         temp = temp & " " & Replace(FrmPlotLot.CoursesListBox.List(index, Lot_Closure_Column_Data_2), " ", "")
         temp = temp & " " & Replace(FrmPlotLot.CoursesListBox.List(index, Lot_Closure_Column_Data_3), " ", "")
         
         If typeString <> Lot_Closure_Data_Prefix_TangentOut And typeString <> Lot_Closure_Data_Prefix_Radius Then
            temp = temp & " " & Replace(FrmPlotLot.CoursesListBox.List(index, Lot_Closure_Column_Data_4), " ", "")
         End If
         
         If typeString = Lot_Closure_Data_Prefix_Chord_Az Or typeString = Lot_Closure_Data_Prefix_Chord_Dr Then
            temp = temp & " " & FrmPlotLot.CoursesListBox.List(index, Lot_Closure_Column_Data_5)
         End If
         
         temp = Lot_Closure_Rec_Prefix_Curve & temp
         CreateOutRecString = temp
      Case Else 'error, should not reach here
         CreateOutRecString = "error"
   End Select
End Function



Public Function DistributeRecord(RecordTypeString As String, RecordDataString As String) As Boolean
'RETURNS TRUE IF SUCCESSFUL
   Dim lastIndex As Long
   DistributeRecord = True
   Select Case RecordTypeString
      Case Lot_Closure_Rec_Prefix_Start
         DistributeRecord = EnterStartPoint(RecordDataString)
      Case Lot_Closure_Rec_Prefix_Line
         DistributeRecord = EnterLine(RecordDataString)
      Case Lot_Closure_Rec_Prefix_Curve
         DistributeRecord = EnterCurve(RecordDataString)
      Case Lot_Closure_Rec_Prefix_Project
         FrmPlotLot.ProjectTextBox.text = RecordDataString
      Case Lot_Closure_Rec_Prefix_Proj_Num
         FrmPlotLot.ProjNumTextBox.text = RecordDataString
      Case Lot_Closure_Rec_Prefix_Date
         FrmPlotLot.DateTextBox.text = RecordDataString
      Case Lot_Closure_Rec_Prefix_Azimuth
         FrmPlotLot.AzimuthTextBox.text = RecordDataString
      Case Lot_Closure_Rec_Prefix_Coordinate
         FrmPlotLot.CoordinateTextBox.text = RecordDataString
      Case Lot_Closure_Rec_Prefix_Description
         FrmPlotLot.DescriptionTextBox.text = RecordDataString
      Case Lot_Closure_Rec_Prefix_Note
         FrmPlotLot.NoteTextBox.text = RecordDataString
      Case Else
         DistributeRecord = False
   End Select
End Function



Private Function EnterCurve(RecordDataString As String) As Boolean
'ENTERS CURVE RECORD INTO LISTBOX
'RETURNS TRUE IF SUCCESSFUL
   EnterCurve = False
   Dim WorkingDataString As String
   WorkingDataString = Trim(RecordDataString)
   If Len(WorkingDataString) < 5 Then
      Exit Function
   End If

   Dim splitStrings As Variant
   splitStrings = Split(WorkingDataString, " ")
   Dim FirstIndex As Long
   FirstIndex = LBound(splitStrings)
   Dim lastIndex As Long
   lastIndex = UBound(splitStrings)
   Dim NumberOfDataStrings As Long
   NumberOfDataStrings = lastIndex - FirstIndex + 1
   If NumberOfDataStrings < 3 Or NumberOfDataStrings > 5 Then
      Exit Function
   End If

   Dim ColonPos As Long
   ColonPos = InStr(splitStrings(FirstIndex), ":")
   
   If ColonPos < 2 Then
      Exit Function
   End If
   Dim dataTypeString As String
   dataTypeString = Mid(splitStrings(FirstIndex), 1, ColonPos)
   Dim temp As String
   Dim dataString As String
   FrmPlotLot.CoursesListBox.AddItem " "
   Dim CourseNum As Long
   CourseNum = FrmPlotLot.CoursesListBox.ListCount
   Dim NewIndex As Long
   NewIndex = CourseNum - 1
   FrmPlotLot.CoursesListBox.List(NewIndex, Lot_Closure_Column_Leg_Num) = FormatNumber(CourseNum, 0)
   FrmPlotLot.CoursesListBox.List(NewIndex, Lot_Closure_Column_Leg_Type) = Lot_Closure_List_Type_Curve
   Select Case dataTypeString
      Case Lot_Closure_Data_Prefix_Chord_Dr
         ProcessChordSub Lot_Closure_Data_Prefix_Chord_Dr, EnterCurve, dataString, dataTypeString, splitStrings, NumberOfDataStrings, FirstIndex, NewIndex
      Case Lot_Closure_Data_Prefix_Chord_Az
         ProcessChordSub Lot_Closure_Data_Prefix_Chord_Az, EnterCurve, dataString, dataTypeString, splitStrings, NumberOfDataStrings, FirstIndex, NewIndex
      Case Lot_Closure_Data_Prefix_RadialIn
         If NumberOfDataStrings <> 4 Then
            Exit Function
         End If
         Dim radialInString As String
         temp = splitStrings(FirstIndex)
         If Not IsValidDirectionData(Lot_Closure_Data_Prefix_RadialIn, temp, radialInString) Then
            Exit Function
         End If
         FrmPlotLot.CoursesListBox.List(NewIndex, Lot_Closure_Column_Data_1) = Lot_Closure_Data_Prefix_RadialIn & radialInString
         
         Dim radiusString As String
         temp = splitStrings(FirstIndex + 1)
         If Not IsValidLengthData(Lot_Closure_Data_Prefix_Radius, temp, radiusString) Then
            Exit Function
         End If
         FrmPlotLot.CoursesListBox.List(NewIndex, Lot_Closure_Column_Data_2) = Lot_Closure_Data_Prefix_Radius & radiusString
         
         Dim radialOutString As String
         temp = splitStrings(FirstIndex + 2)
         If Not IsValidDirectionData(Lot_Closure_Data_Prefix_RadialOut, temp, radialOutString) Then
            Exit Function
         End If
         FrmPlotLot.CoursesListBox.List(NewIndex, Lot_Closure_Column_Data_3) = Lot_Closure_Data_Prefix_RadialOut & radialOutString
         temp = splitStrings(FirstIndex + 3)
         SplitData temp, dataTypeString, dataString
         If dataTypeString <> Lot_Closure_Data_Prefix_Size Or _
                              (dataString <> Lot_Closure_Data_Size_Small And dataString <> Lot_Closure_Data_Size_Large) Then
            Exit Function
         End If
         FrmPlotLot.CoursesListBox.List(NewIndex, Lot_Closure_Column_Data_4) = dataTypeString & dataString
         EnterCurve = True
         
      Case Lot_Closure_Data_Prefix_TangentIn
         If NumberOfDataStrings <> 4 Then
            Exit Function
         End If
         Dim tangentInString As String
         temp = splitStrings(FirstIndex)
         If Not IsValidDirectionData(Lot_Closure_Data_Prefix_TangentIn, temp, tangentInString) Then
            Exit Function
         End If
         FrmPlotLot.CoursesListBox.List(NewIndex, Lot_Closure_Column_Data_1) = Lot_Closure_Data_Prefix_TangentIn & tangentInString
         
         temp = splitStrings(FirstIndex + 1)
         If Not IsValidLengthData(Lot_Closure_Data_Prefix_Radius, temp, radiusString) Then
            Exit Function
         End If
         FrmPlotLot.CoursesListBox.List(NewIndex, Lot_Closure_Column_Data_2) = Lot_Closure_Data_Prefix_Radius & radiusString
         
         Dim tangentOutString As String
         temp = splitStrings(FirstIndex + 2)
         If Not IsValidDirectionData(Lot_Closure_Data_Prefix_TangentOut, temp, tangentOutString) Then
            Exit Function
         End If
         FrmPlotLot.CoursesListBox.List(NewIndex, Lot_Closure_Column_Data_3) = Lot_Closure_Data_Prefix_TangentOut & tangentOutString
         temp = splitStrings(FirstIndex + 3)
         SplitData temp, dataTypeString, dataString
         If dataTypeString <> Lot_Closure_Data_Prefix_Size Or _
                              (dataString <> Lot_Closure_Data_Size_Small And dataString <> Lot_Closure_Data_Size_Large) Then
            Exit Function
         End If
         FrmPlotLot.CoursesListBox.List(NewIndex, Lot_Closure_Column_Data_4) = dataTypeString & dataString
         EnterCurve = True
   
      Case Lot_Closure_Data_Prefix_TangentOut
         If NumberOfDataStrings <> 3 Then
            Exit Function
         End If
         temp = splitStrings(FirstIndex)
         If Not IsValidDirectionData(Lot_Closure_Data_Prefix_TangentOut, temp, tangentOutString) Then
            Exit Function
         End If
         FrmPlotLot.CoursesListBox.List(NewIndex, Lot_Closure_Column_Data_1) = Lot_Closure_Data_Prefix_TangentOut & tangentOutString
         temp = splitStrings(FirstIndex + 1)
         If Not IsValidLengthData(Lot_Closure_Data_Prefix_Radius, temp, radiusString) Then
            Exit Function
         End If
         FrmPlotLot.CoursesListBox.List(NewIndex, Lot_Closure_Column_Data_2) = Lot_Closure_Data_Prefix_Radius & radiusString
         temp = splitStrings(FirstIndex + 2)
         Dim chordDrString As String
         If Not IsValidDirectionData(Lot_Closure_Data_Prefix_Chord_Dr, temp, chordDrString) Then
            Exit Function
         End If
         FrmPlotLot.CoursesListBox.List(NewIndex, Lot_Closure_Column_Data_3) = Lot_Closure_Data_Prefix_Chord_Dr & chordDrString
         FrmPlotLot.CoursesListBox.List(NewIndex, Lot_Closure_Column_Data_4) = ""
         FrmPlotLot.CoursesListBox.List(NewIndex, Lot_Closure_Column_Data_5) = ""
         EnterCurve = True
   
      Case Lot_Closure_Data_Prefix_Radius
         If NumberOfDataStrings <> 3 Then
            Exit Function
         End If
         temp = splitStrings(FirstIndex)
         If Not IsValidLengthData(Lot_Closure_Data_Prefix_Radius, temp, radiusString) Then
            Exit Function
         End If
         FrmPlotLot.CoursesListBox.List(NewIndex, Lot_Closure_Column_Data_1) = Lot_Closure_Data_Prefix_Radius & radiusString
         temp = splitStrings(FirstIndex + 1)
         If Not IsValidDirectionData(Lot_Closure_Data_Prefix_TangentIn, temp, tangentInString) Then
            Exit Function
         End If
         FrmPlotLot.CoursesListBox.List(NewIndex, Lot_Closure_Column_Data_2) = Lot_Closure_Data_Prefix_TangentIn & tangentInString
         temp = splitStrings(FirstIndex + 2)
         If Not IsValidDirectionData(Lot_Closure_Data_Prefix_Chord_Dr, temp, chordDrString) Then
            Exit Function
         End If
         FrmPlotLot.CoursesListBox.List(NewIndex, Lot_Closure_Column_Data_3) = Lot_Closure_Data_Prefix_Chord_Dr & chordDrString
         FrmPlotLot.CoursesListBox.List(NewIndex, Lot_Closure_Column_Data_4) = ""
         FrmPlotLot.CoursesListBox.List(NewIndex, Lot_Closure_Column_Data_5) = ""
         EnterCurve = True
      
   End Select
End Function


Private Sub ProcessChordSub(prefixString As String, _
                            EnterCurve As Boolean, _
                            dataString As String, _
                            dataTypeString As String, _
                            splitStrings As Variant, _
                            NumberOfDataStrings As Long, _
                            FirstIndex As Long, _
                            NewIndex As Long)
      If NumberOfDataStrings <> 5 Then
         Exit Sub
      End If

      Dim chordAzString As String
      Dim temp As String
      temp = splitStrings(FirstIndex)
      If Not IsValidDirectionData(prefixString, temp, chordAzString) Then
         Exit Sub
      End If
      FrmPlotLot.CoursesListBox.List(NewIndex, Lot_Closure_Column_Data_1) = Lot_Closure_Data_Prefix_Chord_Dr & chordAzString
                                                      
      temp = splitStrings(FirstIndex + 1)
      Dim chordString As String
      If Not IsValidLengthData(Lot_Closure_Data_Prefix_Chord, temp, chordString) Then
         Exit Sub
      End If
      FrmPlotLot.CoursesListBox.List(NewIndex, Lot_Closure_Column_Data_2) = Lot_Closure_Data_Prefix_Chord & chordString
      temp = splitStrings(FirstIndex + 2)
      Dim radiusString As String
      If Not IsValidLengthData(Lot_Closure_Data_Prefix_Radius, temp, radiusString) Then
         Exit Sub
      End If
      FrmPlotLot.CoursesListBox.List(NewIndex, Lot_Closure_Column_Data_3) = Lot_Closure_Data_Prefix_Radius & radiusString
      temp = splitStrings(FirstIndex + 3)
      SplitData temp, dataTypeString, dataString
      If dataTypeString <> Lot_Closure_Data_Prefix_Rotation Or _
                           (dataString <> Lot_Closure_Data_Rot_Left And dataString <> Lot_Closure_Data_Rot_Right) Then
         Exit Sub
      End If
      FrmPlotLot.CoursesListBox.List(NewIndex, Lot_Closure_Column_Data_4) = dataTypeString & dataString
      temp = splitStrings(FirstIndex + 4)
      SplitData temp, dataTypeString, dataString
      If dataTypeString <> Lot_Closure_Data_Prefix_Size Or _
                           (dataString <> Lot_Closure_Data_Size_Small And dataString <> Lot_Closure_Data_Size_Large) Then
         Exit Sub
      End If
      FrmPlotLot.CoursesListBox.List(NewIndex, Lot_Closure_Column_Data_5) = dataTypeString & dataString
'MAKE SURE RADIUS IS GREATER THAN CHORD
      If CDbl(radiusString) * 2 < CDbl(chordString) Then
         Exit Sub
      End If
      EnterCurve = True
End Sub



Private Function EnterLine(RecordDataString As String) As Boolean
'ENTERS LINE RECORD INTO LISTBOX
'RETURNS TRUE IF SUCCESSFUL
   Dim DMSString As String
   Dim DistString As String
   If IsValidLineString(RecordDataString, DMSString, DistString) Then
      Dim CourseNum As Long
      CourseNum = FrmPlotLot.CoursesListBox.ListCount + 1
      FrmPlotLot.CoursesListBox.AddItem FormatNumber(CourseNum, 0)
      Dim NewIndex As Long
      NewIndex = FrmPlotLot.CoursesListBox.ListCount - 1
      FrmPlotLot.CoursesListBox.List(NewIndex, Lot_Closure_Column_Leg_Type) = Lot_Closure_List_Type_Line
      FrmPlotLot.CoursesListBox.List(NewIndex, Lot_Closure_Column_Data_1) = Lot_Closure_Data_Prefix_Direction & DMSString
      FrmPlotLot.CoursesListBox.List(NewIndex, Lot_Closure_Column_Data_2) = Lot_Closure_Data_Prefix_Distance & DistString
      EnterLine = True
   Else
      EnterLine = False
   End If
End Function



Private Function EnterStartPoint(RecordDataString As String) As Boolean
'RETURNS TRUE IF SUCCESSFUL
   Dim XValue As Double
   Dim YValue As Double
   Dim ZValue As Double
   If IsValidStartPointString(RecordDataString, XValue, YValue, ZValue) Then
      FrmPlotLot.SetStartPoint Point3dFromXYZ(XValue, YValue, ZValue)
      EnterStartPoint = True
   Else
      EnterStartPoint = False
   End If
End Function



Public Function GetSuggestedLotPath() As String
   Dim DefaultFilename As String
   DefaultFilename = "C:\output" & Lot_Closure_File_Extension
   Dim FilePath As String
   FilePath = GetSetting(APP_NAME, SECTION_LOT_CLOSURE, KEY_FILENAME, DefaultFilename)
   Dim xSplit2 As Variant
   xSplit2 = Split(FilePath, "\")
   xSplit2(UBound(xSplit2)) = ""
   Dim NewTextFilePath As String
   NewTextFilePath = Join(xSplit2, "\")
   GetSuggestedLotPath = NewTextFilePath
End Function



Private Function IsValidDirectionData(prefixString As String, _
                                      DirectionDataString As String, _
                                      ByRef dirDMSString As String) As Boolean
'RETURNS TRUE IF VALID AND STRING OF DDD.MMSS FLOATING AZIMUTH
   IsValidDirectionData = False
   Dim dataString As String
   dataString = Trim(DirectionDataString)
   Dim splitStrings As Variant
   splitStrings = Split(dataString, ":")
   Dim FirstIndex As Long
   FirstIndex = LBound(splitStrings)
   Dim lastIndex As Long
   lastIndex = UBound(splitStrings)
   If (lastIndex - FirstIndex) <> 1 Then
      Exit Function
   End If
   If prefixString <> (splitStrings(FirstIndex) & ":") Then
      Exit Function
   End If

   Dim AngleString As String
   AngleString = splitStrings(lastIndex)
   Dim origPrec As Long
   Dim degPart As Long
   Dim minPart As Long
   Dim secPart As Double
   Dim dirType As Integer
   Dim quad As Integer
   If Not IsDirString(AngleString, origPrec, degPart, minPart, secPart, dirType, quad) Then
      MsgBox "Invalid direction"
      Exit Function
   End If
   dirDMSString = DirString(degPart, minPart, secPart, origPrec, dirType, PlotLotEntryAngleStyle, quad)
   IsValidDirectionData = True
End Function



Private Function IsValidLengthData(prefixString As String, LengthDataString As String, ByRef DistString As String) As Boolean
'RETURNS TRUE IF VALID AND STRING FLOATING DISTANCE
   IsValidLengthData = False
   Dim dataString As String
   dataString = Trim(LengthDataString)
   Dim splitStrings As Variant
   splitStrings = Split(dataString, ":")
   Dim FirstIndex As Long
   FirstIndex = LBound(splitStrings)
   Dim lastIndex As Long
   lastIndex = UBound(splitStrings)
   If (lastIndex - FirstIndex) <> 1 Then
      Exit Function
   End If
   If prefixString <> (splitStrings(FirstIndex) & ":") Then
      Exit Function
   End If
   Dim disDataString As String
   disDataString = splitStrings(lastIndex)
   Dim dist As Double
   Dim origPrec As Long
   If Not IsNonnegativeString(disDataString, False, dist, origPrec) Then
      MsgBox "Invalid distance"
      Exit Function
   End If
   DistString = FormatNumber(disDataString, origPrec, vbTrue, vbFalse, vbTrue)
   IsValidLengthData = True
End Function




Private Function IsValidLineString(RecordDataString As String, ByRef DMSString As String, ByRef DistString As String) As Boolean
'RETURNS TRUE IF VALID AND STRINGS OF DIRECTION AND DISTANCE
   IsValidLineString = False
   Dim dataString As String
   dataString = Trim(RecordDataString)
   Dim splitStrings As Variant
   splitStrings = Split(dataString, " ")
   Dim FirstIndex As Long
   FirstIndex = LBound(splitStrings)
   Dim lastIndex As Long
   lastIndex = UBound(splitStrings)
   If (lastIndex - FirstIndex) <> 1 Then
      Exit Function
   End If
   Dim dirDataString As String
   dirDataString = splitStrings(FirstIndex)
   Dim prefix As String
'CHECK PREFIX
   SplitData dirDataString, prefix, dirDataString
   If prefix <> Lot_Closure_Data_Prefix_Azimuth And prefix <> Lot_Closure_Data_Prefix_Direction Then
      Exit Function
   End If
'GET DATA PART
   Dim origPrec As Long
   Dim degPart As Long
   Dim minPart As Long
   Dim secPart As Double
   Dim dirType As Integer
   Dim quad As Integer
   If Not IsDirString(dirDataString, origPrec, degPart, minPart, secPart, dirType, quad) Then
      MsgBox "Invalid direction"
      Exit Function
   End If
'FORMAT STRING
   Dim dirDMSString As String
   dirDMSString = DirString(degPart, minPart, secPart, origPrec, dirType, PlotLotEntryAngleStyle, quad)
   Dim disDataString As String
   disDataString = splitStrings(lastIndex)
'CHECK PREFIX
   SplitData disDataString, prefix, disDataString
   If prefix <> Lot_Closure_Data_Prefix_Distance Then
      Exit Function
   End If
'GET DATA PART
   Dim dist As Double
   If Not IsNonnegativeString(disDataString, False, dist, origPrec) Then
      MsgBox "Invalid distance"
      Exit Function
   End If
'FORMAT STRING
   DistString = FormatNumber(dist, origPrec, vbTrue, vbFalse, vbTrue)

'RETURN FORMATTED STRING
   DMSString = dirDMSString

'SIGNAL ALL'S WELL
   IsValidLineString = True
End Function



Private Function IsValidStartPointString(RecordDataString As String, _
                                         ByRef XValue As Double, _
                                         ByRef YValue As Double, _
                                         ByRef ZValue As Double) As Boolean
'RETURNS TRUE IF IS A VALID STRING AND THE X,Y,Z VALUES
   IsValidStartPointString = False
   Dim dataString As String
   dataString = Trim(RecordDataString)
   Dim splitStrings As Variant
   splitStrings = Split(dataString, " ")
   Dim FirstIndex As Long
   FirstIndex = LBound(splitStrings)
   Dim lastIndex As Long
   lastIndex = UBound(splitStrings)
   If (lastIndex - FirstIndex) <> 2 Then
      Exit Function
   End If
   If IsNumeric(splitStrings(FirstIndex)) And _
      IsNumeric(splitStrings(FirstIndex + 1)) And _
      IsNumeric(splitStrings(lastIndex)) Then
      YValue = CDbl(splitStrings(FirstIndex))
      XValue = CDbl(splitStrings(FirstIndex + 1))
      ZValue = CDbl(splitStrings(lastIndex))
      IsValidStartPointString = True
   End If
End Function



Public Function NewLotFile() As Boolean
'RETURNS TRUE IF SUCCESSFUL
'INITIALIZE FLAG
   NewLotFile = False

'GET SUGGESTED PATH
   Dim NewTextFilePath As String
   NewTextFilePath = GetSuggestedLotPath()

'CREATE FILTER STRING
   Dim FilterString As String
   FilterString = "*" & Lot_Closure_File_Extension

'CALL COMMON DIALOG
   Dim retVal As Long
   Dim lngfhandle As Long
   Dim lngrid As Long
   Dim strFName As String
   strFName = space(255)
   retVal = mdlDialog_fileCreate(strFName, lngfhandle, lngrid, "", FilterString, NewTextFilePath, "Create File")
   Select Case retVal
      Case 0 'Open
         strFName = Left(strFName, InStr(1, strFName, Chr(0)) - 1)
         Dim XSplit As Variant
         XSplit = Split(strFName, "\")
         If CreateNewLotFile(strFName) Then
            SaveSetting APP_NAME, SECTION_LOT_CLOSURE, KEY_FILENAME, strFName
            NewLotFile = True
            FrmPlotLot.InitializeForm
            If FrmPlotLot.ClearTexBoxesCheckBox.value = True Then
               FrmPlotLot.ClearTextBoxes
            End If
            FrmPlotLot.Caption = COMMAND_NAME_LOT_CLOSURE & " - " & XSplit(UBound(XSplit))
            FrmPlotLot.UpdateAll
         End If
      Case 1 'Cancel
           'MsgBox "No File Selected."
           'User hit the Cancel Button
   End Select
End Function



Public Function OpenLotFile(OPENFILENAME As String) As Boolean
'RETURNS TRUE IF SUCESSFUL, AND FILENAME
'CREATE FILTER STRING
   Dim FilterString As String
   FilterString = "*" & Lot_Closure_File_Extension

'GET SUGGESTED PATH
   Dim NewTextFilePath As String
   NewTextFilePath = GetSuggestedLotPath()

'CALL COMMON DIALOG
   Dim strFName As String
   strFName = space(255)
   Dim lngfhandle As Long
   Dim lngrid As Long
   Dim retVal As Long
   retVal = mdlDialog_fileOpen(strFName, lngfhandle, lngrid, _
                               "", FilterString, NewTextFilePath, "Open File")
   Select Case retVal
      Case 0 'OPEN
         strFName = Left(strFName, InStr(1, strFName, Chr(0)) - 1)
         OPENFILENAME = strFName
         OpenLotFile = True
      Case 1 'Cancel, no action

    End Select
End Function



Public Function SaveAsLotFile() As Boolean
'RETURNS TRUE IF SUCCESSFUL
'INITIALIZE FLAG
   SaveAsLotFile = False

'GET SUGGESTED PATH
   Dim NewTextFilePath As String
   NewTextFilePath = GetSuggestedLotPath()

'CREATE FILTER STRING
   Dim FilterString As String
   FilterString = "*" & Lot_Closure_File_Extension

'CALL COMMON DIALOG
   Dim retVal As Long
   Dim lngfhandle As Long
   Dim lngrid As Long
   Dim strFName As String
   strFName = space(255)
   retVal = mdlDialog_fileCreate(strFName, lngfhandle, lngrid, "", FilterString, NewTextFilePath, "Save As")
   Select Case retVal
      Case 0 'Open
         strFName = Left(strFName, InStr(1, strFName, Chr(0)) - 1)
         Dim XSplit As Variant
         XSplit = Split(strFName, "\")
         If CreateNewLotFile(strFName) Then
            SaveSetting APP_NAME, SECTION_LOT_CLOSURE, KEY_FILENAME, strFName
            SaveAsLotFile = True
            FrmPlotLot.Caption = COMMAND_NAME_LOT_CLOSURE & " - " & XSplit(UBound(XSplit))
            FrmPlotLot.UpdateAll
         End If
      Case 1 'Cancel
           'MsgBox "No File Selected."
           'User hit the Cancel Button
   End Select
End Function



Public Sub SplitData(wholeDataString As String, typeString As String, dataString As String)
'CREATE WORKING COPY, SEPERATE IT AT COLON
   Dim WorkingStrings As Variant
   WorkingStrings = Split(wholeDataString, ":")

'FIND UPPER AND LOWER BOUNDS TO DETERMINE HOW MANY STRINGS IT SPLIT INTO
   Dim upper As Long
   upper = UBound(WorkingStrings)
   Dim lower As Long
   lower = LBound(WorkingStrings)
   Dim arraySize As Long
   arraySize = upper - lower + 1

'HANDLE THE DIFFERENT SITUATIONS
   Select Case arraySize
      Case 1
         typeString = WorkingStrings(lower) & ":"
         dataString = ""
      Case 2
         typeString = WorkingStrings(lower) & ":"
         dataString = WorkingStrings(upper)
      Case Else
         typeString = ""
         dataString = ""
   End Select
End Sub



Public Function SplitRecord(TheRecordString As String, _
                            ByRef RecordTypeString As String, _
                            ByRef RecordDataString As String) As Boolean
'SPLITS STRING INTO TYPE AND DATA IF CAN
'RETURNS TRUE IF SUCCESSFUL
   Dim StringLength As Long
   StringLength = Len(TheRecordString)
   If StringLength = 4 Then
      RecordTypeString = TheRecordString
      RecordDataString = ""
      SplitRecord = True
   ElseIf StringLength > 4 Then
      RecordTypeString = Left(TheRecordString, 4)
      RecordDataString = Mid(TheRecordString, 5)
      SplitRecord = True
   Else
      SplitRecord = False
   End If
End Function



Private Function StartPointRecord(startPoint As Point3d) As String
'CREATES RECORD STRING FOR STARTPOINT
'MAKE WORKING COPY
   Dim WorkingStartPoint As Point3d
   WorkingStartPoint = startPoint
   
   StartPointRecord = Lot_Closure_Rec_Prefix_Start & FormatNumber(WorkingStartPoint.Y, StartPointPrec, vbTrue, vbFalse, vbFalse) & " " _
                                                   & FormatNumber(WorkingStartPoint.X, StartPointPrec, vbTrue, vbFalse, vbFalse) & " " _
                                                   & FormatNumber(WorkingStartPoint.z, StartPointPrec, vbTrue, vbFalse, vbFalse)
End Function



Public Sub WriteLotFile()
'JUMP ON ERROR
   On Error GoTo errhnd

'GET FILENAME
   Dim DefaultFilename As String
   DefaultFilename = "C:\output" & Lot_Closure_File_Extension
   
   Dim fullFilename As String
   fullFilename = GetSetting(APP_NAME, SECTION_LOT_CLOSURE, KEY_FILENAME, DefaultFilename)

'OPEN FILE
   Open fullFilename For Output As #1

'WRITE HEADER
   Print #1, Lot_Closure_File_Header
   Print #1, Lot_Closure_Format_Number

'WRITE STARTING POINT
   Dim StartPoint3d As Point3d
   StartPoint3d = FrmPlotLot.GetStartPoint()
   Print #1, StartPointRecord(StartPoint3d)

'WRITE PROJECT NAME TEXT
   Print #1, Lot_Closure_Rec_Prefix_Project & FrmPlotLot.ProjectTextBox.text

'WRITE PROJECT NUM TEXT
   Print #1, Lot_Closure_Rec_Prefix_Proj_Num & FrmPlotLot.ProjNumTextBox.text

'WRITE DATE TEXT
   Print #1, Lot_Closure_Rec_Prefix_Date & FrmPlotLot.DateTextBox.text
   
'WRITE AZIMUTH TEXT
   Print #1, Lot_Closure_Rec_Prefix_Azimuth & FrmPlotLot.AzimuthTextBox.text

'WRITE COORDINATE TEXT
   Print #1, Lot_Closure_Rec_Prefix_Coordinate & FrmPlotLot.CoordinateTextBox.text

'WRITE DESCRIPTION TEXT
   Print #1, Lot_Closure_Rec_Prefix_Description & FrmPlotLot.DescriptionTextBox.text

'WRITE NOTE TEXT
   Print #1, Lot_Closure_Rec_Prefix_Note & FrmPlotLot.NoteTextBox.text

'WRITE COURSES
   Dim CourseCount As Long
   Dim index As Long
   CourseCount = FrmPlotLot.CoursesListBox.ListCount
   For index = 0 To CourseCount - 1
      Print #1, CreateOutRecString(index)
   Next index

'CLOSE FILE
   Close #1

'JUMP PAST ERROR CODE
   Exit Sub

'ERROR HANDLING
errhnd:
   ErrorMess Err.Number
   Err.Clear
End Sub



'*************************************************************************************************************
'************************************************REPORT FILES*************************************************
Public Function CreateReportFile(ByRef ReportName As String) As Boolean
'RETURNS TRUE IF SUCCESSFUL
   CreateReportFile = False

'CREATE DEFAULT FILENAME
   Dim DefaultFilename As String
   DefaultFilename = "C:\report" & Lot_Closure_Report_File_Extension

'GET CURRENT LOT FILE NAME
   Dim fullFilename As String
   fullFilename = GetSetting(APP_NAME, SECTION_LOT_CLOSURE, KEY_FILENAME, DefaultFilename)

'GET SUGGESTED FILENAME FOR REPORT FILE
   Dim xSplit2 As Variant
   xSplit2 = Split(fullFilename, "\")
   Dim TheLotFilename As String
   TheLotFilename = xSplit2(UBound(xSplit2))
   Dim PeriodPosition As Long
   PeriodPosition = InStrRev(TheLotFilename, ".")
   Dim SuggestedFilename As String
   If PeriodPosition > 0 Then
      TheLotFilename = Left(TheLotFilename, PeriodPosition - 1)
   End If
   SuggestedFilename = TheLotFilename & Lot_Closure_Report_File_Extension

'GET SUGGESTED PATH FOR REPORT FILE
   xSplit2(UBound(xSplit2)) = ""
   Dim NewTextFilePath As String
   NewTextFilePath = Join(xSplit2, "\")

'CREATE FILTER STRING
   Dim FilterString As String
   FilterString = "*" & Lot_Closure_Report_File_Extension

'CALL COMMON DIALOG FOR CREATING FILE
   Dim retVal As Long
   Dim lngfhandle As Long
   Dim lngrid As Long
   Dim strFName As String
   strFName = space(255)
   retVal = mdlDialog_fileCreate(strFName, lngfhandle, lngrid, SuggestedFilename, FilterString, NewTextFilePath, "Create Report File")
   Select Case retVal
      Case 0 'Open
'RETURN NEW REPORT FILENAME
         strFName = Left(strFName, InStr(1, strFName, Chr(0)) - 1)
         ReportName = strFName
         CreateReportFile = True
      Case 1 'Cancel
           'MsgBox "No File Selected."
           'User hit the Cancel Button
   End Select
End Function
'*************************************************************************************************************

Attribute VB_Name = "PlotLotPickStartPrimitive"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.



'GENERAL NOTES:
'PROGRAM ASSUMES MASTER UNIT IS FOOT OR SURVEY FOOT, SOME KIND OF FOOT

Option Explicit

Implements IPrimitiveCommandEvents

Private Sub IPrimitiveCommandEvents_Cleanup()
   FrmPlotLot.Show
   ClearCommandPromptArea
End Sub

Private Sub IPrimitiveCommandEvents_DataPoint(point As Point3d, ByVal view As view)
   FrmPlotLot.SetStartPoint point
   FrmPlotLot.UpdateAll
   CommandState.StartDefaultCommand
End Sub

Private Sub IPrimitiveCommandEvents_Dynamics(point As Point3d, ByVal view As view, ByVal DrawMode As MsdDrawingMode)
   FrmPlotLot.DrawTheCourses point, Mode_Draw_Dynamic, DrawMode
End Sub

Private Sub IPrimitiveCommandEvents_Keyin(ByVal Keyin As String)
End Sub

Private Sub IPrimitiveCommandEvents_Reset()
   CommandState.StartDefaultCommand
   FrmPlotLot.CalcAndDrawCourses
End Sub

Private Sub IPrimitiveCommandEvents_Start()
   FrmPlotLot.Hide
   ShowCommand COMMAND_NAME_LOT_CLOSURE
   ShowPrompt "Pick Start Point"
   CommandState.StartDynamics
   CommandState.EnableAccuSnap
End Sub

Attribute VB_Name = "STARTHERE"
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.


'THE CODER'S COMMENTS:
'THIS MODULE CONTAINS THE "ENTRY POINTS" FOR THIS SET OF PROGRAMS.
'START HERE AND FOLLOW THE CODE.  TO RUN THESE PROGRAMS, YOU
'KEY IN "VBA RUN " AND THEN THE SUBROUTINE NAME.  SO TO RUN THE
'CURVE SOLVER, YOU'D KEY IN "VBA RUN CURVESOLVER" ON THE
'MICROSTATION COMMAND LINE.  IT'S PROBABLY EASIEST TO JUST RUN
'THE PROGRAM LAUNCHER AND USE THE TOOLBAR.

'THE ORIGINAL SURVEYOR TOOLS PROJECT IS LIKE A MASTER STOCK,
'THAT SOUP THAT JUST GETS ADDED TO YEAR AFTER YEAR IN THE SAME POT.
'METAPHORS ASIDE, THE ORIGINAL PROJECT DID NOT HAVE ANY SET DESIGN
'STANDARDS AND WAS JUST MADE UP AS I WENT ALONG.  AS A RESULT, IT
'IS DISORGANIZED, INCONSISTENT, MESSY AND DIFFICULT TO UNDERSTAND.
'NOW THAT I AM LONG IN THE TOOTH, I AM ATTEMPTING TO CLEAN IT UP AND
'ORGANIZE THE CODE SO THAT I CAN PASS THE TORCH.  AT THE SAME TIME,
'I AM TRYING TO MAKE IT SUITABLE FOR OPEN SOURCE SO OTHERS MAY
'BENEFIT FROM MY LABOR.  THIS IS WHY I'VE ADDED THE ABILITY TO USE
'BEARINGS AND THE OPTION TO USE NORTH AZIMUTH.  THE ORIGINAL ONLY
'WORKED WITH SOUTH AZIMUTH BY DESIGN.  I FELT IT WAS BETTER TO NOT
'BE ABLE TO CHANGE THE AZIMUTH AFTER A WHOLE LOT OF PLANS WENT OUT
'IN NORTH AZIMUTH BEACAUSE SOMEBODY ACCIDENTALLY CHANGED THE SETTINGS.

'THE ORIGINAL SURVEYOR TOOLS IS A LOT OF CODE.  LOTS AND LOTS OF CODE,
'THERE IS WAY TOO MUCH CODE FOR ME TO CLEAN UP.  SO I AM ONLY MOVING
'FORWARD THE MODULES THAT WILL BENEFIT US THE MOST.  I AM LEAVING OUT
'THE THINGS FOR DRAWING TOPO AND CROSS SECTIONS.  SETTINGS IS JUST
'THE MINIMAL.

'ALTHOUGH I HAVE ORGANIZED AND CLEANED THE CODE, I'M SURE SOME WILL
'STILL CONSIDER IT MESSY.  i'M ONLY SAYING THAT IT IS LESS MESSY.
'YOU ARE WELCOME TO CLEAN IT EVEN MORE.  ALSO, I SHOULD MENTION THAT
'IT NOW HAS A BASIC FRAMEWORK TO WORK BY.  THE TextEntriesAndChkBox
'MODULE IS A MAIN PART OF THIS FRAMEWORK.  IT IS THE CODE FOR PROCESSING
'THE TEXT ENTRIES FOR SEVERAL DIFFERENT DATA TYPE.  IT IS THE OUTERMOST
'LAYER OF THE PROGRAM.  CONVERSIONS TO AND FROM DEGREES, MINUTES,
'SECONDS, BEARINGS, AZIMUTH ARE DONE AT THIS LAYER.  IN THIS FRAMEWORK,
'ALL COGO CALCULATIONS ARE DONE IN SOUTH AZIMUTH IN DECIMAL DEGREES.

'THE NEXT PART OF THE FRAMEWORK IS THE CONSTANTS MODULE.  IT PROVIDES
'A METHODICAL WAY OF ORGANIZING VARIABLES.  JUST FOLLOW THE PATTERN
'OF HOW THINGS ARE LAID OUT.  IT'LL BE EASIER TO FIND THINGS THIS WAY.
'YOU MAY NOTICE THAT MY KEYS ARE THE SAME AS THEIR TOKEN/SYMBOL.  i
'DO THIS SO THAT THE COMPILER FINDS DUPLICATES FOR ME.  IT MIGHT TAKE
'A FEW MORE BYTES, BUT I DON'T WORRY ABOUT HAVING TWO OF THE SAME KEY.

'I HAVE A SAMPLE PROGRAM/DIALOG BOX.  I USE IT TO REMIND MYSELF HOW I
'DID THINGS.  YOU CAN USE IT OR HIDE IT OR DELETE IT.  IT DOES NO USEFUL
'TASK.


Option Explicit

Dim oOpenClose As StartupClass



'AZ/AZ INTERSECT
Public Sub AAInt()
   FrmAzAzInt.Show
End Sub



'ARC/LINE INTERSECT
Public Sub ALInt()
   FrmArcLineInt.Show
End Sub



'CURVE SOLVER
Public Sub CurveSolver()
   FrmCurveSolver.Show
End Sub



'COMPASS RULE 2D
Public Sub CR2D()
   FrmCompassRule.Show
End Sub



'ARC/ARC INTERSECT
Public Sub DDInt()
   FrmArcArcInt.Show
End Sub



'DUP FINDER
Public Sub DupFind()
   FrmDupFinder.Show
End Sub



'DRAW TRAVERSE
Public Sub DrawTrav()
   FrmTraverse.Show
End Sub



'DROP DIAGRAM
Public Sub Dropster()
   FrmDropDiagram.Show
End Sub



'LABEL COORDINATE
Public Sub LabelCoord()
    CommandState.StartPrimitive New LabelCoordPrimitive
End Sub



'LABEL CURVE
Public Sub LabelCurve()
   CommandState.StartLocate New LabelCurveLocate
End Sub



'LABEL LINE
Public Sub LabelLine()
   CommandState.StartLocate New LabelLineLocate
End Sub



'MEASURE DIRECTION AND DISTANCE
Public Sub MeasureDandD()
   CommandState.StartPrimitive New MeasureDirPrimitive
End Sub



'PLOT LOT
Public Sub Plotlot()
   FrmPlotLot.Show
End Sub



'USER PROGRAM LAUNCHER (TOOLBAR)
Public Sub Opener()
   FrmOpener.Show
End Sub



'SAMPLES OF USER INTERFACE
Public Sub Sample()
   FrmSample.Show
End Sub



'SETTINGS DIALOG BOX
Public Sub Setting()
   FrmSetting.Show
End Sub



'LABEL STATION
Public Sub StationInverse()
   FrmStationInverse.Show
End Sub



'PLOT BY STATION
Public Sub StationPlot()
   FrmStationPlot.Show
End Sub



'STATION TEXT
Public Sub StationText()
   FrmStationText.Show
End Sub



'**********************************************************************************
'****************THIS SUBROUTINE AUTORUNS AT STARTUP OF THE PROJECT****************
'********************PROBABLY THIS IS UNIQUE TO MICROSTATION***********************
Sub OnProjectLoad()
   If OPTION_TRUE = GetSetting(APP_NAME, SECTION_SETTINGS, KEY_NORTH_MODE, OPTION_FALSE) Then
      NORTH_AZIMUTH_MODE = True
   Else
      NORTH_AZIMUTH_MODE = False
   End If
   If OPTION_TRUE = GetSetting(APP_NAME, SECTION_LAUNCHER, KEY_CHECKBOX, OPTION_TRUE) Then
      Set oOpenClose = New StartupClass
   End If
End Sub
'**********************************************************************************
'**********************************************************************************

Attribute VB_Name = "Settings"
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

'ALL SETTINGS ASSUME MASTER UNIT IS FOOT OR SURVEY FOOT

Option Explicit

Public Const SETTING_DEFAULT_FONT_SIZE_INCH As String = "0.08 inch"
Public Const SETTING_DEFAULT_PLOT_SCALE     As String = "20"


Public Function GetCharSize() As Double
'RETURNS CHARACTER'S WORLD SIZE IN FEET, USED FOR SIZING MANY THINGS.
   Dim fontSizeString As String
   fontSizeString = GetSetting(APP_NAME, SECTION_SETTINGS, KEY_FONT_SIZE_INCH, SETTING_DEFAULT_FONT_SIZE_INCH)
   Dim fontSizeInches As Double
   fontSizeInches = CDbl(Replace(fontSizeString, "inch", ""))
   Dim plotScale As String
   plotScale = GetPlotScale()
   If Not IsNumeric(plotScale) Then
      plotScale = SETTING_DEFAULT_PLOT_SCALE
   End If
   
   GetCharSize = fontSizeInches * CDbl(plotScale)
End Function



Public Function GetPlotScale() As String
   GetPlotScale = GetSetting(APP_NAME, SECTION_SETTINGS, KEY_PLOT_SCALE, SETTING_DEFAULT_PLOT_SCALE)
End Function



Public Function GetTetherColor() As Integer
   Dim defaultColor As String
   defaultColor = "3"
   Dim previousColor As String
   previousColor = GetSetting(APP_NAME, SECTION_SETTINGS, KEY_COLOR, "")
   If previousColor = "" Then
      SaveSetting APP_NAME, SECTION_SETTINGS, KEY_COLOR, defaultColor
      previousColor = defaultColor
   End If
   If previousColor = BY_LEVEL Then
      GetTetherColor = ByLevelColor
   Else
      GetTetherColor = CInt(previousColor)
   End If
End Function

Attribute VB_Name = "StartupClass"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit

Implements IEnterIdleEvent

Private done As Boolean
Dim WithEvents hooks As Application
Attribute hooks.VB_VarHelpID = -1

Private Sub Class_Initialize()
   Set hooks = Application
   done = False
End Sub

Private Sub hooks_OnDesignFileOpened(ByVal DesignFileName As String)
   If Not done Then
      AddEnterIdleEventHandler Me
   End If
End Sub



Private Sub IEnterIdleEvent_EnterIdle(ByVal Reserved As Long)
   If Not done Then
      done = True
      Opener
   End If
   RemoveEnterIdleEventHandler Me
End Sub

Attribute VB_Name = "StationInverseLocate"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit

Implements ILocateCommandEvents

Dim myLC As LocateCriteria

Private Sub ILocateCommandEvents_Accept(ByVal Element As Element, point As Point3d, ByVal view As view)
'PASS ACCEPTED ELEMENT TO DIALOG BOX
   FrmStationInverse.PickedElement = Element
         
'SIGNAL DIALOG BOX NOT TO CLOSE
   FrmStationInverse.DoNotClose = True

'START PICKING POINTS TO LABEL
   Dim PlaceTool As New StationInversePrimitive
   PlaceTool.BaseElement = Element
   CommandState.StartPrimitive PlaceTool
End Sub



Private Sub ILocateCommandEvents_Cleanup()
'CLEAR PROMPT AREA
   ClearCommandPromptArea

'NOTIFY DIALOG THAT COMMAND IS CLOSING
   FrmStationInverse.CommandIsClosing
End Sub



Private Sub ILocateCommandEvents_Dynamics(point As Point3d, ByVal view As view, ByVal DrawMode As MsdDrawingMode)

End Sub



Private Sub ILocateCommandEvents_LocateFailed()
'PROVIDE INSTRUCTIONS TO USER
   UserFeedbackPick
End Sub



Private Sub ILocateCommandEvents_LocateFilter(ByVal Element As Element, point As Point3d, Accepted As Boolean)
'INITIALIZE FLAG
   Accepted = False

'CHECK, MAKE SURE THEY ARE SURVEYOR TOOLS BASELINE SEGMENTS AND IN THE XY PLANE
   Select Case Element.Type
      Case msdElementTypeArc 'CHECK IF VALID ARC
         If ArcIsValidBaselineSegment(Element) Then
            'IT'S A GOOD ELEMENT
            Accepted = True
            UserFeedbackAccept
         End If
      Case msdElementTypeLine 'CHECK IF VALID LINE
         If LineIsValidBaselineSegment(Element) Then
            'IT'S A GOOD ELEMENT
            Accepted = True
            UserFeedbackAccept
         End If
      Case msdElementTypeLineString 'CHECK IF VALID SPIRAL
         If IsSpiralElementLite(Element) Then
            'IT'S A GOOD ELEMENT
            Accepted = True
            UserFeedbackAccept
          End If
   End Select
End Sub



Private Sub ILocateCommandEvents_LocateReset()
'QUIT
   CommandState.StartDefaultCommand
End Sub



Private Sub ILocateCommandEvents_Start()
'MAKE SURE NOTHING IS SELECTED
   ActiveModelReference.UnselectAllElements
   
'CREATE SCAN CRITERIA
   Set myLC = CommandState.CreateLocateCriteria(False)
   myLC.ExcludeAllTypes
   myLC.IncludeType msdElementTypeArc
   myLC.IncludeType msdElementTypeLine
   myLC.IncludeType msdElementTypeLineString

'START LOCATING PROCESS
   CommandState.SetLocateCriteria myLC

'SIGNAL DIALOG BOX IT'S OKAY TO CLOSE
   FrmStationInverse.DoNotClose = False

'PROVIDE INSTRUCTIONS TO USER
   UserFeedbackPick
End Sub



Private Sub UserFeedbackPick()
'PROVIDE INSTRUCTIONS TO USER
   ShowCommand COMMAND_NAME_STATION_INVERSE
   ShowPrompt "Pick baseline SEGMENT/Reset to quit"
End Sub



Private Sub UserFeedbackAccept()
'PROVIDE INSTRUCTIONS TO USER
  ShowCommand COMMAND_NAME_STATION_INVERSE
   ShowPrompt "Accept to apply/Reset"
End Sub

Attribute VB_Name = "StationInversePrimitive"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit

Implements IPrimitiveCommandEvents

Private baselineSegment    As Element
Private beenPicked         As Boolean 'FLAGS IF STATION OFFSET POINT HAS BEEN PICKED
Private invStation         As Double
Private pointOffsetString  As String
Private pointToLabel       As Point3d

Private stationStyleGlobal As Integer

'LET FLAG GET SET EXTERNALLY
Property Let BaseElement(ByVal BaselineElement As Element)
   Set baselineSegment = BaselineElement
End Property





Private Sub DrawTextAndLeader(point As Point3d, _
                              ByVal StationingString As String, _
                              ByVal offsetString As String, _
                              ByVal makePermanent As Boolean, _
                              view As view, _
                              Optional ByVal DrawMode As MsdDrawingMode)
'CREATE THE STATION OFFSET TEXT ELEMENTS TO GET THE DIMENSIONS
   Dim charSize As Double
   charSize = GetCharSize()
   Dim textTemplate As TextElement
   Set textTemplate = FrmStationInverse.GetTextTemp()
   Dim StationTextEl As TextElement
   Set StationTextEl = CreateTextElement1(textTemplate, StationingString, point, Matrix3dIdentity)
   Dim StationDims As Point2d
   StationTextEl.GetTotalTextSize StationDims.X, StationDims.Y
   Dim OffsetTextEl As TextElement
   Set OffsetTextEl = CreateTextElement1(textTemplate, offsetString, point, Matrix3dIdentity)
   Dim OffsetDims As Point2d
   OffsetTextEl.GetTotalTextSize OffsetDims.X, OffsetDims.Y
      
'DRAW THE LEADER
'DETERMINE SIZE OF TAIL
   Dim TailSize As Double
   TailSize = Max(OffsetDims.X, StationDims.X) / charSize + 0.8
   Dim useLeftText As Boolean
   Dim labelPoint As Point3d
   Dim ViewAngleRadians As Double
   ViewAngleRadians = TheViewRotRadians(view)
   Dim leaderCell As CellElement
   Set leaderCell = CreateArrowLeader(pointToLabel, point, charSize, textTemplate, ViewAngleRadians, TailSize, 0.6, useLeftText, labelPoint, 1)
'USE CORRECT JUSTIFICATION FOR LEFT OR RIGHT LEADER LINE
   If Not useLeftText Then
      ChangeJustification StationTextEl, msdTextJustificationLeftCenter
      ChangeJustification OffsetTextEl, msdTextJustificationLeftCenter
   End If

'MOVE THE STATION OFFSET TEXT TO LABEL POINT'
   Dim tempPoint As Point3d
   tempPoint = labelPoint
   tempPoint.Y = labelPoint.Y + charSize * 0.7
   StationTextEl.origin = tempPoint
   tempPoint.Y = labelPoint.Y - charSize * 0.7
   OffsetTextEl.origin = tempPoint

'MAKE INTO ORPHAN CELL
   Dim cellArray(1 To 2) As Element
   Set cellArray(1) = StationTextEl
   Set cellArray(2) = OffsetTextEl
   Dim StationCell As CellElement
   Set StationCell = CreateCellElement1(vbNullString, cellArray, labelPoint)

'ROTATE IT TO THE VIEW ANGLE
   StationCell.RotateAboutZ labelPoint, ViewAngleRadians

'MAKE ADD IT TO THE DRAWING IF REQUESTED
   If makePermanent Then
'MAKE SURE YOU CAN WRITE TO FILE
      If ActiveModelReference.IsReadOnly = True Then
         ReadOnlyErrorMess
         Exit Sub
      End If
      ActiveModelReference.AddElement StationCell
      ActiveModelReference.AddElement leaderCell
   End If

'DISPLAY THE ELEMENT
   leaderCell.Redraw DrawMode
   StationCell.Redraw DrawMode
End Sub



Private Function CreateOffsetString(ByVal offset As Double) As String
   offset = Round(offset, 2)
   If offset < 0 Then
      CreateOffsetString = FormatNumber(Abs(offset), 2) & " lt"
   ElseIf offset > 0 Then
      CreateOffsetString = FormatNumber(Abs(offset), 2) & " rt"
   Else
      CreateOffsetString = "0"
   End If
   CreateOffsetString = "o/s " & CreateOffsetString
End Function



Private Sub UserFeedbackPick()
'PROVIDE INSTRUCTIONS TO USER
   ShowCommand COMMAND_NAME_STATION_INVERSE
   ShowPrompt "Pick POINT to label/Reset"
End Sub



Private Sub UserFeedbackAccept()
'PROVIDE INSTRUCTIONS TO USER
   ShowCommand COMMAND_NAME_STATION_INVERSE
   ShowPrompt "Pick PLACE for the label/Reset"
End Sub



Private Function PointStationString() As String
   PointStationString = FrmStationInverse.prefixString & "Sta " & StationToString(invStation, DEFAULT_STATION_PRECISION, stationStyleGlobal)
End Function



Private Sub IPrimitiveCommandEvents_Cleanup()
'CLEAR PROMPT AREA
   ClearCommandPromptArea

'NOTIFY DIALOG BOX COMMAND IS CLOSING
   FrmStationInverse.CommandIsClosing
End Sub



Private Sub IPrimitiveCommandEvents_DataPoint(point As Point3d, ByVal view As view)
'ADD THE CELLS TO DRAWING
   If beenPicked Then
      DrawTextAndLeader point, PointStationString(), pointOffsetString, True, view

'RESTART THIS SO UNDO WORKS, BUT DON'T CLOSE THE DIALOG BOX
      FrmStationInverse.DoNotClose = True
      CommandState.StartPrimitive Me
      Exit Sub
   End If

'INITIATE LOOKING FOR SPOT TO DRAW CELLS
   Dim station As Double
   Dim offset As Double
   Dim beginStation As Double
   If IsPointWithinSegment(point, baselineSegment, beginStation, station, offset) And Not beenPicked Then
      beenPicked = True
      pointToLabel = point
      invStation = station
      pointOffsetString = CreateOffsetString(offset)
      ShowStatus ""
      UserFeedbackAccept
      CommandState.DisableAccuSnap
   End If
End Sub



Private Sub IPrimitiveCommandEvents_Dynamics(point As Point3d, ByVal view As view, ByVal DrawMode As MsdDrawingMode)
'DRAW LEADER LINE WITH STATION AND OFFSET
   If beenPicked Then
      DrawTextAndLeader point, PointStationString(), pointOffsetString, False, view, DrawMode
      Exit Sub
   End If

'DRAW TETHER LINE WITH POINTER TO BASELINE STATION
   Dim station As Double
   Dim offset As Double
   Dim beginStation As Double
   If IsPointWithinSegment(point, baselineSegment, beginStation, station, offset) And Not beenPicked Then
'CALCULATE POINT ON THE BASELINE
      If baselineSegment.IsArcElement Then
         Dim PointOnBaseline As Point3d
         Dim FwdAz As Double
         GetBasePntFwdAzArc station, baselineSegment, beginStation, PointOnBaseline, FwdAz
      ElseIf baselineSegment.Type = msdElementTypeLineString Then
         GetBasePntFwdAzSpiral station, baselineSegment, PointOnBaseline, FwdAz
      Else
         GetBasePntFwdAzLine station, baselineSegment, beginStation, PointOnBaseline, FwdAz
      End If
'DRAW TETHER
      DrawTether PointOnBaseline, point, DrawMode

'DISPLAY STATION OFFSET
      ShowStatus "Sta. " & StationToString(station, DEFAULT_STATION_PRECISION, stationStyleGlobal) & " " & CreateOffsetString(offset)
   Else
      ShowStatus ""
   End If
End Sub



Private Sub IPrimitiveCommandEvents_Keyin(ByVal Keyin As String)
End Sub



Private Sub IPrimitiveCommandEvents_Reset()
   If Not beenPicked Then
'PICK NEW SEGMENT
     FrmStationInverse.PickNewSegment
   Else
'LOOK AGAIN FOR POINT TO LABEL
      UserFeedbackPick
      beenPicked = False
'ENABLE ACCUSNAP
      CommandState.EnableAccuSnap
   End If
End Sub




Private Sub IPrimitiveCommandEvents_Start()
'SET STATION STYLE
   stationStyleGlobal = 0

'OKAY TO CLOSE DIALOG BOX
   FrmStationInverse.DoNotClose = False
   UserFeedbackPick

'INITIALIZE FLAG
   beenPicked = False

'START DYNAMICS TO SHOW TETHER
   CommandState.StartDynamics
   
'ENABLE ACCUSNAP
   CommandState.EnableAccuSnap
End Sub

Attribute VB_Name = "StationPlotLocate"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit

Implements ILocateCommandEvents

Dim myLC As LocateCriteria


Private Sub ILocateCommandEvents_Accept(ByVal Element As Element, point As Point3d, ByVal view As view)
   FrmStationPlot.PickedElement = Element
End Sub



Private Sub ILocateCommandEvents_Cleanup()
'CLEAR PROMPT AREA
   ClearCommandPromptArea

'NOTIFY DIALOG BOX PROGRAM ENDING
   FrmStationPlot.NotifyOfQuit
End Sub



Private Sub ILocateCommandEvents_Dynamics(point As Point3d, ByVal view As view, ByVal DrawMode As MsdDrawingMode)
End Sub



Private Sub ILocateCommandEvents_LocateFailed()
   UserFeedbackPick
End Sub



Private Sub ILocateCommandEvents_LocateFilter(ByVal Element As Element, point As Point3d, Accepted As Boolean)
'INITIALIZE FLAG
   Accepted = False

'CHECK, MAKE SURE THEY ARE SURVEYOR TOOLS BASELINE SEGMENTS AND IN THE XY PLANE
   Select Case Element.Type
      Case msdElementTypeArc 'CHECK IF VALID ARC
         If ArcIsValidBaselineSegment(Element) Then
            'IT'S A GOOD ELEMENT
            Accepted = True
            UserFeedbackAccept
         End If
      Case msdElementTypeLine 'CHECK IF VALID LINE
         If LineIsValidBaselineSegment(Element) Then
            'IT'S A GOOD ELEMENT
            Accepted = True
            UserFeedbackAccept
         End If
      Case msdElementTypeLineString 'CHECK IF VALID SPIRAL
         If IsSpiralElementLite(Element) Then
            'IT'S A GOOD ELEMENT
            Accepted = True
            UserFeedbackAccept
         End If
   End Select
End Sub



Private Sub ILocateCommandEvents_LocateReset()
'QUIT
   CommandState.StartDefaultCommand
End Sub



Private Sub ILocateCommandEvents_Start()
'NOTIFY DIALOG BOX PROGRAM STARTING
   FrmStationPlot.NotifyOfOpen

'MAKE SURE NOTHING IS SELECTED
   ActiveModelReference.UnselectAllElements
   
'CREATE SCAN CRITERIA
   Set myLC = CommandState.CreateLocateCriteria(False)
   myLC.ExcludeAllTypes
   myLC.IncludeType msdElementTypeArc
   myLC.IncludeType msdElementTypeLine
   myLC.IncludeType msdElementTypeLineString

'START LOCATING PROCESS
   CommandState.SetLocateCriteria myLC

'PROVIDE INSTRUCTIONS TO USER
   UserFeedbackPick
End Sub



Private Sub UserFeedbackPick()
'PROVIDE INSTRUCTIONS TO USER
   ShowCommand COMMAND_NAME_STATION_PLOT
   ShowPrompt "Pick baseline segment"
End Sub



Private Sub UserFeedbackAccept()
'PROVIDE INSTRUCTIONS TO USER
   ShowCommand COMMAND_NAME_STATION_PLOT
   ShowPrompt "Accept to apply/Reset"
End Sub

Attribute VB_Name = "StationTextLocate"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit

Implements ILocateCommandEvents

Dim myLC As LocateCriteria


Private Sub ILocateCommandEvents_Accept(ByVal Element As Element, point As Point3d, ByVal view As view)
'PASS ACCEPTED ELEMENT TO DIALOG BOX
   FrmStationText.DoTheTextingAndTicks Element
End Sub



Private Sub ILocateCommandEvents_Cleanup()
'CLEAR PROMPT AREA
   ClearCommandPromptArea

'CLOSE DIALOG BOX
   FrmStationText.LocateIsClosing 5
End Sub



Private Sub ILocateCommandEvents_Dynamics(point As Point3d, ByVal view As view, ByVal DrawMode As MsdDrawingMode)
End Sub



Private Sub ILocateCommandEvents_LocateFailed()
'PROVIDE INSTRUCTIONS TO USER
   UserFeedbackPick
End Sub



Private Sub ILocateCommandEvents_LocateFilter(ByVal Element As Element, point As Point3d, Accepted As Boolean)
'INITIALIZE FLAG
   Accepted = False

'CHECK, MAKE SURE THEY ARE SURVEYOR TOOLS BASELINE SEGMENTS AND IN THE XY PLANE
   Select Case Element.Type
      Case msdElementTypeArc 'CHECK IF VALID ARC
         If ArcIsValidBaselineSegment(Element) Then
            'IT'S A GOOD ELEMENT
            Accepted = True
            UserFeedbackAccept
            FrmStationText.PickedElement = Element
         End If
      Case msdElementTypeLineString 'CHECK IF VALID SPIRAL
         If IsSpiralElementLite(Element) Then
             Accepted = True
             UserFeedbackAccept
             FrmStationText.PickedElement = Element
          End If
      Case msdElementTypeLine 'CHECK IF VALID LINE
         If LineIsValidBaselineSegment(Element) Then
            'IT'S A GOOD ELEMENT
            Accepted = True
            UserFeedbackAccept
            FrmStationText.PickedElement = Element
         End If
   End Select
End Sub



Private Sub ILocateCommandEvents_LocateReset()
'QUIT
   CommandState.StartDefaultCommand
End Sub



Private Sub ILocateCommandEvents_Start()
'MAKE SURE NOTHING IS SELECTED
   ActiveModelReference.UnselectAllElements
   
'CREATE SCAN CRITERIA
   Set myLC = CommandState.CreateLocateCriteria(True)
   myLC.ExcludeAllTypes
   myLC.IncludeType msdElementTypeArc
   myLC.IncludeType msdElementTypeLine
   myLC.IncludeType msdElementTypeLineString

'START LOCATING PROCESS
   CommandState.SetLocateCriteria myLC

'PROVIDE INSTRUCTIONS TO USER
   UserFeedbackPick
End Sub



Private Sub UserFeedbackPick()
'PROVIDE INSTRUCTIONS TO USER
   ShowCommand COMMAND_NAME_STATION_TEXT
   ShowPrompt "Pick baseline segment/Reset to quit"
End Sub



Private Sub UserFeedbackAccept()
'PROVIDE INSTRUCTIONS TO USER
   ShowCommand COMMAND_NAME_STATION_TEXT
   ShowPrompt "Accept to apply/Reset"
End Sub

Attribute VB_Name = "Symbols"
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

'GENERAL NOTES:
'RUN THESE ROUTINES FROM THE COMMAND LINE. THEY ARE THE STARTING
'POINTS. FOR EXAMPLE, ENTERING "VBA RUN SAMPLE" WOULD LAUNCH THE
'SAMPLE DIALOG BOX.

Option Explicit

Public Const ARROW_HEAD_ANGLE               As Double = 14   'FOR LEADER AND OTHER ARROW HEADS IN DEGREES
Public Const ARROW_LENGTH                   As Double = 2    'LENGTH OF ARROW IN CHARACTERS, FOR SYMBOLS MODULE
Public Const ARROW_HEAD_LENGTH              As Double = 0.9  'FOR LEADER AND OTHER ARROW HEADS IN CHARACTERS
Private previouslyLeft                      As Boolean       'STORES WHAT SIDE LEADER WAS ON LAST

Public Const SYMBOL_NONE = "SYMBOL_NONE"
Public Const SYMBOL_1 = "SYMBOL_1"
Public Const SYMBOL_2 = "SYMBOL_2"
Public Const SYMBOL_3 = "SYMBOL_3"
Public Const SYMBOL_4 = "SYMBOL_4"
Public Const SYMBOL_5 = "SYMBOL_5"
Public Const SYMBOL_6 = "SYMBOL_6"


Public Function CreateSpiralData(ByVal thetaString As String, _
                                 lengthString As String, _
                                 prefixString As String, _
                                 headingString As String, _
                                 InsertionPoint As Point3d, _
                                 ByVal prototype As Element, _
                                 Optional RotateZangle As Double = 0) As CellElement
'CALCULATE METRICS
   Dim characterSize As Double
   characterSize = GetCharSize()
   Dim halfChar As Double
   halfChar = characterSize / 2
   Dim lineHeight As Double
   lineHeight = characterSize * 1.4

'CREATE THETA TEXT ELEMENT
   Dim tInsertPoint As Point3d
   tInsertPoint = InsertionPoint
   tInsertPoint.Y = tInsertPoint.Y + lineHeight * 3
   Dim largestX As Double
   largestX = InsertionPoint.X
   Dim largestNumX As Double
   largestNumX = largestX
   thetaString = ReplaceDegreeSymbol2(thetaString)
   Dim thetaText As TextElement
   Set thetaText = CurveDataSub2(prototype, thetaString, tInsertPoint, tInsertPoint, lineHeight, largestX)

'CREATE LENGTH OF SPIRAL TEXT ELEMENT
   Dim lInsertPoint As Point3d
   Dim lengthOfSpiralText As TextElement
   Set lengthOfSpiralText = CurveDataSub2(prototype, lengthString, tInsertPoint, lInsertPoint, lineHeight, largestNumX)

'CALCULATE SHORT AND LONG TANGENT
   Dim spiralAngleDecimal As Double
   If AngleStringToDegree(thetaString, spiralAngleDecimal) Then
      Dim shortTangent As Double
      Dim longTangent As Double
      calcShortLongTanget spiralAngleDecimal, CDbl(lengthString), longTangent, shortTangent
   End If

'DETERMINE HOW MANY PRECISON TO DISPLAY BASED ON PRECISION OF SPIRAL LENGTH
   Dim prec As Long
   prec = StrPrec(lengthString)

'CREATE LONG TANGENT TEXT ELEMENT
   Dim longTangentString As String
   longTangentString = FormatNumber(longTangent, prec, vbTrue, vbFalse, vbTrue)
   Dim lTInsertPoint As Point3d
   Dim longTangentText As TextElement
   Set longTangentText = CurveDataSub2(prototype, longTangentString, lInsertPoint, lTInsertPoint, lineHeight, largestNumX)

'CREATE SHORT TANGENT TEXT ELEMENT
   Dim shortTangentString As String
   shortTangentString = FormatNumber(shortTangent, prec, vbTrue, vbFalse, vbTrue)
   Dim sTInsertPoint As Point3d
   Dim shortTangentText As TextElement
   Set shortTangentText = CurveDataSub2(prototype, shortTangentString, lTInsertPoint, sTInsertPoint, lineHeight, largestNumX)

'CALCULATE LARGEST X
   largestX = Max(largestNumX, largestX)

'LOOK FOR SMALLEST X
   Dim smallestX As Double
   smallestX = tInsertPoint.X

'CREATE THETA =
   Dim tEquals As TextElement
   Set tEquals = CurveDataSub1(prototype, "=", tInsertPoint, halfChar, smallestX)
   Dim tSymInsertPoint As Point3d
   tSymInsertPoint = tEquals.origin
   tSymInsertPoint.X = tSymInsertPoint.X - characterSize
   smallestX = Min(smallestX, tSymInsertPoint.X - halfChar)
   Dim theta As CellElement
   Set theta = CreateThetaSymbol(tSymInsertPoint, characterSize, prototype)

'CREATE L=
   Dim Lequals As TextElement
   Set Lequals = CurveDataSub1(prototype, "Ls =", lInsertPoint, halfChar, smallestX)

'CREATE LT=
   Dim LTequals As TextElement
   Set LTequals = CurveDataSub1(prototype, "LT =", lTInsertPoint, halfChar, smallestX)

'CREATE ST=
   Dim STequals As TextElement
   Set STequals = CurveDataSub1(prototype, "ST =", sTInsertPoint, halfChar, smallestX)


'CREATE HEADING TEXT ELEMENT
   Dim sDHeadingInsertPoint As Point3d
   sDHeadingInsertPoint = InsertionPoint
   sDHeadingInsertPoint.Y = sDHeadingInsertPoint.Y + lineHeight * 3#
   Dim spiralDataHeader As TextElement
   Set spiralDataHeader = CreateTextElement1(prototype, _
                                             prefixString & headingString, _
                                             sDHeadingInsertPoint, _
                                             Matrix3dIdentity)

'GET LENGTH OF HEADING TEXT ELEMENT
   Dim spiralDataHeadingDim As Point2d
   spiralDataHeader.GetTotalTextSize spiralDataHeadingDim.X, spiralDataHeadingDim.Y

'CENTER THE HEADING
   sDHeadingInsertPoint.X = (largestX + smallestX) / 2# - (spiralDataHeadingDim.X / 2#)
   spiralDataHeader.origin = sDHeadingInsertPoint

'DRAW HEADING LINE
   Dim LineStartPoint As Point3d
   LineStartPoint = spiralDataHeader.origin
   LineStartPoint.Y = LineStartPoint.Y - characterSize * 0.7
   Dim LineEndPoint As Point3d
   LineEndPoint = LineStartPoint
   Dim blockWidth As Double
   blockWidth = largestX - smallestX
   If blockWidth >= (spiralDataHeadingDim.X + characterSize) Then
      LineStartPoint.X = smallestX
      LineEndPoint.X = largestX
   Else
      LineStartPoint.X = spiralDataHeader.origin.X - halfChar
      LineEndPoint.X = LineStartPoint.X + spiralDataHeadingDim.X + characterSize
   End If
   Dim headingLine As LineElement
   Set headingLine = CreateLineElement2(prototype, LineStartPoint, LineEndPoint)
                                           
   Dim cellArray(0 To 10) As Element
   Set cellArray(0) = thetaText
   Set cellArray(1) = lengthOfSpiralText
   Set cellArray(2) = spiralDataHeader
   Set cellArray(3) = theta
   Set cellArray(4) = tEquals
   Set cellArray(5) = Lequals
   Set cellArray(6) = headingLine
   Set cellArray(7) = longTangentText
   Set cellArray(8) = shortTangentText
   Set cellArray(9) = LTequals
   Set cellArray(10) = STequals
   
   Set CreateSpiralData = CreateCellElement1(vbNullString, cellArray, InsertionPoint)
   CreateSpiralData.RotateAboutZ InsertionPoint, RotateZangle
End Function



Public Function CreateThetaSymbol(InsertionPoint As Point3d, ByVal charSize As Double, ByVal prototype As Element) As CellElement
   Dim halfHeight As Double
   halfHeight = charSize * 0.5
   
   Dim halfWidth As Double
   halfWidth = (charSize * 0.6) / 2#
   
   Dim pointLeft As Point3d
   pointLeft = InsertionPoint
   pointLeft.X = pointLeft.X - halfWidth

   Dim pointRight As Point3d
   pointRight = InsertionPoint
   pointRight.X = pointRight.X + halfWidth

   Dim cellArray(0 To 1) As Element
   Set cellArray(0) = CreateEllipseElement2(prototype, InsertionPoint, halfWidth, halfHeight, Matrix3dIdentity)
   Set cellArray(1) = CreateLineElement2(prototype, pointLeft, pointRight)

   Set CreateThetaSymbol = CreateCellElement1(vbNullString, cellArray, InsertionPoint)
End Function



Public Function CreateArrowCellMidOrigin(InsertionPoint As Point3d, ByVal characterSize As Double, prototype As Element) As CellElement
' creates arrow cell but does not make part of drawing
' arrow pointing East
   Dim ArrowCell(0 To 2) As Element
   Dim endShaft As Point3d
   Dim beginShaft As Point3d
   Dim headtop As Point3d
   Dim headbottom As Point3d
   Dim fract As Double
   Dim originPoint As Point3d
   Dim ShaftLength As Double
   ShaftLength = Abs(ARROW_LENGTH * characterSize)

   fract = 5
   originPoint = InsertionPoint
   beginShaft = originPoint
   endShaft = beginShaft
   beginShaft.X = beginShaft.X - (ShaftLength / 2)
   endShaft.X = endShaft.X + (ShaftLength / 2)
   
   Set ArrowCell(0) = CreateLineElement2(prototype, beginShaft, endShaft)
   headtop = endShaft
   headtop.X = headtop.X - (ShaftLength) / 3
   headtop.Y = headtop.Y + (characterSize / fract)
   headbottom = headtop
   headbottom.Y = beginShaft.Y - (characterSize / fract)
   Set ArrowCell(1) = CreateLineElement2(prototype, endShaft, headtop)
   Set ArrowCell(2) = CreateLineElement2(prototype, endShaft, headbottom)
   Set CreateArrowCellMidOrigin = CreateCellElement1(vbNullString, ArrowCell, originPoint)
End Function


Public Function CreateSymbol1Cell(template As Element, originPoint As Point3d, characterSize As Double, Optional RotateZangle As Double = 0) As CellElement
   Dim armLength As Double
   armLength = characterSize / 2
   Dim ArmEnd As Point3d
   ArmEnd = originPoint
   Dim CrossLines(0 To 4) As Element
   Set CrossLines(0) = CreateEllipseElement2(template, originPoint, armLength, armLength, Matrix3dIdentity)
   
   ArmEnd.Y = ArmEnd.Y + armLength
   Set CrossLines(1) = CreateLineElement2(template, originPoint, ArmEnd)
   ArmEnd = originPoint
   ArmEnd.X = ArmEnd.X + armLength
   Set CrossLines(2) = CreateLineElement2(template, originPoint, ArmEnd)
   
   ArmEnd = originPoint
   ArmEnd.Y = ArmEnd.Y - armLength
   Set CrossLines(3) = CreateLineElement2(template, originPoint, ArmEnd)

   ArmEnd = originPoint
   ArmEnd.X = ArmEnd.X - armLength
   Set CrossLines(4) = CreateLineElement2(template, originPoint, ArmEnd)

   Dim Symbol1Cell As CellElement
   Set Symbol1Cell = CreateCellElement1(vbNullString, CrossLines, originPoint)
   Set CreateSymbol1Cell = Symbol1Cell
   CreateSymbol1Cell.RotateAboutZ originPoint, RotateZangle
End Function



Public Function CreateSymbol2Cell(template As Element, originPoint As Point3d, characterSize As Double, Optional RotateZangle As Double = 0) As CellElement
   Dim D08 As Double
   D08 = characterSize
   Dim halfD As Double
   halfD = D08 / 2
   
   Dim ArmEnd As Point3d
   ArmEnd = originPoint
   ArmEnd.X = ArmEnd.X + halfD
   ArmEnd.Y = ArmEnd.Y + halfD
   Dim CrossLines(0 To 3) As Element
   Set CrossLines(0) = CreateLineElement2(template, originPoint, ArmEnd)
   
   ArmEnd = originPoint
   ArmEnd.X = ArmEnd.X + halfD
   ArmEnd.Y = ArmEnd.Y - halfD
   Set CrossLines(1) = CreateLineElement2(template, originPoint, ArmEnd)
   
   ArmEnd = originPoint
   ArmEnd.X = ArmEnd.X - halfD
   ArmEnd.Y = ArmEnd.Y - halfD
   Set CrossLines(2) = CreateLineElement2(template, originPoint, ArmEnd)

   ArmEnd = originPoint
   ArmEnd.X = ArmEnd.X - halfD
   ArmEnd.Y = ArmEnd.Y + halfD
   Set CrossLines(3) = CreateLineElement2(template, originPoint, ArmEnd)

   Set CreateSymbol2Cell = CreateCellElement1(vbNullString, CrossLines, originPoint)
   CreateSymbol2Cell.RotateAboutZ originPoint, RotateZangle
End Function



Public Function CreateSymbol3Cell(template As Element, originPoint As Point3d, characterSize As Double, Optional RotateZangle As Double = 0) As CellElement
   Dim armLength As Double
   armLength = characterSize / 2
   
   Dim ArmEnd As Point3d
   ArmEnd = originPoint
   ArmEnd.Y = ArmEnd.Y + armLength
   Dim CrossLines(0 To 7) As Element
   Set CrossLines(0) = CreateLineElement2(template, originPoint, ArmEnd)
   
   ArmEnd = originPoint
   ArmEnd.X = ArmEnd.X + armLength
   Set CrossLines(1) = CreateLineElement2(template, originPoint, ArmEnd)
   
   ArmEnd = originPoint
   ArmEnd.Y = ArmEnd.Y - armLength
   Set CrossLines(2) = CreateLineElement2(template, originPoint, ArmEnd)

   ArmEnd = originPoint
   ArmEnd.X = ArmEnd.X - armLength
   Set CrossLines(3) = CreateLineElement2(template, originPoint, ArmEnd)

   Dim cornerA As Point3d
   cornerA = originPoint
   cornerA.X = cornerA.X + armLength
   cornerA.Y = cornerA.Y + armLength

   Dim cornerB As Point3d
   cornerB = cornerA
   cornerB.Y = originPoint.Y - armLength
   
   Dim cornerC As Point3d
   cornerC = cornerB
   cornerC.X = originPoint.X - armLength
   
   Dim cornerD As Point3d
   cornerD = cornerC
   cornerD.Y = cornerA.Y
   
   Set CrossLines(4) = CreateLineElement2(template, cornerA, cornerB)
   Set CrossLines(5) = CreateLineElement2(template, cornerB, cornerC)
   Set CrossLines(6) = CreateLineElement2(template, cornerC, cornerD)
   Set CrossLines(7) = CreateLineElement2(template, cornerD, cornerA)
   
   Set CreateSymbol3Cell = CreateCellElement1(vbNullString, CrossLines, originPoint)
   CreateSymbol3Cell.RotateAboutZ originPoint, RotateZangle
End Function



Public Function CreateSymbol4Cell(template As Element, originPoint As Point3d, characterSize As Double, Optional RotateZangle As Double = 0) As CellElement
   Dim D08 As Double
   D08 = characterSize
   Dim halfD08 As Double
   halfD08 = D08 / 2
   Dim eighthD08 As Double
   eighthD08 = D08 / 8
   Dim CrossLines(0 To 3) As Element
   Set CrossLines(0) = CreateEllipseElement2(template, originPoint, eighthD08, eighthD08, Matrix3dIdentity)
   Dim cornerA As Point3d
   cornerA = originPoint
   cornerA.Y = cornerA.Y + 0.577 * D08
   Dim cornerB As Point3d
   cornerB = originPoint
   cornerB.X = cornerB.X + halfD08
   cornerB.Y = cornerB.Y - 0.289 * D08
   Dim cornerC As Point3d
   cornerC = cornerB
   cornerC.X = originPoint.X - halfD08
   Set CrossLines(1) = CreateLineElement2(template, cornerA, cornerB)
   Set CrossLines(2) = CreateLineElement2(template, cornerB, cornerC)
   Set CrossLines(3) = CreateLineElement2(template, cornerC, cornerA)
   Set CreateSymbol4Cell = CreateCellElement1(vbNullString, CrossLines, originPoint)
   CreateSymbol4Cell.RotateAboutZ originPoint, RotateZangle
End Function




Public Function CreateSymbol5Cell(template As Element, originPoint As Point3d, characterSize As Double, Optional RotateZangle As Double = 0) As CellElement
   Dim circleDiameter As Double
   circleDiameter = characterSize / 3.5
   Dim cellArray(0 To 0) As Element
   Set cellArray(0) = CreateEllipseElement2(template, originPoint, circleDiameter, circleDiameter, Matrix3dIdentity)
   Set CreateSymbol5Cell = CreateCellElement1(vbNullString, cellArray, originPoint)
   CreateSymbol5Cell.RotateAboutZ originPoint, RotateZangle
End Function



Public Function CreateSymbol6Cell(template As Element, originPoint As Point3d, characterSize As Double, Optional RotateZangle As Double = 0) As CellElement
   Dim outerRadius As Double
   outerRadius = characterSize / 2
   Dim innerRadius As Double
   innerRadius = outerRadius * 0.67
   Dim Circles(0 To 1) As Element
   Set Circles(0) = CreateEllipseElement2(template, originPoint, outerRadius, outerRadius, Matrix3dIdentity)
   Set Circles(1) = CreateEllipseElement2(template, originPoint, innerRadius, innerRadius, Matrix3dIdentity)
   Set CreateSymbol6Cell = CreateCellElement1(vbNullString, Circles, originPoint)
   CreateSymbol6Cell.RotateAboutZ originPoint, RotateZangle
End Function




Public Function CreateCurveDataCell(insertPoint As Point3d, _
                                    rotationRadians As Double, _
                                    templateTextElement As TextElement, _
                                    ByVal deltaString As String, _
                                    ByVal halfDeltaString As String, _
                                    radiusString As String, _
                                    tangentString As String, _
                                    longChordString As String, _
                                    curveLengthString As String, _
                                    curveDataPrefix As String, _
                                    curveDataHeading As String, _
                                    Optional alignRight As Boolean = False) As CellElement
                                        

'CALCULATE METRICS
   Dim characterSize As Double
   characterSize = GetCharSize()
   Dim halfChar As Double
   halfChar = characterSize / 2
   Dim lineHeight As Double
   lineHeight = characterSize * 1.4
    
'CREATE DELTA TEXT ELEMENT
   Dim dInsertPoint As Point3d
   dInsertPoint = insertPoint
   dInsertPoint.Y = dInsertPoint.Y + lineHeight * 3
   Dim largestX As Double
   largestX = insertPoint.X
   Dim largestNumX As Double
   largestNumX = largestX
   Dim origPrec As Long
   Dim degPart As Long
   Dim minPart As Long
   Dim secPart As Double
   If IsDeltaString(deltaString, origPrec, degPart, minPart, secPart) Then
      deltaString = DirString(degPart, minPart, secPart, origPrec, DIR_TYPE_AZIMUTH, STYLE_ANGLE_CARET Or STYLE_ANGLE_LEAD)
   End If
   Dim DeltaText As TextElement
   Set DeltaText = CurveDataSub2(templateTextElement, deltaString, dInsertPoint, dInsertPoint, lineHeight, largestX)

'CREATE HALF DELTA TEXT ELEMENT
   Dim hDInsertPoint As Point3d
   If IsDeltaString(halfDeltaString, origPrec, degPart, minPart, secPart) Then
      halfDeltaString = DirString(degPart, minPart, secPart, origPrec, DIR_TYPE_AZIMUTH, STYLE_ANGLE_CARET Or STYLE_ANGLE_LEAD)
   End If
   
   Dim halfDeltaText As TextElement
   Set halfDeltaText = CurveDataSub2(templateTextElement, halfDeltaString, dInsertPoint, hDInsertPoint, lineHeight, largestX)

'CREATE RADIUS TEXT ELEMENT
   Dim rInsertPoint As Point3d
   Dim RadiusText As TextElement
   Set RadiusText = CurveDataSub2(templateTextElement, radiusString, hDInsertPoint, rInsertPoint, lineHeight, largestNumX)
   
'CREATE TANGENT TEXT ELEMENT
   Dim tInsertPoint As Point3d
   Dim tangentText As TextElement
   Set tangentText = CurveDataSub2(templateTextElement, tangentString, rInsertPoint, tInsertPoint, lineHeight, largestNumX)
   
'CREATE CHORD TEXT ELEMENT
   Dim cInsertPoint As Point3d
   Dim chordText As TextElement
   Set chordText = CurveDataSub2(templateTextElement, longChordString, tInsertPoint, cInsertPoint, lineHeight, largestNumX)

'CREATE LENGTH OF CURVE TEXT ELEMENT
   Dim lInsertPoint As Point3d
   Dim lengthOfCurveText As TextElement
   Set lengthOfCurveText = CurveDataSub2(templateTextElement, curveLengthString, cInsertPoint, lInsertPoint, lineHeight, largestNumX)
   
'CALCULATE LARGEST X
   largestX = Max(largestNumX, largestX)

'LOOK FOR SMALLEST X
   Dim smallestX As Double
   smallestX = dInsertPoint.X

'CREATE DELTA =
   Dim dEquals As TextElement
   Set dEquals = CurveDataSub1(templateTextElement, "=", dInsertPoint, halfChar, smallestX)
   Dim dSymInsertPoint As Point3d
   dSymInsertPoint = dEquals.origin
   dSymInsertPoint.X = dSymInsertPoint.X - characterSize
   smallestX = Min(smallestX, dSymInsertPoint.X - halfChar)
   Dim delta As CellElement
   Set delta = CreateDeltaSymbol(dSymInsertPoint, characterSize, templateTextElement)

'CREATE HALF DELTA =
   Dim hDEquals As TextElement
   Set hDEquals = CurveDataSub1(templateTextElement, "/2 =", hDInsertPoint, halfChar, smallestX)
   Dim d2SymInsertPoint As Point3d
   d2SymInsertPoint = hDEquals.origin
   d2SymInsertPoint.X = d2SymInsertPoint.X - characterSize
   Dim delta2 As CellElement
   Set delta2 = CreateDeltaSymbol(d2SymInsertPoint, characterSize, templateTextElement)

'CREATE R=
   Dim rEquals As TextElement
   Set rEquals = CurveDataSub1(templateTextElement, "R =", rInsertPoint, halfChar, smallestX)

'CREATE T=
   Dim tEquals As TextElement
   Set tEquals = CurveDataSub1(templateTextElement, "T =", tInsertPoint, halfChar, smallestX)

'CREATE C=
   Dim Cequals As TextElement
   Set Cequals = CurveDataSub1(templateTextElement, "C =", cInsertPoint, halfChar, smallestX)

'CREATE L=
   Dim Lequals As TextElement
   Set Lequals = CurveDataSub1(templateTextElement, "Lc =", lInsertPoint, halfChar, smallestX)

'MOVE THEM RIGHT IF ALIGN RIGHT
   If alignRight Then
      CurveDataSub3 RadiusText, largestNumX
      CurveDataSub3 tangentText, largestNumX
      CurveDataSub3 chordText, largestNumX
      CurveDataSub3 lengthOfCurveText, largestNumX
   End If
   
'CREATE HEADING TEXT ELEMENT
   Dim cDHeadingInsertPoint As Point3d
   cDHeadingInsertPoint = insertPoint
   cDHeadingInsertPoint.Y = cDHeadingInsertPoint.Y + lineHeight * 3
   Dim curveDataHeader As TextElement
   Set curveDataHeader = CreateTextElement1(templateTextElement, _
                                            curveDataPrefix & curveDataHeading, _
                                            cDHeadingInsertPoint, _
                                            Matrix3dIdentity)
                                           
'GET LENGTH OF HEADING TEXT ELEMENT
   Dim curveDataHeadingDim As Point2d
   curveDataHeader.GetTotalTextSize curveDataHeadingDim.X, curveDataHeadingDim.Y

'CENTER THE HEADING
   cDHeadingInsertPoint.X = (largestX + smallestX) / 2 - (curveDataHeadingDim.X / 2)
   curveDataHeader.origin = cDHeadingInsertPoint

'DRAW HEADING LINE
   Dim LineStartPoint As Point3d
   LineStartPoint = curveDataHeader.origin
   LineStartPoint.Y = LineStartPoint.Y - characterSize * 0.7
   Dim LineEndPoint As Point3d
   LineEndPoint = LineStartPoint
   Dim blockWidth As Double
   blockWidth = largestX - smallestX
   If blockWidth >= (curveDataHeadingDim.X + characterSize) Then
      LineStartPoint.X = smallestX
      LineEndPoint.X = largestX
   Else
      LineStartPoint.X = curveDataHeader.origin.X - halfChar
      LineEndPoint.X = LineStartPoint.X + curveDataHeadingDim.X + characterSize
   End If
   Dim headingLine As LineElement
   Set headingLine = CreateLineElement2(templateTextElement, LineStartPoint, LineEndPoint)

'CREATE THE CURVE DATA CELL
   Dim TheCellElements(1 To 16) As Element
   Set TheCellElements(1) = curveDataHeader
   Set TheCellElements(2) = DeltaText
   Set TheCellElements(3) = halfDeltaText
   Set TheCellElements(4) = RadiusText
   Set TheCellElements(5) = tangentText
   Set TheCellElements(6) = chordText
   Set TheCellElements(7) = lengthOfCurveText
   Set TheCellElements(8) = dEquals
   Set TheCellElements(9) = hDEquals
   Set TheCellElements(10) = rEquals
   Set TheCellElements(11) = tEquals
   Set TheCellElements(12) = Cequals
   Set TheCellElements(13) = Lequals
   Set TheCellElements(14) = delta
   Set TheCellElements(15) = delta2
   Set TheCellElements(16) = headingLine
   Dim CurveDataCell As CellElement
   Set CurveDataCell = CreateCellElement1(vbNullString, TheCellElements, insertPoint)
   CurveDataCell.RotateAboutZ insertPoint, rotationRadians

'RETURN THE CURVE DATA CELL
   Set CreateCurveDataCell = CurveDataCell
End Function



Private Function CurveDataSub1(textTemplate As TextElement, _
                               theText As String, _
                               initInsertPoint As Point3d, _
                               halfChar As Double, _
                               ByRef smallestX As Double) As TextElement
   Dim textEl As TextElement
   Set CurveDataSub1 = CreateTextElement1(textTemplate, theText, initInsertPoint, Matrix3dIdentity)
   Dim texMet As Point2d
   CurveDataSub1.GetTotalTextSize texMet.X, texMet.Y
   Dim newInsertPoint As Point3d
   newInsertPoint = initInsertPoint
   newInsertPoint.X = newInsertPoint.X - (texMet.X + halfChar)
   CurveDataSub1.origin = newInsertPoint
   smallestX = Min(smallestX, newInsertPoint.X)
End Function



Private Function CurveDataSub2(textTemplate As TextElement, _
                               theText As String, _
                               initInsertPoint As Point3d, _
                               ByRef newInsertPoint As Point3d, _
                               lineHeight As Double, _
                               ByRef largestX As Double) As TextElement
   newInsertPoint = initInsertPoint
   newInsertPoint.Y = newInsertPoint.Y - lineHeight
   Set CurveDataSub2 = CreateTextElement1(textTemplate, theText, newInsertPoint, Matrix3dIdentity)
   Dim texMet As Point2d
   CurveDataSub2.GetTotalTextSize texMet.X, texMet.Y
   largestX = Max(largestX, newInsertPoint.X + texMet.X)
End Function



Private Sub CurveDataSub3(TheTextElement As TextElement, largestNumX As Double)
   Dim texMet As Point2d
   Dim newOrigin As Point3d
   TheTextElement.GetTotalTextSize texMet.X, texMet.Y
   newOrigin = TheTextElement.origin
   newOrigin.X = largestNumX - texMet.X
   TheTextElement.origin = newOrigin
End Sub



Public Function CreateArrowLeader(ArrowTip As Point3d, _
                                  ArrowEnd As Point3d, _
                                  charSize As Double, _
                                  theTemplate As Element, _
                                  rotateToAngleRadians As Double, _
                                  TailLength As Double, _
                                  LabelOffset As Double, _
                                  ByRef isLeft As Boolean, _
                                  ByRef labelPoint As Point3d, _
                                  ByRef leadLengthChars As Double) As CellElement
                                  'isLeft returns which side it is, LabelPoint returns where to insert object
   Dim theTip As Point3d
   Dim TheEnd As Point3d
   Dim TailEnd As Point3d
   Dim LeftEnd As Point3d
   Dim RightEnd As Point3d
   Dim offset As Point3d
   
   Dim headToTailAzimuth As Double  ' in decimal degrees
   Dim ShaftLength As Double
   
   Dim HeadLeftLineElement As LineElement
   Dim HeadRightLineElement As LineElement
   Dim ShaftLineElement As LineElement
   Dim TailLineElement As LineElement
   
   Dim HeadLeftAzimuth As Double
   Dim HeadRightAzimuth As Double
   Dim TailAzimuth As Double
   Dim viewAzimuth As Double
   
   theTip = ArrowTip
   TheEnd = ArrowEnd
   TheEnd.z = ArrowTip.z
 
   Inverse theTip, TheEnd, headToTailAzimuth, ShaftLength
   
   viewAzimuth = 180 - Degrees(rotateToAngleRadians)
   Dim relAngle As Double
   relAngle = To360(viewAzimuth, headToTailAzimuth)
   Dim flipAngleDegrees As Double 'ANGLE OFF OF VERTICAL THAT LEADER WILL FLIP LEFT-RIGHT AT
   flipAngleDegrees = 20

   If previouslyLeft Then
      If relAngle < (180 + flipAngleDegrees) Or relAngle > (360 - flipAngleDegrees) Then
         isLeft = True
         TailAzimuth = viewAzimuth - 90
      Else
         isLeft = False
         TailAzimuth = viewAzimuth + 90
      End If
   Else
      If relAngle < (180 - flipAngleDegrees) And relAngle > flipAngleDegrees Then
         isLeft = True
         TailAzimuth = viewAzimuth - 90
      Else
         isLeft = False
         TailAzimuth = viewAzimuth + 90
      End If
   End If
   previouslyLeft = isLeft

   RightEnd = CoordFwdSAz(theTip, headToTailAzimuth + ARROW_HEAD_ANGLE, charSize * ARROW_HEAD_LENGTH)
   LeftEnd = CoordFwdSAz(theTip, headToTailAzimuth - ARROW_HEAD_ANGLE, charSize * ARROW_HEAD_LENGTH)
   TailEnd = CoordFwdSAz(TheEnd, TailAzimuth, charSize * TailLength)
   labelPoint = CoordFwdSAz(TheEnd, TailAzimuth, charSize * LabelOffset)

   Set ShaftLineElement = CreateLineElement2(theTemplate, TheEnd, theTip)
   Set HeadLeftLineElement = CreateLineElement2(theTemplate, theTip, LeftEnd)
   Set HeadRightLineElement = CreateLineElement2(theTemplate, theTip, RightEnd)
   Set TailLineElement = CreateLineElement2(theTemplate, TheEnd, TailEnd)

   Dim leaderCell As CellElement
   Dim arrayForCell(1 To 4) As Element

   Set arrayForCell(1) = ShaftLineElement
   Set arrayForCell(2) = HeadLeftLineElement
   Set arrayForCell(3) = HeadRightLineElement
   Set arrayForCell(4) = TailLineElement
   Set CreateArrowLeader = CreateCellElement1(vbNullString, arrayForCell, ArrowTip)
   leadLengthChars = ShaftLength / charSize
End Function



Public Function CreateDeltaSymbol(InsertionPoint As Point3d, ByVal charSize As Double, ByVal prototype As Element) As CellElement
   Dim cellArray(1 To 3) As Element
   Dim originPoint As Point3d
   Dim cornerA As Point3d
   Dim cornerB As Point3d
   Dim cornerC As Point3d
   Dim halfChar As Double
   
   originPoint = InsertionPoint
   halfChar = charSize / ARROW_LENGTH
   
   cornerA = originPoint
   cornerA.Y = cornerA.Y + 0.577 * charSize
   cornerB = originPoint
   cornerB.X = cornerB.X + halfChar
   cornerB.Y = cornerB.Y - 0.289 * charSize
   cornerC = cornerB
   cornerC.X = originPoint.X - halfChar

   Set cellArray(1) = CreateLineElement2(prototype, cornerA, cornerB)
   Set cellArray(2) = CreateLineElement2(prototype, cornerC, cornerB)
   Set cellArray(3) = CreateLineElement2(prototype, cornerA, cornerC)

   Set CreateDeltaSymbol = CreateCellElement1(vbNullString, cellArray, originPoint)
End Function



Public Function MyCreateArrowCell(inPoint As Point3d, ByVal characterSize As Double, ByVal pointsLeft As Boolean, prototype As Element) As CellElement
' creates arrow cell but does not make part of drawing
   Dim ArrowCell(0 To 2) As Element
   Dim endShaft As Point3d
   Dim headtop As Point3d
   Dim headbottom As Point3d
   Dim fract As Double
   Dim InsertionPoint As Point3d
   
   fract = 5
   
'MAKE WORKING COPY
   InsertionPoint = inPoint
   
   endShaft = InsertionPoint
   endShaft.X = endShaft.X + ARROW_LENGTH * characterSize
   Set ArrowCell(0) = CreateLineElement2(prototype, InsertionPoint, endShaft)
   If pointsLeft = True Then
      headtop = InsertionPoint
      headtop.X = headtop.X + (ARROW_LENGTH * characterSize) / 3
      headtop.Y = headtop.Y + (characterSize / fract)
      headbottom = headtop
      headbottom.Y = InsertionPoint.Y - (characterSize / fract)
      Set ArrowCell(1) = CreateLineElement2(prototype, InsertionPoint, headtop)
      Set ArrowCell(2) = CreateLineElement2(prototype, InsertionPoint, headbottom)
   Else
      headtop = endShaft
      headtop.X = headtop.X - (ARROW_LENGTH * characterSize) / 3
      headtop.Y = headtop.Y + (characterSize / fract)
      headbottom = headtop
      headbottom.Y = InsertionPoint.Y - (characterSize / fract)
      Set ArrowCell(1) = CreateLineElement2(prototype, endShaft, headtop)
      Set ArrowCell(2) = CreateLineElement2(prototype, endShaft, headbottom)
   End If
   Set MyCreateArrowCell = CreateCellElement1(vbNullString, ArrowCell, InsertionPoint)
End Function

Attribute VB_Name = "TextEntriesAndChkBox"
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.



'GENERAL NOTES:
'ALL THESE ROUTINES WERE WRITTEN BY JASON LOOK.  THEY ARE NOT
'WRITTEN IN THE STYLE COMMONLY USED BY PROFESSIONAL PROGRAMMERS.
'THEY ARE WRITTEN IN THE STYLE PREFERRED BY JASON.  JASON IS NOT
'A PROFESSIONAL PROGRAMMER!
'
'
'THIS MODULE IS JUST GENERIC VBA, IT DOES NOT CONTAIN ANY API
'SPECIFIC CODE.
'
'
'The strategy is this.  DEGREES,MINUTES,SECONDS format, or DMS
'as it will be referred to from here, is only used for input
'and for output.  Calculations will be done using mostly decimal
'degrees and radians.  In addition to that, Calculation will be
'done using South azimuth when directions are needed.  If you
'use North azimuth, set the constant NORTH_AZIMUTH_MODE to True
'and the routines that take a South azimuth and make an azimuth
'string will change accordingly.  Also, the functions that take
'an azimuth string and convert them to a South azimuth will
'convert them appropriately.
'
'
'DIRECTION ENTRIES WILL EITHER BE IN AZIMUTH OR BEARING
'   Type of azimuth (North or South) is not determined
'   from keyed in entries.  Instead, a mode toggle
'   shall be used if ever needed.  INTERNALLY,
'   ALL COGO CALCULATION ARE DONE IN SOUTH AZIMUTH.
'
'ALLOWABLE DIRECTION ENTRIES
'   AZIMUTHS:
'       no sign
'       leading zero for degrees optional
'
'       if keyed in as a number, there is no space
'       between the degrees and the decimal point,
'       and no space between the decimal point and
'       the minutes.
'       Leading zeros are important for minutes and
'       seconds.  Trailing zeros are not important
'       for minutes and seconds.
'       123degrees 10minutes could be keyed in "123.1"
'       12degrees 5minutes could be keyed in "12.05"
'       0degrees 5minutes 30.25sconds could be keyed
'       in "0.053025" or ".053025"
'
'   BEARINGS:
'       QUADRANT NOTATION FORMAT FOR KEY ENTRIES
'       DMS prefixed and postfixed
'       with signs for quadrants or letters
'       the order of the signs is Northing Easting
'       N23^10'20"W could be entered like +23.1020-
'       or N23.1020W or n23.1020w,
'       no mixing signs and letters.
'       the signs are chosen because they are on
'       the keypad making it easy to enter.
'       It's also easier to differentiate from an
'       angle or azimuth.
'
'
'HORIZONTAL COORDINATE ENTRIES ARE ENTERED BY NORTHING/EASTING
'   A Northing or Easting field can be entered in the normal
'   way of just entering a positive or negative number.
'   Optionally, it can be entered by entering it with the
'   traditional N,S,E, or W appended to the end of the number.
'   If entering it with the letter on the end, a negative sign
'   is not allowed.  A third way to enter the value is to have
'   sign on the end instead of the letters. The plus sign
'   would be for N or E and the negative sign would be for the
'   W or S.  Again, no prefix allowed when entering this way.
'   The advantage with this third method is that we often read
'   the coordinates from left to right and enter them as we read
'   them.  We do not always scan the line first then enter the
'   sign, then start entering the coordinate's value.  This
'   way, we can just enter it the way we read it, left to right.
'
'
'STATIONS ENTRIES ARE STRAIGHT FORWARD
'   One can enter stations just as a number or a number with
'   the plus sign stuck in it.
'
'
'IMPLIED PRECISION
'   "Implied Precision" might mean something in the scientific
'   world, but here, it is the name given to a feature.  I have
'   not seen this feature in any other software, so it will be
'   described here.  Everybody knows what fixed precision is.
'   Say, when you enter "27" into a field where its precision is
'   fixed at two decimal places, it is displayed as "27.00".  With
'   Implied Precision, when you enter 27, it gets displayed as
'   "27".  If you enter it as "27.0", it gets displayed as "27.0".
'   This is similar to floating point, except if you entered
'   "27.0" in floating point, it would display as "27".  This
'   is useful for several issues like "too many zeros," as my old
'   boss used to say, or "where do I change the precision."  It
'   is not a panacea.  It is appropriate to have fixed precision
'   for some things, but it's useful in things like plotting
'   boundaries where the chord azimuth sometimes needs a little
'   more precison from the rest of the lot.  The routines are
'   coded so that you can choose a fixed precision for the field
'   or don't enter a precision and it will use Implied Precision.
'   Most of the Save????Entry subroutines have it.
'
'   There is a max precision set for these fields, when the keyed
'   in precision is higher than the max precision, the max precision
'   prevails.  Otherwise, entering a value with excessive precision
'   could cause crashing and other undesired results.
'
'





Option Explicit

Public Const MAX_LEN_COORDINATE_STRING             As Long = 18  '9,999,999.999999 N
Public Const MAX_LEN_DIR_STRING                    As Long = 19  'Ndd^ mm' ss.sssssE"
Public Const MAX_LEN_DIST_STRING                   As Long = 14  '9,999,999.9999
Public Const MAX_LEN_ELEV_STRING                   As Long = 12  '-99,999.9999
Public Const MAX_LEN_FONT_SCALE_STRING             As Long = 7   '9.99999
Public Const MAX_LEN_HEADING                       As Long = 35
Public Const MAX_LEN_PLOT_SCALE_STRING             As Long = 6   '10,000
Public Const MAX_LEN_POINT_DESC                    As Long = 24
Public Const MAX_LEN_POINT_NAME                    As Long = 18
Public Const MAX_LEN_NONEG_STRING                  As Long = 17  '99,999,999.999999
Public Const MAX_LEN_PREFIX                        As Long = 30
Public Const MAX_LEN_RADIUS_STRING                 As Long = 14  '9,999,999.9999
Public Const MAX_LEN_STA_STRING                    As Long = 14  '12 SIGNIFICANT DIGITS, PLUS SIGN, POSSIBLE MINUS SIGN
Public Const MAX_LEN_TRANSFORM_SCALE_STRING        As Long = 13  '9.99999999999
Public Const MAX_PRECISION_COORDINATE              As Long = 6
Public Const MAX_PRECISION_DISTANCE                As Long = 4
Public Const MAX_PRECISION_ELEV                    As Long = 4
Public Const MAX_PRECISION_FONT_SCALE              As Long = 5
Public Const MAX_PRECISION_OG                      As Long = 9   'MAX_PRECISION_SECONDS + 4
Public Const MAX_PRECISION_OFFSET                  As Long = 3
Public Const MAX_PRECISION_PLOT_SCALE              As Long = 2   'TO ACCOMODATE 2.5 AND 1.25
Public Const MAX_PRECISION_RADIUS                  As Long = 4   'NOT SURE WHAT IT SHOULD BE
Public Const MAX_PRECISION_SECONDS                 As Long = 5   'SECONDS TO 5 DECIMAL PLACES MAX
Public Const MAX_PRECISION_STATION                 As Long = 3   'WORKS FOR BOTH METRIC AND ENGLISH
Public Const MAX_PRECISION_TRANFORM_SCALE          As Long = 11

Public Const MAX_COORDINATE                        As Double = 9999999.999999
Public Const MAX_DISTANCE                          As Double = 9999999.9999
Public Const MAX_ELEVATION                         As Double = 99999.9999
Public Const MAX_FONT_SCALE                        As Double = 9.99999
Public Const MAX_PLOT_SCALE                        As Double = 10000#
Public Const MAX_POINT_NUMBER                      As Long = 999999
Public Const MAX_RADIUS                            As Double = 9999999.9999
Public Const MAX_STATION                           As Double = 99999999.999
Public Const MAX_TRANSFORM_SCALE                   As Double = 9.99999999999

Public Const DIR_TYPE_AZIMUTH                      As Integer = 0
Public Const DIR_TYPE_BEARING                      As Integer = 1

Public Const QUAD_NORTH_EAST                       As Integer = 11
Public Const QUAD_SOUTH_EAST                       As Integer = 21
Public Const QUAD_SOUTH_WEST                       As Integer = 22
Public Const QUAD_NORTH_WEST                       As Integer = 12

Public Const NORTH                                 As Integer = 10
Public Const SOUTH                                 As Integer = 20
Public Const EAST                                  As Integer = 1
Public Const WEST                                  As Integer = 2

Public Const STRING_CARET                          As String = "^"
Public Const STRING_SPACE                          As String = " "
Public Const STRING_PLUS                           As String = "+"
Public Const STRING_MINUS                          As String = "-"
Public Const STRING_DOT                            As String = "."
Public Const STRING_ZERO                           As String = "0"
Public Const STRING_N                              As String = "N"
Public Const STRING_E                              As String = "E"
Public Const STRING_S                              As String = "S"
Public Const STRING_W                              As String = "W"

'STYLES
'YOU CAN COMBINE STYLES BY USING BITWISE Or
Public Const STYLE_ANGLE_SPACE                     As Integer = 1   'SPACE BETWEEN DEGREES AND MINUTES, MINUTES AND SECONDS
Public Const STYLE_ANGLE_LEAD                      As Integer = 2   'LEADING ZEROS
Public Const STYLE_ANGLE_DEG_LEAD                  As Integer = 4   'USED FOR BEARINGS GENERATION, NO NEED TO USE
Public Const STYLE_ANGLE_CARET                     As Integer = 8   'USE CARET FOR DEGREE SYMBOL
Public Const STYLE_ANGLE_NO_00_MIN                 As Integer = 16  'LEAVE OFF MINUTES WHEN MINUTES AND SECONDS ARE ZERO
Public Const STYLE_ANGLE_NO_00_SEC                 As Integer = 32  'LEAVE OFF SECONDS WHEN SECONDS ARE ZERO

Public Const STYLE_STATION_NO_0_FRAC               As Integer = 1   'LEAVE OFF THE FRACTIONAL PART WHEN IT'S ZERO
Public Const STYLE_STATION_NO_BALLS_0_FRAC         As Integer = 2   'LEAVE OFF THE FRACTIONAL PART WHEN IT'S ZERO AND BALLS
Public Const STYLE_STATION_METRIC                  As Integer = 4   'XXX+XXX.XXX

'SETTINGS
Public NORTH_AZIMUTH_MODE                          As Boolean       'TRUE IF YOU USE NORTH AZIMUTH








'************************************************PUBLIC ROUTINES BEGIN HERE***********************************************
Public Function AngleStringToDegree(AngleString As String, ByRef decDegrees As Double) As Boolean
   AngleStringToDegree = False
   Dim origPrec As Long
   Dim degPart As Long
   Dim minPart As Long
   Dim secPart As Double
   Dim isNeg As Boolean
   If IsPlusMinusAngleString(AngleString, origPrec, degPart, minPart, secPart, isNeg) Then
      decDegrees = DmsToDec(degPart, minPart, secPart)
      If isNeg Then
         decDegrees = -decDegrees
      End If
      AngleStringToDegree = True
   Else
'SHOULD NEVER GET HERE, CREATE ERROR IF IT DOES
      Err.Raise ERROR_NUM_537
   End If
End Function

Public Sub DecToDMS(angDecimal As Double, _
                    ByRef degPart As Long, _
                    ByRef minPart As Long, _
                    ByRef secPart As Double)
'CONVERT DECIMAL TO DMS
   Dim az As Double
   az = Abs(angDecimal) 'SHOULD ALWAYS BE POSITIVE
   degPart = Int(az)
   Dim fractionalPart As Double
   fractionalPart = az - degPart
   Dim Minutes As Double
   Minutes = fractionalPart * 60
   minPart = Int(Minutes)
   Dim fractionalMinutes As Double
   fractionalMinutes = Minutes - minPart
   secPart = fractionalMinutes * 60
End Sub



Public Function DegreesToAngleString(ByVal angleInDegrees As Double, _
                                     precision As Long, _
                                     style As Integer) As String
'NEED TO CHECK VALID ANGLE/AZIMUTH FIRST (0 <= ANGLE <360)
'TAKES ANGLE IN DECIMAL DEGREES AND CONVERTS IT TO A STRING
'ANGLES FROM 0 DEGREES TO LESS THAN 360 DEGREES
   Dim degPart As Long
   Dim minPart As Long
   Dim secPart As Double
   DecToDMS angleInDegrees, degPart, minPart, secPart
   DegreesToAngleString = DirString(degPart, minPart, secPart, precision, DIR_TYPE_AZIMUTH, style)
End Function



Public Sub DirectionOnUpdate(ByRef DirectionTextBox As TextBox, ByRef PreviousDirection As String)
   Dim origPrec As Long
   Dim degPart As Long
   Dim minPart As Long
   Dim secPart As Double
   Dim dirType As Integer
   Dim quad As Integer
   If IsDirString(DirectionTextBox.text, origPrec, degPart, minPart, secPart, dirType, quad) Then
       DirectionTextBox.text = DirString(degPart, minPart, secPart, origPrec, dirType, PlotLotEntryAngleStyle, quad)
       PreviousDirection = DirectionTextBox.text
   Else
       DirectionTextBox.text = PreviousDirection
       Beep
   End If
End Sub



Public Function DirString(DegreesPart As Long, _
                          minutesPart As Long, _
                          secondsPart As Double, _
                          precision As Long, _
                          dirType As Integer, _
                          style As Integer, _
                          Optional quadrant As Integer = QUAD_NORTH_EAST) As String
'CREATES DIRECTION STRING

   Dim degPart As Long
   degPart = DegreesPart
   Dim minPart As Long
   minPart = minutesPart
   
'ROUND TO PRECISION
'WORK ON SECONDS
   If precision = 1 Or precision = 2 Then
      Dim secPart As Double
      secPart = 0
      If secondsPart >= 30 Then
         minPart = minPart + 1
      End If
   ElseIf precision <= 0 Then
      secPart = 0
   Else
      If precision = 3 Then
         Dim secPrec As Long
         secPrec = 0
      ElseIf precision > 3 Then
         secPrec = precision - 4
      End If
      secPart = Round(secondsPart, secPrec)
      If secPart >= 60 Then
         secPart = secPart - 60
         minPart = minPart + 1
      End If
   End If

'WORK ON MINUTES
   If precision = 0 Then
      minPart = 0
      If minutesPart >= 30 Then
         degPart = degPart + 1
      End If
   Else
      If minPart >= 60 Then
         degPart = degPart + 1
         minPart = minPart - 60
      End If
   End If

'WORK ON DEGREES
   If dirType = DIR_TYPE_AZIMUTH And degPart >= 360 Then
      degPart = degPart Mod 360
   End If
   
'GENERATE STRING
   Dim workingStyle As Integer
   workingStyle = style
   If (dirType = DIR_TYPE_BEARING) And (style And STYLE_ANGLE_LEAD) Then
      workingStyle = style Or STYLE_ANGLE_DEG_LEAD
   End If
   Dim AngleString As String
   AngleString = DMSString(degPart, minPart, secPart, precision, workingStyle)
   If dirType = DIR_TYPE_BEARING Then
      Select Case quadrant
      Case QUAD_NORTH_EAST
         AngleString = STRING_N & AngleString & STRING_E
      Case QUAD_SOUTH_EAST
         AngleString = STRING_S & AngleString & STRING_E
      Case QUAD_SOUTH_WEST
         AngleString = STRING_S & AngleString & STRING_W
      Case QUAD_NORTH_WEST
         AngleString = STRING_N & AngleString & STRING_W
      End Select
   End If
   DirString = AngleString
End Function



Public Function DirStringToSAz(DirString As String, _
                               ByRef sAzimuth As Double, _
                               ByRef origPrec As Long, _
                               ByRef dirType As Integer, _
                               ByRef quad As Integer) As Boolean
'RETURNS TRUE IF SUCCESSFUL
'CAN USE TO EXTRACT VALUE FROM TEXT BOX
   DirStringToSAz = False
   Dim degPart As Long
   Dim minPart As Long
   Dim secPart As Double
   If IsDirString(DirString, origPrec, degPart, minPart, secPart, dirType, quad) Then
      If dirType = DIR_TYPE_BEARING Then
         sAzimuth = BearingToSAz(degPart, minPart, secPart, quad)
         DirStringToSAz = True
         Exit Function
      End If
      If dirType = DIR_TYPE_AZIMUTH Then
         ReverseForNorthMode degPart
         sAzimuth = DmsToDec(degPart, minPart, secPart)
         DirStringToSAz = True
      End If
   End If
End Function



Public Sub DistanceOnUpdate(ByRef DistanceBox As TextBox, ByRef PreviousDistance As String, allowZero As Boolean)
'PROCESS DISTANCE ENTRIES
   Dim value As Double
   Dim origPrec As Long
   If IsNonnegativeString(DistanceBox.text, _
                          allowZero, _
                          value, _
                          origPrec) Then
      DistanceBox.text = FormatNumber(value, origPrec, vbTrue, vbFalse, vbTrue)
      PreviousDistance = DistanceBox.text
   Else
'REVERT TO PREVIOUSLY ENTERED VALUE
      DistanceBox.text = PreviousDistance
      Beep
   End If
End Sub



Public Function DoubleToEastingString(ByVal theValue As Double, _
                                      precision As Long, _
                                      Optional space As Boolean = True) As String
'CREATES AN EASTING STRING FROM DOUBLE, CHECK VALUE RANGE BEFORE HAND
   DoubleToEastingString = DoubleToAxisString(theValue, precision, STRING_E, STRING_W, space)
End Function



Public Function DoubleToNorthingString(ByVal theValue As Double, _
                                       precision As Long, _
                                       Optional space As Boolean = True) As String
'CREATES AN NORTHING STRING FROM DOUBLE, CHECK VALUE RANGE BEFORE HAND
   DoubleToNorthingString = DoubleToAxisString(theValue, precision, STRING_N, STRING_S, space)
End Function



Public Function DmsToDec(degPart As Long, minPart As Long, secPart As Double) As Double
'CONVERT DMS TO DECIMAL FORMAT
'ALWAYS POSITIVE
   Dim az As Double
   az = degPart
   Dim minutesPart As Double
   minutesPart = minPart
   az = az + minutesPart / 60#
   az = az + secPart / 3600#
   DmsToDec = az
End Function



Public Function DmsToDecSigned(degPart As Long, minPart As Long, secPart As Double, isNeg As Boolean) As Double
'CONVERT DMS TO DECIMAL FORMAT
   DmsToDecSigned = DmsToDec(degPart, minPart, secPart)
   If isNeg Then
      DmsToDecSigned = -DmsToDecSigned
   End If
End Function



Public Sub EnabledColor(theTextbox As TextBox)
   If theTextbox.enabled Then
      theTextbox.BackColor = &H80000005  'WINDOW BACKGROUND
   Else
      theTextbox.BackColor = &H8000000F  'BUTTON FACE
   End If
End Sub



Public Function halfDelta(Entry As String, _
                          ByRef DegreesPart As Long, _
                          ByRef minutesPart As Long, _
                          ByRef secondsPart As Double, _
                          ByRef precision As Long, _
                          ByRef deltaOver2 As Double) As Boolean
'TAKES THE DELTA STRING AND RETURNS THE HALF DELTA IN DMS AND DOUBLE
'ALSO SUGGESTS A PRECISION TO USE.
'RETURNS TRUE IF SUCCESSFUL.
   halfDelta = False
   Dim origPrec As Long
   Dim degPart As Long
   Dim minPart As Long
   Dim secPart As Double
   
   If IsDeltaString(Entry, origPrec, degPart, minPart, secPart) Then
      Dim delta As Double
      delta = DmsToDec(degPart, minPart, secPart)
      deltaOver2 = delta / 2
      DecToDMS deltaOver2, DegreesPart, minutesPart, secondsPart
      precision = origPrec
      If origPrec >= 4 Then
         Dim prePlusOne As Long
         prePlusOne = origPrec + 1
         If Round(secondsPart, origPrec - 4) <> Round(secondsPart, prePlusOne - 4) Then
            precision = MinLong(prePlusOne, MAX_PRECISION_OG)
         End If
      ElseIf origPrec = 3 Then
         precision = 4
         If Round(secondsPart, 0) <> Round(secondsPart, 1) Then
            precision = 5
         End If
      ElseIf origPrec = 1 Or origPrec = 2 Then
         precision = 2
         If secondsPart >= 1 Then
            precision = 4
         End If
      ElseIf origPrec = 0 Then
         If minutesPart > 0 Then
            precision = 2
         End If
      End If
      halfDelta = True
   End If
End Function



Public Function IncPointName(ByVal pointName As String) As String
'TAKES VALID POINT NAME AND INCREMENTS POINT NAME
   Dim prefixStr As String
   Dim numStr As String
   If FoundRightMostNum(pointName, prefixStr, numStr) Then
'NUMBER FOUND, INCREMENT NUMBER. GO BACK TO 1 IF NO FIT MAX SIZE
      Dim pointNum As Long
      pointNum = CLng(numStr) + 1
      If pointNum > MAX_POINT_NUMBER Then
         pointNum = 1
      End If
      Dim NewNumStr As String
      NewNumStr = FormatNumber(pointNum, 0, vbFalse, vbFalse, vbFalse)
'CHECK FOR LEADING ZEROS
      LeadingZero numStr, NewNumStr
'CHECK THAT NEW STRING IS NOT TOO LONG
      If Len(prefixStr) + Len(NewNumStr) > MAX_LEN_POINT_NAME Then
'SHORTEN PREFIX BY ONE
         prefixStr = Left(prefixStr, Len(prefixStr) - 1)
      End If
'RETURN NEW POINT NAME
      IncPointName = prefixStr & NewNumStr
   Else
'NO NUMBER FOUND, INCREMENT LAST CHARACTER IF NOT SPECIAL
      Dim charStr As String
      charStr = right(pointName, 1)
'CHECK IF IT'S A SPECIAL CHAR
      If IsSpecialChar(charStr) Then
'CHECK IF IT'S TOO LONG
         If Len(pointName) < MAX_LEN_POINT_NAME Then
'SHORT ENOUGH, SO APPEND 1 TO IT
            IncPointName = pointName & "1"
         Else
'TOO LONG THEN RESTART AT 1
            IncPointName = "1"
         End If
      Else
'ENDS IN A LETTER
         IncPointName = IncLetter(pointName, charStr)
      End If
   End If
End Function



Public Function IsDeltaString(Entry As String, _
                              ByRef origPrec As Long, _
                              ByRef degPart As Long, _
                              ByRef minPart As Long, _
                              ByRef secPart As Double) As Boolean
'CHECK IF STRING IS A VALID DELTA STRING, RETURNS VALUES IF IT IS.
'CAN USE TO EXTRACT VALUE FROM TEXT BOX
'RETURNS TRUE IF OK

'INITIALIZE FLAG
   IsDeltaString = False

'MAKE TRIMMED COPY
   Dim trimEntry As String
   trimEntry = Trim(Entry)

'CHECK IF IT'S AN ANGLE
   If IsDmsString(trimEntry, origPrec, degPart, minPart, secPart, 360, True) Then
      If origPrec > MAX_PRECISION_OG Then
         Exit Function
      End If
      IsDeltaString = True
   End If
End Function



Public Function IsDirString(Entry As String, _
                            ByRef origPrec As Long, _
                            ByRef degPart As Long, _
                            ByRef minPart As Long, _
                            ByRef secPart As Double, _
                            ByRef dirType As Integer, _
                            ByRef quad As Integer) As Boolean
'CHECK IF STRING IS A VALID DIRECTION STRING, RETURNS VALUES IF IT IS.
'CAN USE TO EXTRACT VALUE FROM TEXT BOX
'RETURNS TRUE IF OK

'INITIALIZE FLAG
   IsDirString = False

'CHECK IF IT'S AN AZIMUTH STRING
  If IsDeltaString(Entry, origPrec, degPart, minPart, secPart) Then
     dirType = DIR_TYPE_AZIMUTH
     IsDirString = True
     Exit Function
  End If

'MAKE TRIMMED COPY
   Dim trimEntry As String
   trimEntry = Trim(Entry)
   
'CHECK IF IT'S LONG ENOUGH TO BE A BEARING STRING
  Dim entryLen As Long
  entryLen = Len(trimEntry)
  If entryLen < 3 Then
     Exit Function
  End If

'GET QUADRANT PART
   trimEntry = UCase(trimEntry)
   Dim yAxis As String
   yAxis = Mid(trimEntry, 1, 1)
   Dim xAxis As String
   xAxis = Mid(trimEntry, entryLen, 1)
   If (yAxis = STRING_N Or yAxis = STRING_S) Then
      If Not (xAxis = STRING_E Or xAxis = STRING_W) Then
         Exit Function
      End If
   ElseIf (yAxis = STRING_PLUS Or yAxis = STRING_MINUS) Then
      If Not (xAxis = STRING_PLUS Or xAxis = STRING_MINUS) Then
         Exit Function
      End If
   Else
      Exit Function
   End If

'GET ANGLE PART
   Dim anglePart As String
   anglePart = Mid(trimEntry, 2, entryLen - 2)
   If IsDmsString(anglePart, origPrec, degPart, minPart, secPart, 90, False) Then
      dirType = DIR_TYPE_BEARING
      If yAxis = STRING_N Or yAxis = STRING_PLUS Then
         quad = NORTH
      Else
         quad = SOUTH
      End If
      If xAxis = STRING_E Or xAxis = STRING_PLUS Then
         quad = quad + EAST
      Else
         quad = quad + WEST
      End If
      If origPrec > MAX_PRECISION_OG Then
         Exit Function
      End If
      IsDirString = True
   End If
End Function



Public Function IsEastingString(theString As String, _
                                ByRef theScaler As Double, _
                                ByRef origPrec As Long) As Boolean
'RETURNS TRUE IF GOOD
'CAN USE TO EXTRACT VALUE FROM TEXT BOX
   IsEastingString = IsAxisScalerString(theString, STRING_E, STRING_W, theScaler, origPrec)
End Function



Public Function IsElevationString(Entry As String, _
                                  ByRef elevation As Double, _
                                  ByRef origPrec As Long) As Boolean
'CHECKS IF VALID ELEVATION STRING
   IsElevationString = False
   If Len(Entry) > MAX_LEN_ELEV_STRING Then
      Exit Function
   End If
   If IsNumeric(Entry) Then
      Dim value As Double
      value = CDbl(Entry)
      If Abs(value) > MAX_ELEVATION Then
         Exit Function
      End If
      elevation = value
      origPrec = StrPrec(Entry)
      IsElevationString = True
   End If
End Function




Public Function IsNonnegativeString(Entry As String, _
                                    allowZero As Boolean, _
                                    ByRef value As Double, _
                                    ByRef origPrec As Long) As Boolean
   IsNonnegativeString = False
   If IsNumeric(Entry) Then
      Dim Val As Double
      Val = CDbl(Entry)
      If (Not allowZero) And Val = 0 Then
         Exit Function
      End If
      If Val < 0 Then
         Exit Function
      End If
      If Len(Entry) > MAX_LEN_NONEG_STRING Then
         Exit Function
      End If
      value = Val
      origPrec = StrPrec(Entry)
      IsNonnegativeString = True
   End If
End Function



Public Function IsNorthingString(theString As String, _
                                 ByRef theScaler As Double, _
                                 ByRef origPrec As Long) As Boolean
'RETURNS TRUE IF GOOD
'CAN USE TO EXTRACT VALUE FROM TEXT BOX
   IsNorthingString = IsAxisScalerString(theString, STRING_N, STRING_S, theScaler, origPrec)
End Function



Public Function IsPlusMinusAngleString(Entry As String, _
                                       ByRef origPrec As Long, _
                                       ByRef degPart As Long, _
                                       ByRef minPart As Long, _
                                       ByRef secPart As Double, _
                                       ByRef isNeg As Boolean) As Boolean
'RETURNS TRUE IF GOOD
'CAN USE TO EXTRACT VALUE FROM TEXT BOX

'MAKE WORKING COPY
   Dim Entered As String
   Entered = Trim(Entry)
      
'FLAG NEGATIVE SIGN
   Dim isNegative  As Boolean
   isNegative = False

'ENTERED AS A NUMBER
   If IsNumeric(Entered) Then
      Dim value As Double
      value = CDbl(Entered)
'FLAG IF IT'S NEGATIVE
      If value < 0 Then
         isNegative = True
'REMOVE NEATIVE SIGN IF IT IS
         Entered = Replace(Entered, STRING_MINUS, "")
      End If
'CHECK IF VALID ANGLE STRING
      If IsDmsString(Entered, origPrec, degPart, minPart, secPart, 360, True) Then
         isNeg = isNegative
         IsPlusMinusAngleString = True
      End If
      Exit Function
   End If
   
'ENTERED AS FORMATTED STRING
'MAKE SURE STRING IS LONG ENOUGH
   Dim length As Long
   length = Len(Entered)
   If length < 2 Then
      Exit Function
   End If
'CHECK FOR NEGATIVE SIGN
   If Mid(Entered, 1, 1) = STRING_MINUS Then
      isNegative = True
      Entered = Mid(Entered, 2, length)
   End If
'CHECK IF VALID STRING
   If IsDmsString(Entered, origPrec, degPart, minPart, secPart, 360, True) Then
      isNeg = isNegative
      IsPlusMinusAngleString = True
   End If
End Function



Public Function IsPointnameString(ByVal nameString As String, ByRef formmattedString As String) As Boolean
'*******FOR INCREMENTING POINT NAME FIELDS*********
'RETURNS TRUE IF IT IS A VALID POINT NAME
'A POINT NAME MUST BEGIN WITH A LETTER OR A NUMBER
'NOT CASE SENSITIVE
'THESE SPECIAL CHARACTERS ARE ALLOWED -_.
'SPACES ARE ALLOWED, BUT LEADING AND TRAINING SPACES ARE TRIMMED
'INTEGER NAMES AND POSTFIXES MUST BE 1 THROUGH 999999
   IsPointnameString = False
   Dim trimmedNameString As String
   trimmedNameString = Trim(nameString)
'CHECK STRING LENGTH
   If Not IsPNameLenOK(trimmedNameString) Then
      Exit Function
   End If
'CHECK IF IT BEGINS WITH A LETTER OR A NUMBER
   Dim firstChar As String
   firstChar = Left(trimmedNameString, 1)
   If Not (CharIsALetter(firstChar) Or CharIsDigit(firstChar)) Then
      Exit Function
   End If
'SEARCH FOR INVALID CHARACTERS
   Dim index As Long
   For index = 1 To Len(trimmedNameString)
      If Not IsValidChar(Mid(trimmedNameString, index, 1)) Then
         Exit Function
      End If
   Next
'CHECK IF IT'S A POINT NUMBER ONLY
   If IsNumeric(trimmedNameString) Then
      Dim pointNumber As Double
      pointNumber = CDbl(trimmedNameString)
      If pointNumber > MAX_POINT_NUMBER Or pointNumber <= 0 Then
         Exit Function
      End If
      formmattedString = FormatNumber(pointNumber, 0, vbFalse, vbFalse, vbFalse)
      IsPointnameString = True
      Exit Function
   End If
'IF NOT A POINT NUMBER, FIRST CHARACTER CANNOT BE A NUMBER
   If CharIsDigit(Mid(trimmedNameString, 1, 1)) Then
      Exit Function
   End If
'CHECK IF GOES BEYOND POINT NUMBER
   Dim prefix As String
   Dim numStr As String
   If FoundRightMostNum(trimmedNameString, prefix, numStr) Then
      pointNumber = CDbl(numStr)
      If pointNumber > MAX_POINT_NUMBER Then
         Exit Function
      End If
   End If
   formmattedString = trimmedNameString
   IsPointnameString = True
End Function



Public Function IsStationString(ByVal theString As String, _
                                ByRef TheStation As Double, _
                                ByRef origPrec As Long, _
                                style As Integer) As Boolean
'RETURNS TRUE IF GOOD
'CAN USE TO EXTRACT VALUE FROM TEXT BOX
   IsStationString = False
   If IsNumeric(theString) Then
      origPrec = StrPrec(theString)
      Dim sta As Double
      sta = CDbl(theString)
      If Abs(sta) > MAX_STATION Then
         Exit Function
      End If
      TheStation = sta
      IsStationString = True
   End If
   If IsStaStr(theString, TheStation, origPrec, style) Then
      IsStationString = True
      Exit Function
   End If
End Function



Public Sub LoadDirEntry(theTextbox As TextBox, Section As String, Key As String)
'LOADS SAVED DIRECTION INTO TEXT BOX IF ANY
   theTextbox.text = GetSetting(APP_NAME, Section, Key, DegreesToAngleString(1.5, 4, STYLE_ANGLE_LEAD))
End Sub



Public Sub LoadEastingEntry(theTextbox As TextBox, _
                            Section As String, _
                            Key As String, _
                            Optional precision As Long = 4, _
                            Optional space As Boolean = True)
'LOADS SAVED EASTING INTO TEXT BOX IF ANY
   theTextbox.text = GetSetting(APP_NAME, Section, Key, DoubleToEastingString(100#, precision, space))
End Sub



Public Sub LoadElevationEntry(theTextbox As TextBox, _
                              Section As String, _
                              Key As String, _
                              Optional precision As Long = 2)
'LOADS SAVED ELEVATION INTO TEXT BOX IF ANY
   theTextbox.text = GetSetting(APP_NAME, Section, Key, FormatNumber(100#, precision, vbTrue, vbFalse, vbTrue))
End Sub



Public Sub LoadNonnegativeEntry(theTextbox As TextBox, _
                                Section As String, _
                                Key As String, _
                                defaultVal As Double, _
                                Optional precision As Long = 2)
'LOADS SAVED NON-NEGATIVE ENTRY INTO TEXT BOX IF ANY
   theTextbox.text = GetSetting(APP_NAME, Section, Key, FormatNumber(Abs(defaultVal), precision, vbTrue, vbFalse, vbTrue))
End Sub



Public Sub LoadNorthingEntry(theTextbox As TextBox, _
                             Section As String, _
                             Key As String, _
                             Optional precision As Long = 4, _
                             Optional space As Boolean = True)
'LOADS SAVED NORTHING INTO TEXT BOX IF ANY
   theTextbox.text = GetSetting(APP_NAME, Section, Key, DoubleToNorthingString(100#, precision, space))
End Sub



Public Sub LoadPlotScaleEntry(theTextbox As TextBox, _
                              Section As String, _
                              Key As String, _
                              Optional precision As Long = 2)
'LOADS SAVED PLOTSCALE INTO TEXT BOX IF ANY
   theTextbox.text = GetSetting(APP_NAME, Section, Key, SETTING_DEFAULT_PLOT_SCALE)
End Sub



Public Sub LoadPlusMinusEntry(theTextbox As TextBox, Section As String, Key As String, style As Integer, precision As Long)
'LOADS SAVED PLUS OR MINUS ANGLE (-360 < ANGLE < 360) INTO TEXT BOX IF ANY
   theTextbox.text = GetSetting(APP_NAME, Section, Key, DegreesToAngleString(0, precision, style))
End Sub


Public Sub LoadPointDescEntry(ByRef pointDescBox As TextBox, _
                              ByVal Section As String, _
                              ByVal Key As String)
'LOADS SAVED POINT DESCRIPTION INTO TEXT BOX IF ANY
   pointDescBox.text = GetSetting(APP_NAME, Section, Key, "")
End Sub



Public Sub LoadPointName(ByRef pointNameBox As TextBox, _
                         ByVal Section As String, _
                         ByVal Key As String)
'LOADS SAVED POINTNAME INTO TEXT BOX IF ANY
   pointNameBox.text = GetSetting(APP_NAME, Section, Key, "Trav1")
End Sub



Public Sub LoadRadiusEntry(theTextbox As TextBox, _
                           Section As String, _
                           Key As String, _
                           Optional precision As Long = 2)
'LOADS SAVED RADIUS INTO TEXT BOX IF ANY
   theTextbox.text = GetSetting(APP_NAME, Section, Key, FormatNumber(1#, precision, vbTrue, vbFalse, vbTrue))
End Sub



Public Sub LoadStaEntry(theTextbox As TextBox, _
                        Section As String, _
                        Key As String, _
                        style As Integer, _
                        Optional precision As Long = 2)
'LOADS SAVED STATION INTO TEXT BOX IF ANY
   theTextbox.text = GetSetting(APP_NAME, Section, Key, StationToString(100#, precision, style))
End Sub



Public Sub MakeSure360(angleDegrees As Double)
'MAKE SURE 360 > ANGLE >= 0

'CHECK RANGE
   If angleDegrees < 360 And angleDegrees >= 0 Then
      Exit Sub
   End If

'MAKE WORKING COPY
   Dim Angle As Double
   Angle = angleDegrees
   
'IF NEGATIVE, MAKE IT POSITIVE
   If angleDegrees < 0 Then
      Angle = Abs(Angle)
   End If

'MAKE SURE NOT 360 DEGREES OR MORE
   Dim wholePart As Double
   wholePart = Int(Angle)
   Dim fractionPart As Double
   fractionPart = Angle - wholePart
   wholePart = wholePart Mod 360
   Angle = wholePart + fractionPart
   
'CONVERT LEFT HAND CURVE TO RIGHT HAND CURVE
   If angleDegrees < 0 Then
      Angle = 360# - Angle
   End If
   
'RETURN VALUE
   angleDegrees = Angle
End Sub



Public Function MaxLong(a As Long, b As Long) As Long
   If a >= b Then
       MaxLong = a
   Else
       MaxLong = b
   End If
End Function



Public Function MinLong(ByVal a As Long, ByVal b As Long) As Long
'MINIMUM FUNCTION FOR LONG DATA TYPE, RETURNS SMALLER VALUE
   If a <= b Then
      MinLong = a
   Else
      MinLong = b
   End If
End Function



Public Sub Plus180(theTextbox As TextBox)
'MODIFIES ORIGINAL STRING, NEED TO REEVALUATE ENTRY OF TEXT BOX
'READS DIRECTION STRING FROM TEXT BOX, REVERSES IT'S DIRECTION
   Dim entryString As String
   entryString = theTextbox.text
   If ReverseDirText(entryString) Then
      theTextbox.text = entryString
   End If
End Sub



Public Function ReverseDirText(ByRef Entry As String) As Boolean
'RETURNS TRUE IF SUCCESSFUL
'CHANGES DIRECTION STRING TO REVERSE DIRECTION
   ReverseDirText = False
   Dim origPrec As Long
   Dim degPart As Long
   Dim minPart As Long
   Dim secPart As Double
   Dim dirType As Integer
   Dim quad As Integer
   If IsDirString(Entry, origPrec, degPart, minPart, secPart, dirType, quad) Then
      If dirType = DIR_TYPE_AZIMUTH Then
         degPart = (degPart + 180) Mod 360
         Entry = DirString(degPart, minPart, secPart, origPrec, dirType, 0, quad)
         ReverseDirText = True
      End If
      
      If dirType = DIR_TYPE_BEARING Then
         Dim newQuad As Integer
         Select Case quad
            Case QUAD_NORTH_EAST
               newQuad = QUAD_SOUTH_WEST
            Case QUAD_SOUTH_EAST
               newQuad = QUAD_NORTH_WEST
            Case QUAD_SOUTH_WEST
               newQuad = QUAD_NORTH_EAST
            Case QUAD_NORTH_WEST
               newQuad = QUAD_SOUTH_EAST
            Case Else
               Exit Function
         End Select
         Entry = DirString(degPart, minPart, secPart, origPrec, dirType, 0, newQuad)
         ReverseDirText = True
      End If
   End If
End Function



Public Sub SaveCheckBoxSetting(theCheckBox As CheckBox, Section As String, Key As String)
   If theCheckBox.value = True Then
      SaveSetting APP_NAME, Section, Key, OPTION_TRUE
   Else
      SaveSetting APP_NAME, Section, Key, OPTION_FALSE
   End If
End Sub



Public Sub SaveDeltaEntry(theTextbox As TextBox, _
                          Section As String, _
                          Key As String, _
                          style As Integer, _
                          Optional precision As Long = -1)
'DO NOT ENTER PRECISION TO USE IMPLIED PRECISION
'SAVES DELTA ENTRY FROM TEXT BOX
   Dim origPrec As Long
   Dim degPart As Long
   Dim minPart As Long
   Dim secPart As Double
   If IsDeltaString(theTextbox.text, origPrec, degPart, minPart, secPart) Then
      If precision <> -1 Then
         origPrec = precision
      End If
      theTextbox.text = DirString(degPart, minPart, secPart, origPrec, DIR_TYPE_AZIMUTH, style)
      SaveSetting APP_NAME, Section, Key, theTextbox.text
   Else
      LoadDirEntry theTextbox, Section, Key
      Beep
   End If
End Sub



Public Sub SavePointDescEntry(theTextbox As TextBox, Section As String, Key As String)
'SAVES POINT DESCRIPTION ENTRY FROM TEXT BOX
   If Len(theTextbox.text) > MAX_LEN_POINT_DESC Then
      theTextbox.text = Mid(theTextbox.text, 1, MAX_LEN_POINT_DESC)
   End If
   SaveSetting APP_NAME, Section, Key, theTextbox.text
End Sub



Public Sub SaveDirEntry(theTextbox As TextBox, _
                        Section As String, _
                        Key As String, _
                        style As Integer, _
                        Optional precision As Long = -1)
'DO NOT ENTER PRECISION TO USE IMPLIED PRECISION
'SAVES DIRECTION ENTRY FROM TEXT BOX
   Dim origPrec As Long
   Dim degPart As Long
   Dim minPart As Long
   Dim secPart As Double
   Dim dirType As Integer
   Dim quad As Integer
   If IsDirString(theTextbox.text, origPrec, degPart, minPart, secPart, dirType, quad) Then
      If precision <> -1 Then
         origPrec = precision
      End If
      theTextbox.text = DirString(degPart, minPart, secPart, origPrec, dirType, style, quad)
      SaveSetting APP_NAME, Section, Key, theTextbox.text
   Else
      LoadDirEntry theTextbox, Section, Key
      Beep
   End If
End Sub



Public Sub SaveEastingEntry(theTextbox As TextBox, _
                            Section As String, _
                            Key As String, _
                            precision As Long, _
                            Optional space As Boolean = True)
'SAVES EASTING ENTRY FROM TEXT BOX
   Dim value As Double
   Dim origPrec As Long
   If IsEastingString(theTextbox.text, value, origPrec) Then
      theTextbox.text = DoubleToEastingString(value, precision)
      SaveSetting APP_NAME, Section, Key, theTextbox.text
   Else
      LoadEastingEntry theTextbox, Section, Key, precision, space
      Beep
   End If
End Sub



Public Sub SaveElevationEntry(theTextbox As TextBox, _
                              Section As String, _
                              Key As String, _
                              Optional precision As Long = -1)
'DO NOT ENTER PRECISION TO USE IMPLIED PRECISION
'SAVES ELEVATION ENTRY FROM TEXT BOX
   Dim value As Double
   Dim origPrec As Long
   If IsElevationString(theTextbox.text, value, origPrec) Then
      If precision = -1 Then
         Dim newPrec As Long
         newPrec = MinLong(origPrec, MAX_PRECISION_ELEV)
      Else
         newPrec = precision
      End If
      theTextbox.text = FormatNumber(value, newPrec, vbTrue, vbFalse, vbTrue)
      SaveSetting APP_NAME, Section, Key, theTextbox.text
   Else
      If precision = -1 Then
         newPrec = 2
      Else
         newPrec = precision
      End If
      LoadElevationEntry theTextbox, Section, Key, newPrec
      Beep
   End If
End Sub



Public Sub SaveNonnegativeEntry(theTextbox As TextBox, _
                                Section As String, _
                                Key As String, _
                                maxVal As Double, _
                                maxPrec As Long, _
                                allowZero As Boolean, _
                                defaultVal As Double, _
                                Optional precision As Long = -1)
'DO NOT ENTER PRECISION TO USE IMPLIED PRECISION
'SAVES NON-NEGATIVE ENTRY FROM TEXTBOX
   Dim value As Double
   Dim origPrec As Long
   If IsNonnegativeString(theTextbox.text, allowZero, value, origPrec) Then
      If precision = -1 Then
         Dim newPrec As Long
         newPrec = MinLong(origPrec, maxPrec)
      Else
         newPrec = precision
      End If
      theTextbox.text = FormatNumber(value, newPrec, vbTrue, vbFalse, vbTrue)
      Dim textValue As Double
      textValue = CDbl(theTextbox.text)
      If (Not allowZero) And (textValue = 0) Then
         LoadNonnegativeEntry theTextbox, Section, Key, defaultVal
         Beep
      End If
      If textValue < 0 Or textValue > maxVal Then
         LoadNonnegativeEntry theTextbox, Section, Key, defaultVal
         Beep
         Exit Sub
      End If
      SaveSetting APP_NAME, Section, Key, theTextbox.text
   Else
      LoadNonnegativeEntry theTextbox, Section, Key, defaultVal
      Beep
   End If
End Sub



Public Sub SaveNorthingEntry(theTextbox As TextBox, _
                             Section As String, _
                             Key As String, _
                             precision As Long, _
                             Optional space As Boolean = True)
'SAVES NORTHING ENTRY FROM TEXT BOX
   Dim value As Double
   Dim origPrec As Long
   If IsNorthingString(theTextbox.text, value, origPrec) Then
      theTextbox.text = DoubleToNorthingString(value, precision)
      SaveSetting APP_NAME, Section, Key, theTextbox.text
   Else
      LoadNorthingEntry theTextbox, Section, Key, precision, space
      Beep
   End If
End Sub



Public Sub SaveOffsetEntry(theTextbox As TextBox, _
                           OptionLeft As optionButton, _
                           OptionRight As optionButton, _
                           Section As String, _
                           Key As String, _
                           maxVal As Double, _
                           defaultVal As Double, _
                           Optional precision As Long = -1)
'DO NOT ENTER PRECISION TO USE IMPLIED PRECISION
'SAVES OFFSET ENTRY FROM TEXT BOX, SETS OPTION BUTTONS IF SIGN IS ENCOUNTERED
   Dim value As Double
   Dim origPrec As Long
   Dim optLeft As Boolean
   Dim optRight As Boolean
   If IsOffsetString(theTextbox.text, maxVal, value, origPrec, optLeft, optRight) Then
      If precision = -1 Then
         Dim newPrec As Long
         newPrec = MinLong(origPrec, MAX_PRECISION_OFFSET)
      Else
         newPrec = precision
      End If
      theTextbox.text = FormatNumber(Abs(value), newPrec, vbTrue, vbFalse, vbTrue)
      SaveSetting APP_NAME, Section, Key, theTextbox.text
      If optLeft Then
         OptionLeft.value = True
      End If
      If optRight Then
         OptionRight.value = True
      End If
   Else
      LoadNonnegativeEntry theTextbox, Section, Key, defaultVal
      Beep
   End If
End Sub



Public Sub SavePlusMinusAngleEntry(theTextbox As TextBox, _
                                   Section As String, _
                                   Key As String, _
                                   style As Integer, _
                                   maxAngleDegrees As Double, _
                                   Optional precision As Long = -1)
'DO NOT ENTER PRECISION TO USE IMPLIED PRECISION
'SAVES PLUS OR MINUS ANGLE ENTRY FROM TEXT BOX

'ENTERED AS NUMBER
   Dim origPrec As Long
   Dim degPart As Long
   Dim minPart As Long
   Dim secPart As Double
   Dim isNeg As Boolean
   If IsPlusMinusAngleString(theTextbox.text, origPrec, degPart, minPart, secPart, isNeg) Then
      Dim value As Double
      value = DmsToDec(degPart, minPart, secPart)
      If value > maxAngleDegrees Then
'OUT OF RANGE
         LoadPlusMinusEntry theTextbox, Section, Key, style, 4
         Beep
      Else
         Dim newPrec As Long
         If precision = -1 Then
            newPrec = MinLong(origPrec, MAX_PRECISION_OG)
         Else
            newPrec = precision
         End If
'ADD NEGATIVE SIGN IF NEEDED
         Dim formattedEntry As String
         formattedEntry = DirString(degPart, minPart, secPart, newPrec, DIR_TYPE_AZIMUTH, style)
         If isNeg Then
'CHECK TO MAKE SURE ROUNDING DOESN'T MAKE IT ZERO
            If IsDmsString(formattedEntry, origPrec, degPart, minPart, secPart, 360, True) Then
                If degPart <> 0 Or minPart <> 0 Or secPart <> 0# Then
                   formattedEntry = STRING_MINUS & formattedEntry
                End If
            Else
'SHOULD NEVER REACH HERE
               LoadPlusMinusEntry theTextbox, Section, Key, style, 4
               Beep
            End If
         End If
'SAVE FORMATTED ENTRY
         theTextbox.text = formattedEntry
         SaveSetting APP_NAME, Section, Key, theTextbox.text
      End If
   Else
'INVALID STRING
      LoadPlusMinusEntry theTextbox, Section, Key, style, 4
      Beep
   End If
End Sub



Public Sub SavePointNameEntry(ByRef pointNameBox As TextBox, _
                              ByVal Section As String, _
                              ByVal Key As String)
'SAVES POINT NAME ENTRY FROM TEXT BOX
   Dim formattedString As String
   If IsPointnameString(pointNameBox.text, formattedString) Then
      pointNameBox.text = formattedString
      SaveSetting APP_NAME, Section, Key, pointNameBox.text
   Else
      LoadPointName pointNameBox, Section, Key
      Beep
   End If
End Sub



Public Sub SaveStationEntry(theTextbox As TextBox, _
                            Section As String, _
                            Key As String, _
                            style As Integer, _
                            Optional precision As Long = -1)
'DO NOT ENTER PRECISION TO USE IMPLIED PRECISION
'SAVES STATION ENTRY FROM TEXT BOX

   Dim prec As Long
   prec = precision
   Dim station As Double
   Dim origPrec As Long
   If IsStationString(theTextbox.text, station, origPrec, style) Then
      If precision = -1 Then
         prec = MinLong(origPrec, MAX_PRECISION_STATION)
      End If
      theTextbox.text = StationToString(station, prec, style)
      SaveSetting APP_NAME, Section, Key, theTextbox.text
   Else
      If precision = -1 Then
         prec = 2
      End If
      LoadStaEntry theTextbox, Section, Key, style, prec
      Beep
   End If
End Sub



Public Sub SelectAllText(TheBox As TextBox)
'SELECTS ALL THE TEXT IN TEXT BOX
   TheBox.SelStart = 0
   TheBox.SelLength = Len(TheBox.text)
End Sub


Public Function SAzToAzimuthStr(sAzInDegrees As Double, _
                                precision As Long, _
                                style As Integer) As String
'CONVERTS SOUTH AZIMUTH IN DEGREES TO A FORMATTED AZIMUTH STRING,
'IT ACCOUNTS FOR NORTH AZIMUTH MODE
   Dim degPart As Long
   Dim minPart As Long
   Dim secPart As Double
   DecToDMS sAzInDegrees, degPart, minPart, secPart
   ReverseForNorthMode degPart
   SAzToAzimuthStr = DirString(degPart, minPart, secPart, precision, DIR_TYPE_AZIMUTH, style)
End Function



Public Function SAzToBearingStr(ByVal sAzInDegrees As Double, _
                                precision As Long, _
                                style As Integer) As String
'360 > SOUTH AZIMTH >= 0
'CONVERTS SOUTH AZIMUTH IN DEGREES TO A FORMATTED BEARING STRING,
'IT ACCOUNTS FOR NORTH AZIMUTH MODE
   
'MAKE SURE VALUES ARE IN RANGE
   MakeSure360 sAzInDegrees

'DETERMINE QUADRANT
   Dim quad As Integer
   If sAzInDegrees <= 90# Then
      quad = QUAD_SOUTH_WEST
      Dim bearingAngle As Double
      bearingAngle = sAzInDegrees
   ElseIf sAzInDegrees < 180# Then
      quad = QUAD_NORTH_WEST
      bearingAngle = 180# - sAzInDegrees
   ElseIf sAzInDegrees <= 270# Then
      quad = QUAD_NORTH_EAST
      bearingAngle = sAzInDegrees - 180#
   Else
      quad = QUAD_SOUTH_EAST
      bearingAngle = 360# - sAzInDegrees
   End If

'CONVERT TO DMS FORMAT
   Dim degPart As Long
   Dim minPart As Long
   Dim secPart As Double
   DecToDMS bearingAngle, degPart, minPart, secPart

'GENERATE THE STRING
   SAzToBearingStr = DirString(degPart, minPart, secPart, precision, DIR_TYPE_BEARING, style, quad)
End Function



Public Function SAzToDirectionStr(sAzInDegrees As Double, _
                                  precision As Long, _
                                  dirType As Integer, _
                                  style As Integer) As String
'CONVERTS SOUTH AZIMUTH IN DEGREES TO A FORMATTED BEARING OR AZIMUTH STRING,
'IT ACCOUNTS FOR NORTH AZIMUTH MODE
   If dirType = DIR_TYPE_AZIMUTH Then
      SAzToDirectionStr = SAzToAzimuthStr(sAzInDegrees, precision, style)
   Else
      SAzToDirectionStr = SAzToBearingStr(sAzInDegrees, precision, style)
   End If
End Function



Public Function StationToString(ByVal station As Double, _
                                precision As Long, _
                                style As Integer) As String
'TAKES A STATION, INCLUDING FEET, AND MAKES IT INTO A STRING

'CHECK IF TOO BIG
   If Abs(station) > MAX_STATION Then
      StationToString = "Out of Range"
      Exit Function
   End If
'ROUND TO PRECISION
   Dim temp As String
   station = Round(station, precision)
'FLAG IF IT'S NEGATIVE
   If station < 0 Then
      Dim isNeg As Boolean
      isNeg = True
   Else
      isNeg = False
   End If
'WORK WITH THE POSITIVE VALUE
   station = Abs(station)
   
'METRIC STYLE, INCLUDED BECAUSE WE ONCE TRIED TO CONVERT TO METRIC
   If (style And STYLE_STATION_METRIC) Then
      Dim stationPart As Long
      stationPart = Int(station / 1000#)
      Dim meterPart As Double
      meterPart = station - stationPart * 1000#
      temp = FormatNumber(stationPart, 0, vbTrue, vbFalse, vbFalse) & STRING_PLUS
      If meterPart < 100# Then
         temp = temp & STRING_ZERO
      End If
      If meterPart < 10# Then
         temp = temp & STRING_ZERO
      End If
      Dim rightSidePart As Double
      rightSidePart = meterPart
      
'ENGLISH STYLE
   Else
      stationPart = Int(station / 100)
      Dim feetPart As Double
      feetPart = station - stationPart * 100
      temp = FormatNumber(stationPart, 0, vbTrue, vbFalse, vbFalse) & STRING_PLUS
      If feetPart < 10 Then
         temp = temp & STRING_ZERO
      End If
      rightSidePart = feetPart
   End If

'ADD THE RIGHT SIDE OF THE PLUS SIGN
   Dim rightSideString As String
   rightSideString = FormatNumber(rightSidePart, precision, vbTrue, vbFalse, vbFalse)
   If (style And STYLE_STATION_NO_0_FRAC) Then
      Dim rightSideIntegerPart As Double
      rightSideIntegerPart = Int(rightSidePart)
      If CDbl(rightSideString) = rightSideIntegerPart Then
         rightSideString = FormatNumber(rightSidePart, 0, vbTrue, vbFalse, vbFalse)
      End If
   End If
   If (style And STYLE_STATION_NO_BALLS_0_FRAC) Then
      If rightSidePart = 0 Then
         rightSideString = STRING_ZERO
      End If
   End If
   temp = temp & rightSideString

'ADD NEGATIVE SIGN IF NEEDED
   If isNeg Then
      temp = STRING_MINUS & temp
   End If

'RETURN STRING
   StationToString = temp
End Function



Public Function StrPrec(Entry As String) As Long
'FINDS PRECISION OF NUMBER STRING
'COUNTS NUMERALS FOLLOWING THE DECIMAL POINT
   Dim dotFound As Boolean
   dotFound = False
   StrPrec = 0
   Dim i, iMax As Long
   iMax = Len(Entry)
   For i = 1 To iMax
      If Not dotFound Then
         If STRING_DOT = Mid(Entry, i, 1) Then
            dotFound = True
            Dim dotIndex As Long
            dotIndex = i
         End If
      ElseIf Not CharIsDigit(Mid(Entry, i, 1)) Then
         Exit Function
      Else
         StrPrec = StrPrec + 1
      End If
   Next i
End Function



Public Function StrToFloatStr(ByVal origString As String, ByRef floatString As String) As Boolean
'RETURNS TRUE IF FLOAT STRING FOUND
'USED FOR EXTRACTING ELEVATION FROM STRINGS
'ONLY STRINGS UP TO 40 CHARACTERS ALLOWED
   Dim MaxStringSize As Long
   MaxStringSize = 40
   StrToFloatStr = False
   Dim OrigStringSize As Long
   OrigStringSize = Len(origString)
   If OrigStringSize = 0 Or OrigStringSize > MaxStringSize Then
      Exit Function
   End If

'SET FLAGS
   Dim SignFound As Boolean
   SignFound = False
   Dim DecimalPointFound As Boolean
   DecimalPointFound = False
   Dim DigitFound As Boolean
   DigitFound = False

'INITIALIZE
   Dim StartIndex As Long
   StartIndex = 1
   Dim EndIndex As Long
   EndIndex = OrigStringSize

'LOOK THROUGH STRING
   Dim LastChar As String
   LastChar = ""
   Dim index As Long
   For index = 1 To OrigStringSize
      Dim ThisChar As String
      ThisChar = Mid(origString, index, 1)
      If ThisChar = "-" Then
'NEGATIVE SIGN ENCOUNTERED
         If DigitFound Then
            EndIndex = index - 1
            Exit For
         ElseIf DecimalPointFound Then
            StartIndex = index
            DecimalPointFound = False
            SignFound = True
         Else
            StartIndex = index
            SignFound = True
         End If
      ElseIf ThisChar = "." Then
'DECIMAL POINT ENCOUNTRED
         If DigitFound And DecimalPointFound Then
            EndIndex = index - 1
            Exit For
         ElseIf DigitFound Then
            DecimalPointFound = True
         ElseIf DecimalPointFound Then
            SignFound = False
            StartIndex = index
         ElseIf SignFound Then
            DecimalPointFound = True
         Else
            DecimalPointFound = True
            StartIndex = index
         End If
      ElseIf CharIsDigit(ThisChar) Then
'DIGIT ENCOUNTERED
         If (Not SignFound) And (Not DecimalPointFound) And (Not DigitFound) Then
            StartIndex = index
         End If
         DigitFound = True
      ElseIf ThisChar = "," Then
'COMMA ENCOUNTERED
         If LastChar = "," And DigitFound Then
            EndIndex = index - 2
            Exit For
         ElseIf DigitFound And DecimalPointFound Then
            EndIndex = index - 1
            Exit For
         ElseIf DecimalPointFound Then
            DecimalPointFound = False
            SignFound = False
         End If
      Else
'NON-NUMBER COMPONENT ENCOUNTERED
         If DigitFound Then
            EndIndex = index - 1
            Exit For
         Else
            SignFound = False
            DecimalPointFound = False
         End If
      End If
      LastChar = ThisChar
   Next index

'IF NO NUMBER ENCOUNTERED THEN EXIT
   If Not DigitFound Then
      Exit Function
   End If
   
'CHECK IF SUBSTRING IS A NUMBER
   Dim NumString As String
   NumString = Mid(origString, StartIndex, EndIndex - StartIndex + 1)
   If IsNumeric(NumString) Then
      floatString = NumString
      StrToFloatStr = True
   End If
End Function















'************************************************PRIVATE ROUTINES BEGIN HERE***********************************************
Private Sub AddZero(ByRef numStr As String)
'SUBROUTINE FOR ISDMSSTRING()
   If Len(numStr) < 2 Then
      numStr = numStr & STRING_ZERO
   End If
End Sub



Private Function BearingToSAz(degPart As Long, _
                              minPart As Long, _
                              secPart As Double, _
                              quad As Integer) As Double
'CONVERT BEARING TO SOUTH AZIMUTH
   Dim bearAngle As Double
   bearAngle = DmsToDec(degPart, minPart, secPart)
   Select Case quad
      Case QUAD_NORTH_EAST
         BearingToSAz = 180# + bearAngle
      Case QUAD_SOUTH_EAST
         BearingToSAz = 360# - bearAngle
      Case QUAD_SOUTH_WEST
         BearingToSAz = bearAngle
      Case QUAD_NORTH_WEST
         BearingToSAz = 180# - bearAngle
   End Select
End Function



Private Function CharIsDigit(ByVal ThisChar As String) As Boolean
'RETURNS TRUE IF IT IS A LETTER
   Dim character As Integer
   character = Asc(ThisChar)
   CharIsDigit = (character >= Asc("0")) And (character <= Asc("9"))
End Function



Private Function CharIsALetter(ByVal chrStr As String) As Boolean
'RETURNS TRUE IF IT IS A LETTER
   Dim character As Integer
   character = Asc(UCase(chrStr))
   CharIsALetter = (character >= Asc("A")) And (character <= Asc("Z"))
End Function



Private Function DMSString(DegreesPart As Long, _
                           minutesPart As Long, _
                           secondsPart As Double, _
                           precision As Long, _
                           style As Integer) As String
'JUST STRAIGHT CREATES STRING FROM VALUES.  NO ROUNDING OR CHANGING DONE.
'ALL VALUES ARE TO BE POSITIVE

'PRECISION AS IN DDD.MMSS, 0 IS DEGREES ONLY, 1 AND 2 ARE TO THE MINUTE,
'3 AND 4 ARE TO THE SECOND.  ANYTHING BEYOND THAT IS FRACTIONAL SECONDS.
'5 WOULD BE TO THE TENTH OF A SECOND 0.12345.
   
'INITIALIZE
   Dim Seconds As Double
   Seconds = 0
   Dim minutesString As String
   minutesString = ""
   Dim secondsString As String
   secondsString = ""

'CREATE DEGREES PART
   Dim degreesString As String
   degreesString = FormatNumber(DegreesPart, 0, vbTrue, vbFalse, vbTrue)
   If (style And STYLE_ANGLE_DEG_LEAD) And (Abs(DegreesPart) < 10) Then
      degreesString = STRING_ZERO & degreesString
   End If
'APPLY DEGREE SYMBOL
   If (style And STYLE_ANGLE_CARET) Then
      degreesString = degreesString & STRING_CARET
   Else
      degreesString = degreesString & OtherDegSymbol()
   End If

'CREATE MINUTES PART
   If precision > 0 Then
      minutesString = FormatNumber(minutesPart, 0, vbTrue, vbFalse, vbTrue) & "'"
      If (style And STYLE_ANGLE_LEAD) And (minutesPart < 10) Then
         minutesString = STRING_ZERO & minutesString
      End If
      If (style And STYLE_ANGLE_SPACE) Then
         minutesString = STRING_SPACE & minutesString
      End If
   End If

'CREATE SECONDS PART
   If precision > 2 Then
      Dim secPrec As Long
      secPrec = 0
      If precision > 4 Then
         secPrec = precision - 4
      End If
      secondsString = FormatNumber(secondsPart, secPrec, vbTrue, vbFalse, vbTrue)
      If (style And STYLE_ANGLE_LEAD) Then
         Seconds = CDbl(secondsString)
         If Seconds < 10 Then
            secondsString = STRING_ZERO & secondsString
         End If
      End If
      If (style And STYLE_ANGLE_SPACE) Then
         secondsString = STRING_SPACE & secondsString
      End If
      secondsString = secondsString & QuoteSymbol()
   End If

'LEAVE OFF ZERO SECONDS IF STYLE IS CHOSEN
   If (style And STYLE_ANGLE_NO_00_SEC) And (Seconds = 0) Then
      secondsString = ""
   End If

'LEAVE OFF ZERO MINUTES ZERO SECONDS IF STYLE IS CHOSEN
   If (style And STYLE_ANGLE_NO_00_MIN) And (Seconds = 0) Then
      secondsString = ""
      If minutesPart = 0 Then
         minutesString = ""
      End If
   End If

'ASSEMBLE AND RETURN THE STRING
   DMSString = degreesString & minutesString & secondsString
End Function



Private Function DoubleToAxisString(ByVal theValue As Double, _
                                    precision As Long, _
                                    positiveString As String, _
                                    negativeString As String, _
                                    Optional space As Boolean = True) As String
   theValue = Round(theValue, precision)
   If theValue < 0 Then
      theValue = Abs(theValue)
      Dim signString As String
      signString = negativeString
   Else
      signString = positiveString
   End If
   If space Then
      signString = " " & signString
   End If
   DoubleToAxisString = FormatNumber(theValue, precision, vbTrue, vbFalse, vbTrue) & signString
End Function



Private Function FoundRightMostNum(ByVal pointNameStr As String, _
                                   ByRef prefixStr As String, _
                                   ByRef NumString As String) As Boolean
'RETURNS TRUE IF NUM STRING FOUND,
'IF FOUND, ALSO RETURNS NUMBER STRING AND THE PREFIX STRING
'FUNCTION USED BY POINT NAME CHECKING AND GENERATING ROUINES
   Dim length As Long
   length = Len(pointNameStr)
   Dim index As Long
   index = length
'SEARCH FOR FIRST NON-DIGIT FROM RIGHT
   FoundRightMostNum = False
   Do While index >= 1
      If CharIsDigit(Mid(pointNameStr, index, 1)) Then
         FoundRightMostNum = True
         index = index - 1
      Else
         Exit Do
      End If
   Loop
   If FoundRightMostNum Then
      NumString = Mid(pointNameStr, index + 1, length - index)
      If index = 0 Then
         prefixStr = ""
      Else
         prefixStr = Left(pointNameStr, index)
      End If
   End If
End Function



Private Function IncLetter(ByVal OrigStr As String, ByVal LastChar As String) As String
'INCREMENT LETTER
'EXAMPLE SS9-7A -> SS9-7B
'IF IT'S Z THEN APPEND 1
'EXAMPLE SS9-7Z -> SS 9-7Z1
'IF TOO LONG TO APPEND 1 TO END, THEN GO BACK TO 1
'EXAMPLE 12345678901234567Z -> 1

   If LastChar = "Z" Or LastChar = "z" Then
'LAST CHAR IS Z, APPEND 1 IF CAN
      If Len(OrigStr) < MAX_LEN_POINT_NAME Then
         IncLetter = OrigStr & "1"
      Else
'TOO LONG RESTART AT 1
         IncLetter = "1"
      End If
   Else
'LAST CHARACTER IS NOT Z OR z, JUST INCREMENT
      IncLetter = Left(OrigStr, Len(OrigStr) - 1) & Chr(Asc(LastChar) + 1)
   End If
End Function



Public Sub InitializeCheckBox(theCheckBox As CheckBox, _
                              Section As String, _
                              Key As String, _
                              Optional defaultState As String = OPTION_TRUE)
   Dim myOption As String
   myOption = GetSetting(APP_NAME, Section, Key, defaultState)
   If myOption = OPTION_TRUE Then
      theCheckBox.value = True
   Else
      theCheckBox.value = False
   End If
End Sub



Private Function IsAxisScalerString(ByVal theString As String, _
                                    positiveString As String, _
                                    negativeString As String, _
                                    ByRef theScaler As Double, _
                                    ByRef origPrec As Long) As Boolean
'RETURNS TRUE IF GOOD
'CHECKS IF VALID STRINGS FOR NORTHING, EASTING FIELDS
   IsAxisScalerString = False

'IF IT'S JUST KEYED IN AS A NUMBER
   If IsNumeric(theString) Then
      theScaler = CDbl(theString)
      If Abs(theScaler) > MAX_COORDINATE Then
         Exit Function
      End If
      origPrec = StrPrec(theString)
      IsAxisScalerString = True
      Exit Function
   End If

'IF IT IS KEYED IN WITH THE AXIS LABELS
   Dim length As Long
   length = Len(theString)
   If length < 2 Then
      Exit Function
   End If

'GET BEGINNING PART OF THE STRING
   Dim begPartString As String
   begPartString = Mid(theString, 1, length - 1)

'MAKE SURE IT'S NUMERIC
   If Not IsNumeric(begPartString) Then
      Exit Function
   End If
   
'MAKE SURE THERE'S NO NEGATIVE SIGN OR NUMBER TOO BIG
   Dim scaler As Double
   scaler = CDbl(begPartString)
   If scaler < 0 Or scaler > MAX_COORDINATE Then
      Exit Function
   End If

'GET SIGN
   Dim LastChar As String
   LastChar = UCase(Mid(theString, length, length))

'ALSO ACCEPT NEGATIVE SIGN AT END OF STRING
   If LastChar = negativeString Or LastChar = STRING_MINUS Then
      theScaler = -scaler
      origPrec = StrPrec(begPartString)
      IsAxisScalerString = True
      Exit Function
   End If
   
'ALSO ACCEPT POSITIVE SIGN AT END OF STRING
   If LastChar = positiveString Or LastChar = STRING_PLUS Then
      theScaler = scaler
      origPrec = StrPrec(begPartString)
      IsAxisScalerString = True
      Exit Function
   End If
End Function



Private Function IsDmsString(Entry As String, _
                             ByRef origPrec As Long, _
                             ByRef degPart As Long, _
                             ByRef minPart As Long, _
                             ByRef secPart As Double, _
                             ByVal degLim As Long, _
                             ByVal lessThanLim As Boolean) As Boolean
'RETURNS TRUE IF OK
'DON'T FORGET TO TRIM ENTRY BEFORE USING THIS FUNCTION
'NOT TRIMMING IS USEFUL FOR DETECTING SPACE BETWEEN MINUS SIGN
'AND DIRECTION ANGLE

'INITIALIZE FLAG
   IsDmsString = False
   
'CHECK IF STRING IS LONG ENOUGH AND SHORT ENOUGH
'MAKE SURE NOT ABSURD LENGTH
'RETURNS TRUE IF OK
   Dim StringLength As Long
   StringLength = Len(Entry)
   If (StringLength < 1) Or (StringLength > MAX_LEN_DIR_STRING) Then
      Exit Function
   End If

'BREAK STRING INTO PIECES
   Dim piecesArray As Variant
   piecesArray = StringToArray(Entry)
   Dim FirstIndex As Long
   FirstIndex = LBound(piecesArray)
   Dim lastIndex As Long
   lastIndex = UBound(piecesArray)
   
'IF IT IS NUMERIC, MAYBE IT'S AN UNFORMATTED AZIMUTH
   If IsNumeric(Entry) Then
'MAKE SURE FIRST CHARACTER IS NOT A SIGN
      If piecesArray(FirstIndex) = STRING_PLUS Or piecesArray(FirstIndex) = STRING_MINUS Then
         Exit Function
      End If
      
'MAKE SURE IT'S NOT NEGATIVE
      Dim negCheck As Double
      negCheck = CDbl(Entry)
      If negCheck < 0 Then
         Exit Function
      End If

'CHECK FOR WAYWARD PLUS SIGN
      If InStr(1, Entry, STRING_PLUS) Then
         Exit Function
      End If

'PARSE SHORT NOTATION STRING
      Dim pointFound As Boolean
      pointFound = False
      Dim degFound As Boolean
      degFound = False
      Dim minFound As Boolean
      minFound = False
      Dim secFound As Boolean
      secFound = False
      Dim degStr As String
      degStr = ""
      Dim minStr As String
      minStr = ""
      Dim secStr As String
      secStr = ""
      Dim secondsIndex As Long
      Dim index As Long
      
      For index = FirstIndex To lastIndex
'GATHERING MINUTES PART
         If pointFound Then
            If index < secondsIndex Then
               minFound = True
               minStr = minStr & piecesArray(index)

'GATHERING SECONDS PART
            Else
               secFound = True
               secStr = secStr & piecesArray(index)
            End If

'GATHERING DEGREES PART
         Else
            If piecesArray(index) = STRING_DOT Then
               Dim pointIndex As Long
               pointIndex = index
               pointFound = True
               secondsIndex = index + 3
            Else
               degStr = degStr & piecesArray(index)
               degFound = True
            End If
         End If
      Next index
      
'DETERMINE ORIGINAL PRECISION
      If pointFound Then
         Dim ogPrec As Long
         ogPrec = lastIndex - pointIndex
      Else
         ogPrec = 0
      End If

'CONVERT TEXT TO NUMBERS
      If degFound Then
'MAKE SURE NOT TOO LONG
         If Len(degStr) > 5 Then
            Exit Function
         End If
         Dim DegreesPart  As Long
         DegreesPart = CLng(degStr)
      Else
         DegreesPart = 0
      End If
      AddZero minStr
      Dim minutesPart As Long
      minutesPart = CLng(minStr)
      AddZero secStr
      Dim secondsPart As Double
      secondsPart = CDbl(STRING_DOT & secStr) * 100

'CHECK FOR INVALID VALUES
      If DegreesPart > degLim Or minutesPart >= 60 Or secondsPart >= 60 Then
         Exit Function
      End If

      If DegreesPart = 360 Then
         If (minutesPart <> 0 Or secondsPart <> 0) Or lessThanLim Then
            Exit Function
         End If
      End If
      
'RETURN VALUES
      origPrec = ogPrec
      degPart = DegreesPart
      minPart = minutesPart
      secPart = secondsPart
      IsDmsString = True
      Exit Function
   End If

'IF FIRST CHARACTER IS A NUMBER, IT COULD BE A FORMATTED AZIMUTH STRING
   If CharIsDigit(piecesArray(FirstIndex)) Then
      Dim secondsString As String
      secondsString = QuoteSymbol()
      ogPrec = 0
      minutesPart = 0
      secondsPart = 0
      degFound = False
      minFound = False
      secFound = False
      degStr = piecesArray(FirstIndex)
      minStr = ""
      secStr = ""
      Dim otherDegSym As String
      otherDegSym = OtherDegSymbol()
      lastIndex = UBound(piecesArray)
      
'PARSE FORMATTED STRING
      Dim spaceOK As Long
      For index = FirstIndex + 1 To lastIndex
'IF SECONDS PART FOUND, THERE ARE EXTRA CHARACTERS, NO GOOD
         If secFound Then
            Exit Function
         End If

'GATHERING SECONDS PART
         If minFound Then
            If piecesArray(index) = secondsString Then
               If IsNumeric(secStr) Then
                  secFound = True
               End If
            ElseIf index = spaceOK And piecesArray(index) = STRING_SPACE Then
               'DO NOTHING
            ElseIf CharIsDigit(piecesArray(index)) Then
               secStr = secStr & piecesArray(index)
            ElseIf piecesArray(index) = STRING_DOT Then
               secStr = secStr & piecesArray(index)
            Else
               Exit Function
            End If
            
'GATHERING MINUTES PART
         ElseIf degFound Then
            If CharIsDigit(piecesArray(index)) Then
               minStr = minStr & piecesArray(index)
            ElseIf piecesArray(index) = "'" Then
               minFound = True
               spaceOK = index + 1
            ElseIf index = spaceOK And piecesArray(index) = STRING_SPACE Then
               'DO NOTHING
            Else
               Exit Function
            End If

'GATHERING DEGREES PART
         Else
            If CharIsDigit(piecesArray(index)) Then
               degStr = degStr & piecesArray(index)
            ElseIf piecesArray(index) = otherDegSym Then
               degFound = True
               spaceOK = index + 1
            ElseIf piecesArray(index) = STRING_CARET Then
               degFound = True
               spaceOK = index + 1
            Else
               Exit Function
            End If
         End If
      Next index
      
'CHECK VALUES
      If degFound Then
         Dim length As Long
         length = Len(degStr)
         If length > 5 Or length = 0 Then
            Exit Function
         End If
         DegreesPart = CLng(degStr)
      Else
         Exit Function
      End If
            
      If DegreesPart >= degLim Then
         Exit Function
      End If
      
      If minFound Then
         length = Len(minStr)
         If length > 2 Or length = 0 Then
            Exit Function
         End If
         minutesPart = CLng(minStr)
         If minutesPart >= 60 Then
            Exit Function
         End If
         ogPrec = 2
      ElseIf minStr <> "" Then
         Exit Function
      End If
      
      If secFound Then
         secondsPart = CDbl(secStr)
         If secondsPart >= 60 Or secondsPart < 0 Then
            Exit Function
         End If
         ogPrec = 4 + StrPrec(secStr)
      ElseIf secStr <> "" Then
         Exit Function
      End If
      
'RETURN VALUES
      origPrec = ogPrec
      degPart = DegreesPart
      minPart = minutesPart
      secPart = secondsPart
      IsDmsString = True
   End If
End Function



Private Function IsOffsetString(Entry As String, _
                                maxVal As Double, _
                                ByRef offset As Double, _
                                ByRef origPrec As Long, _
                                ByRef leftOption As Boolean, _
                                ByRef rightOption As Boolean) As Boolean
'SUB-FUNCTION FOR OFFSET TEXT BOX ROUTINE
   IsOffsetString = False
   If IsNumeric(Entry) Then
      Dim value As Double
      value = CDbl(Entry)
      If Abs(value) > maxVal Then
         Exit Function
      End If
      leftOption = False
      rightOption = False
      If value < 0 Then
         leftOption = True
      ElseIf InStr(1, Entry, "+") Then
         rightOption = True
      End If
      offset = Abs(value)
      origPrec = StrPrec(Entry)
      IsOffsetString = True
   End If
End Function



Private Function IsPNameLenOK(ByVal pName As String) As Boolean
'RETURNS TRUE IF OKAY
   IsPNameLenOK = False
   Dim length As Long
   length = Len(pName)
   If length < 1 Then
      Exit Function
   End If
   If length > MAX_LEN_POINT_NAME Then
      Exit Function
   End If
   IsPNameLenOK = True
End Function



Private Function IsStaStr(ByVal theString As String, _
                          ByRef TheStation As Double, _
                          ByRef origPrec As Long, _
                          style As Integer) As Boolean
'RETURNS TRUE IF SUCCESSFUL IN CONVERTING STRING TO STATION IN MASTER UNITS
'INITIALIZE FLAG
   IsStaStr = False
'MAKE SURE IT'S NOT JUST SPACES
   Dim stationString As String
   stationString = Trim(theString)

'MAKE SURE THERE IS A GOOD RANGE OF CHARACTERS
   Dim StringLen As Long
   StringLen = Len(stationString)
   If StringLen < 4 Or StringLen > MAX_LEN_STA_STRING Then
      Exit Function
   End If

'BREAK IT UP INTO A CHARACTER ARRAY
   Dim stringArray As Variant
   stringArray = StringToArray(stationString)

'GET ITS LIMITS
   Dim arrayPointer As Long
   arrayPointer = LBound(stringArray)
   Dim lastElement As Long
   lastElement = UBound(stringArray)

'CHECK FOR NEGATIVE SIGN
   If stringArray(arrayPointer) = STRING_MINUS Then
      Dim isNegative As Boolean
      isNegative = True
      arrayPointer = arrayPointer + 1
   End If

'GET STATION PART
   Dim doubleString As String
   doubleString = ""
   Dim plusNotFound As Boolean
   plusNotFound = True
   Do While arrayPointer < lastElement And plusNotFound
      If CharIsDigit(stringArray(arrayPointer)) Then
         doubleString = doubleString + stringArray(arrayPointer)
      ElseIf stringArray(arrayPointer) = STRING_PLUS Then
         plusNotFound = False
      Else
         Exit Function
      End If
      arrayPointer = arrayPointer + 1
   Loop
   If plusNotFound Or arrayPointer >= lastElement Then
      Exit Function
   End If

   If isNegative And arrayPointer < 2 Then
      Exit Function
   End If
   
   If arrayPointer < 1 Then
      Exit Function
   End If

'GET FEET/METER PART UP TO THE DECIMAL POINT
   Dim places As Long
   places = 0
   Dim dotNotFound As Boolean
   dotNotFound = True
   Do While arrayPointer <= lastElement And dotNotFound
      If CharIsDigit(stringArray(arrayPointer)) Then
         doubleString = doubleString & stringArray(arrayPointer)
         places = places + 1
      ElseIf stringArray(arrayPointer) = STRING_DOT Then
         doubleString = doubleString & STRING_DOT
         dotNotFound = False
      Else
         Exit Function
      End If
      arrayPointer = arrayPointer + 1
   Loop
   
   If (style And STYLE_STATION_METRIC) Then
      If places <> 3 Then
         Exit Function
      End If
   ElseIf places <> 2 Then
      Exit Function
   End If

'GET THE FRACTIONAL FOOT/METER PART
   Dim ogPrec As Long
   ogPrec = 0
   Do While arrayPointer <= lastElement
      If CharIsDigit(stringArray(arrayPointer)) Then
         doubleString = doubleString & stringArray(arrayPointer)
         ogPrec = ogPrec + 1
      Else
         Exit Function
      End If
      arrayPointer = arrayPointer + 1
   Loop

'CHECK IF IT IS NUMERIC, CONVERT TO DOUBLE IF IT IS
   If IsNumeric(doubleString) Then
      TheStation = CDbl(doubleString)
      If isNegative Then
         TheStation = -TheStation
      End If
   End If

'MAKE SURE NOT TOO BIG
   If Abs(TheStation) > MAX_STATION Then
      Exit Function
   End If
   origPrec = ogPrec
   IsStaStr = True
End Function



Private Function IsSpecialChar(ByVal charStr As String) As Boolean
'RETURNS TRUE IF IT IS AN ALLOWABLE SPECIAL CHARACTER
   IsSpecialChar = True
   Select Case charStr
      Case "-"
         Exit Function
      Case "_"
         Exit Function
      Case " "
         Exit Function
      Case ":"
         Exit Function
      Case "."
         Exit Function
   End Select
   IsSpecialChar = False
End Function



Private Function IsValidChar(ByVal charStr As String) As Boolean
'RETURNS TRUE IF CHARACTER IS NOT AN ILLEGAL CHARACTER
   IsValidChar = True
   If CharIsDigit(charStr) Then
      Exit Function
   End If
   If CharIsALetter(charStr) Then
      Exit Function
   End If
   If IsSpecialChar(charStr) Then
      Exit Function
   End If
   IsValidChar = False
End Function



Private Sub LeadingZero(ByVal OrigStr As String, ByRef newString As String)
   Dim charStr As String
   charStr = Left(OrigStr, 1)
   If charStr = "0" Then
      Dim OrigLen As Long
      OrigLen = Len(OrigStr)
      Dim NewLen As Long
      NewLen = Len(newString)
      Dim i As Long
      For i = 1 To OrigLen - NewLen
         newString = STRING_ZERO & newString
      Next i
   End If
End Sub



Private Function OtherDegSymbol() As String
'CREATES DEGREE SYMBOL STRING
   OtherDegSymbol = Chr(176)
End Function



Private Function QuoteSymbol() As String
'CREATES QUOTATION MARK STRING
   QuoteSymbol = Chr(34)
End Function



Public Function ReplaceDegreeSymbol(InputString) As String
   If InputString = "" Then
      ReplaceDegreeSymbol = ""
   Else
      ReplaceDegreeSymbol = Replace(InputString, STRING_CARET, OtherDegSymbol())
   End If
End Function



Public Function ReplaceDegreeSymbol2(InputString) As String
   If InputString = "" Then
      ReplaceDegreeSymbol2 = ""
   Else
      ReplaceDegreeSymbol2 = Replace(InputString, OtherDegSymbol(), STRING_CARET)
   End If
End Function




Private Sub ReverseForNorthMode(degPart As Long)
'USED TO CONVERT SOUTH AZIMUTH DMS TO NORTH AZIMUTH DMS
   If NORTH_AZIMUTH_MODE Then
      degPart = (degPart + 180) Mod 360
   End If
End Sub



Private Function StringToArray(myString As String) As Variant
'BREAKS STRING UP INTO ARRAY OF SINGLE CHARATER STRINGS
   Dim myArray() As Variant
   Dim i, iMax As Integer
   iMax = Len(myString)
   ReDim myArray(1 To iMax)
   For i = 1 To iMax
      myArray(i) = Mid(myString, i, 1)
   Next i
   StringToArray = myArray
End Function

Attribute VB_Name = "arcLineIntpickPrimitive"
Attribute VB_Base = "0{FCFB3D2A-A0FA-1068-A738-08002B3371B5}"
Attribute VB_GlobalNameSpace = False
Attribute VB_Creatable = False
Attribute VB_PredeclaredId = False
Attribute VB_Exposed = False
Attribute VB_TemplateDerived = False
Attribute VB_Customizable = False
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit

Implements IPrimitiveCommandEvents


Private int1 As Point3d
Private int2 As Point3d



Public Property Let IntersectionA(IntersectionPt As Point3d)
   int1 = IntersectionPt
End Property



Public Property Let IntersectionB(IntersectionPt As Point3d)
   int2 = IntersectionPt
End Property



Private Sub IPrimitiveCommandEvents_Cleanup()
   FrmArcLineInt.Show
End Sub



Private Sub IPrimitiveCommandEvents_DataPoint(point As Point3d, ByVal view As view)
   Dim closerIntersect As Point3d
   closerIntersect = closerInt(point, int1, int2)
   FrmArcLineInt.IntChosen closerIntersect
   CommandState.StartDefaultCommand
End Sub



Private Sub IPrimitiveCommandEvents_Dynamics(point As Point3d, ByVal view As view, ByVal DrawMode As MsdDrawingMode)
'DRAW THE CIRCLE
   Dim radius As Double
   radius = CDbl(FrmArcLineInt.Rad2TextBox.text)
   Dim RP2 As Point3d
   RP2 = FrmArcLineInt.GetRP()
   Dim Arc2 As EllipseElement
   Set Arc2 = CreateEllipseElement2(Nothing, RP2, radius, radius, Matrix3dIdentity)
   Arc2.color = GetTetherColor()
   Arc2.Redraw DrawMode

'DRAW RADIAL LINE
   Dim closerIntersect As Point3d
   closerIntersect = closerInt(point, int1, int2)
   Dim lineTo1 As LineElement
   closerIntersect.z = RP2.z
   Set lineTo1 = CreateLineElement2(Arc2, RP2, closerIntersect)
   lineTo1.Redraw DrawMode
   
'DRAW LINE FROM POL TO INTERSECTION
   Dim lineTo2 As LineElement
   Set lineTo2 = CreateLineElement2(Arc2, FrmArcLineInt.GetPOL(), closerIntersect)
   lineTo2.Redraw DrawMode
End Sub



Private Function closerInt(pointer As Point3d, int1 As Point3d, int2 As Point3d) As Point3d
   Dim distTo1 As Double
   distTo1 = InverseHD(int1, pointer)
   Dim distTo2 As Double
   distTo2 = InverseHD(int2, pointer)
   If distTo1 < distTo2 Then
      closerInt = int1
   Else
      closerInt = int2
   End If
End Function



Private Sub IPrimitiveCommandEvents_Keyin(ByVal Keyin As String)

End Sub



Private Sub IPrimitiveCommandEvents_Reset()
   CommandState.StartDefaultCommand
End Sub




Private Sub IPrimitiveCommandEvents_Start()
   ShowCommand COMMAND_NAME_ARC_LINE_INT
   ShowPrompt "Choose intersection Point/Reset to cancel"
   CommandState.DisableAccuSnap
   CommandState.StartDynamics
End Sub

Attribute VB_Name = "cogo"
'LICENSE:
'This is free and unencumbered software released into the
'public domain.

'Anyone is free to copy, modify, publish, use, compile, sell, or
'distribute this software, either in source code form or as a
'compiled binary, for any purpose, commercial or non-commercial,
'and by any means.

'In jurisdictions that recognize copyright laws, the author or
'authors of this software dedicate any and all copyright interest
'in the software to the public domain. We make this dedication for
'the benefit of the public at large and to the detriment of our
'heirs and successors. We intend this dedication to be an overt act
'of relinquishment in perpetuity of all present and future rights to
'this software under copyright law.

'THE SOFTWARE IS PROVIDED "AS IS", WITHOUT WARRANTY OF ANY KIND,
'EXPRESS OR IMPLIED, INCLUDING BUT NOT LIMITED TO THE WARRANTIES
'OF MERCHANTABILITY, FITNESS FOR A PARTICULAR PURPOSE AND
'NONINFRINGEMENT. IN NO EVENT SHALL THE AUTHORS BE LIABLE FOR ANY
'CLAIM, DAMAGES OR OTHER LIABILITY, WHETHER IN AN ACTION OF
'CONTRACT, TORT OR OTHERWISE, ARISING FROM, OUT OF OR IN
'CONNECTION WITH THE SOFTWARE OR THE USE OR OTHER DEALINGS IN THE
'SOFTWARE.

Option Explicit

Public Sub Inverse(startPoint As Point3d, _
                   endPoint As Point3d, _
                   ByRef southAz As Double, _
                   ByRef horizontalDist As Double)
'RETURNS SOUTH AZIMUTH IN DEGREES AND HORIZONTAL DISTANCE IN MASTER UNITS
   Dim dX As Double
   dX = endPoint.X - startPoint.X
   Dim dY As Double
   dY = endPoint.Y - startPoint.Y
   southAz = InverseAz(dY, dX)
   horizontalDist = InverseDistance(dY, dX)
End Sub


Public Function InverseAz(ByVal dY As Double, ByVal dX As Double) As Double
'RETURNS SOUTH AZIMUTH IN DEGREES
   Dim direction As Double
   direction = Atn2(dY, dX)
'CONVERT TO CLOCKWISE
   direction = -direction
'CONVERT TO DEGREES
   Dim directionDegrees As Double
   directionDegrees = Degrees(direction)
'CONVERT TO SOUTH AZIMUTH
   directionDegrees = directionDegrees + 270#
'MAKE SURE 360 > DIRECTIONDEGREES >= 0
    MakeSure360 directionDegrees
'RETURN VALUE
   InverseAz = directionDegrees
End Function



Public Function InverseAzimuth(startPoint As Point3d, endPoint As Point3d) As Double
'RETURNS SOUTH AZIMUTH IN DEGREES
   InverseAzimuth = InverseAz(endPoint.Y - startPoint.Y, endPoint.X - startPoint.X)
End Function



Public Function InverseDistance(ByVal dY As Double, ByVal dX As Double) As Double
   InverseDistance = Sqr((dX ^ 2) + (dY ^ 2))
End Function



Public Function InverseHD(startPoint As Point3d, endPoint As Point3d) As Double
'RETURNS HORIZONTAL DISTANCE IN MASTER UNITS
   InverseHD = InverseDistance(endPoint.Y - startPoint.Y, endPoint.X - startPoint.X)
End Function



Public Function CalcMidPoint(pointA As Point3d, pointB As Point3d) As Point3d
'CALCULATE AND RETURN MID POINT BETWEEN TWO POINTS
   Dim midPoint As Point3d
   midPoint.X = (pointA.X - pointB.X) / 2 + pointB.X
   midPoint.Y = (pointA.Y - pointB.Y) / 2 + pointB.Y
   midPoint.z = (pointA.z - pointB.z) / 2 + pointB.z
   CalcMidPoint = midPoint
End Function



Public Function CoordFwdSAz(startPoint As Point3d, ByVal southAzInDegrees As Double, ByVal distance As Double) As Point3d
'CONVERT SOUTH AZIMUTH INTO ANGLE LEFT IN RADIANS FROM EAST AXIS
   Dim AngleInRadians As Double
   AngleInRadians = Radians(-southAzInDegrees + 90) - Pi
'CALCULATE HORIZONTAL COORDINATE FORWARD
   CoordFwdSAz.Y = Sin(AngleInRadians) * distance + startPoint.Y
   CoordFwdSAz.X = Cos(AngleInRadians) * distance + startPoint.X
'Z REMAINS UNCHANGED
   CoordFwdSAz.z = startPoint.z
End Function



Public Function CoordFwdSAz2(startPoint As Point3d, _
                             southAzInDegrees As Double, _
                             distance As Double, _
                             ByRef latitude As Double, _
                             ByRef departure As Double) As Point3d
'CONVERT SOUTH AZIMUTH INTO ANGLE LEFT IN RADIANS FROM EAST AXIS
   Dim AngleInRadians As Double
   AngleInRadians = Radians(-southAzInDegrees + 90) - Pi
'CALCULATE HORIZONTAL COORDINATE FORWARD
   latitude = Sin(AngleInRadians) * distance
   CoordFwdSAz2.Y = latitude + startPoint.Y
   departure = Cos(AngleInRadians) * distance
   CoordFwdSAz2.X = departure + startPoint.X
'Z REMAINS UNCHANGED
   CoordFwdSAz2.z = startPoint.z
End Function



Public Function sAzToRay(OriginPt As Point3d, southAzDecimal As Double) As Ray3d
   Dim Vect As Point3d
   Vect = CoordFwdSAz(Point3dFromXYZ(0, 0, 0), southAzDecimal, 1)
   Dim newRay As Ray3d
   newRay.origin = OriginPt
   newRay.direction = Vect
   sAzToRay = newRay
End Function



Public Function calcPI(startPoint As Point3d, _
                       endPoint As Point3d, _
                       tangentInSAz As Double, _
                       tangentOutSAz As Double, _
                       ByRef thePI As Point3d) As Boolean
'TRY TO SOLVE
   Dim Ray1 As Ray3d
   Ray1 = sAzToRay(startPoint, tangentInSAz)
   Dim Ray2 As Ray3d
   Ray2 = sAzToRay(endPoint, tangentOutSAz)

   Dim Inter2 As Point3d
   Dim Frac1 As Double
   Dim Frac2 As Double
   calcPI = Ray3dRay3dIntersectXY(Ray1, Ray2, thePI, Frac1, Inter2, Frac2)
End Function
